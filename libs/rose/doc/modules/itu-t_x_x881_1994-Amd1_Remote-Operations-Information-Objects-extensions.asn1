-- Module Remote-Operations-Information-Objects-extensions (X.881:07/1994)
-- See also ITU-T X.881 (1994) Amend. 1 (11/1995)
-- See also the index of all ASN.1 assignments needed in this document

Remote-Operations-Information-Objects-extensions {joint-iso-itu-t
  remote-operations(4) informationObjects-extensions(8) version2(1)}
DEFINITIONS ::=
BEGIN

-- exports everything
IMPORTS
  CONTRACT
    FROM Remote-Operations-Information-Objects {joint-iso-itu-t
      remote-operations(4) information-Objects(5) version2(1)}
  probe, acknowledge
    FROM Remote-Operations-Useful-Definitions {joint-iso-itu-t
      remote-operations(4) useful-definitions(7) version2(1)};

APPLICATION-CONTEXT ::= CLASS {
  &probe                   BOOLEAN DEFAULT FALSE,
  &acknowledge             BOOLEAN DEFAULT FALSE,
  &associationContract     CONTRACT,
  &associationRealization  REALIZATION OPTIONAL,
  &transferRealization     REALIZATION,
  &AbstractSyntaxes        ABSTRACT-SYNTAX,
  &applicationContextName  OBJECT IDENTIFIER UNIQUE
}
WITH SYNTAX {
  [PROBE &probe]
  [ACKNOWLEDGE &acknowledge]
  CONTRACT &associationContract
  [ESTABLISHED BY &associationRealization]
  INFORMATION TRANSFER BY &transferRealization
  ABSTRACT SYNTAXES &AbstractSyntaxes
  APPLICATION CONTEXT NAME &applicationContextName
}

REALIZATION ::= TYPE-IDENTIFIER

-- information objects ABSTRACT-SYNTAX and TYPE-IDENTIFIER are defined in ITU-T Rec. X.681 |
-- ISO/IEC 8824-2
END -- end of the information-objects-extensions module

-- Generated by Asnp, the ASN.1 pretty-printer of France Telecom R&D
