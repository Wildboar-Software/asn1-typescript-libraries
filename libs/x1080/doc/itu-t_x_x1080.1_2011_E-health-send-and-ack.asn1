-- Module E-health-send-and-ack (X.1080.1:10/2011)
-- See also ITU-T X.1080.1 (10/2011)
-- See also the index of all ASN.1 assignments needed in this document

E-health-send-and-ack {joint-iso-itu-t(2) telebiometrics(42)
  e-health-protocol(3) modules(0) send-and-ack(2) version1(1)}
  "/Telebiometrics/E_Health_Protocol/Modules/Send-and-ack/Version1"
  DEFINITIONS AUTOMATIC TAGS ::=
BEGIN

IMPORTS
  EncryptionOptions, IntegrityOptions
    FROM E-health-setup {joint-iso-itu-t(2) telebiometrics(42)
      e-health-protocol(3) modules(0) set-up(1) version1(1)};

-- Type and CLASS definitions for simple messages
SIMPLE-MESSAGE ::= CLASS {
  &id                 OBJECT IDENTIFIER UNIQUE,
  &Type               ,
  &Errors             ERROR,
  &registration-info  CHOICE {implicit  UTF8String,
                                  -- shall be reference to a web-site
                                  explicit  UniversalString,
                                  ...
  }
}
WITH SYNTAX {
  MESSAGE IDENTIFIED BY &id
  USING TYPE &Type
  POSSIBLE ERRORS &Errors
  REGISTERED AS &registration-info
}

ERROR ::= CLASS {&code       INTEGER,
                 &Parameter
}WITH SYNTAX {ERROR &code
              WITH &Parameter
}

Simple-Messages SIMPLE-MESSAGE ::=
  {...}

Identified-Simple-Message ::= SEQUENCE {
  sm-Identifier  SIMPLE-MESSAGE.&id({Simple-Messages}),
  sm-Content     SIMPLE-MESSAGE.&Type({Simple-Messages}{@sm-Identifier})
}

Command ::= SEQUENCE {
  encryptionOptions  EncryptionOptions,
  integrityOptions   IntegrityOptions,
  content
    OCTET STRING
      (CONSTRAINED BY {-- encoding of an Identified-Simple-Message value by the current ---- encoding rules included in a CMS ContentInfo sequence for encryption --

         -- and/or integrity if needed -- })
}

Ack ::= CHOICE {
  ok     NULL,
  error
    SEQUENCE {code       ERROR.&code({Simple-Message-Errors}),
              parameter  ERROR.&Parameter({Simple-Message-Errors}{@.code})
  }
}

Simple-Message-Errors ERROR ::= {Simple-Messages.&Errors}

Response ::= SEQUENCE {
  encryptionOptions  EncryptionOptions,
  integrityOptions   IntegrityOptions,
  content
    OCTET STRING
      (CONSTRAINED BY {-- encoding of an Ack value by the current encoding rules ---- included in a CMS ContentInfo sequence for encryption and/or --

         -- integrity if needed -- })
}

END

-- Generated by Asnp, the ASN.1 pretty-printer of France Telecom R&D
