USMSecurityParametersSyntax
DEFINITIONS IMPLICIT TAGS ::= BEGIN

UsmSecurityParameters ::= SEQUENCE {
    -- global User-based security parameters
    msgAuthoritativeEngineID     OCTET STRING,
    msgAuthoritativeEngineBoots  INTEGER (0..2147483647),
    msgAuthoritativeEngineTime   INTEGER (0..2147483647),
    msgUserName                  OCTET STRING (SIZE(0..32)),
    -- authentication protocol specific parameters
    msgAuthenticationParameters  OCTET STRING,
    -- privacy protocol specific parameters
    msgPrivacyParameters         OCTET STRING }

END
