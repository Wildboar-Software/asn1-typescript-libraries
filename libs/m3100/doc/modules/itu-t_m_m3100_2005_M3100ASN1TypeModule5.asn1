-- Module M3100ASN1TypeModule5 (M.3100:04/2005)
-- See also ITU-T M.3100 (04/2005)
-- See also the index of all ASN.1 assignments needed in this document

M3100ASN1TypeModule5 {itu-t recommendation m gnm(3100) informationModel(0)
  asn1Modules(2) asn1Module5(4)} DEFINITIONS IMPLICIT TAGS ::=
BEGIN

-- EXPORTS everything
IMPORTS
  ObjectInstance
    FROM CMIP-1 {joint-iso-itu-t ms(9) cmip(1) modules(0) protocol(3)}
  ManagementExtension, AdditionalInformation
    FROM Attribute-ASN1Module {joint-iso-itu-t ms(9) smi(3) part2(2)
      asn1Module(2) 1}
  Failed, PointerOrNull
    FROM ASN1DefinedTypesModule {itu-t recommendation m gnm(3100)
      informationModel(0) asn1Modules(2) asn1DefinedTypesModule(0)};

BridgeRollArg ::=
  SEQUENCE OF
    SEQUENCE {xc                   ObjectInstance,
              bridgeRollFromTp     ObjectInstance,
              bridgeRollToTp       ObjectInstance,
              bridgeRollOperation
                ENUMERATED {bridge(0), roll(1), releaseBridge(2), ...
                            },
              additionalInfo       SET OF ManagementExtension OPTIONAL
    }

BridgeRollReply ::=
  SEQUENCE OF
    CHOICE {bridgeFailed      [0]  Failed,
            bridgeRollResult  [1]  PointerOrNull}

END

-- Generated by Asnp, the ASN.1 pretty-printer of France Telecom R&D
