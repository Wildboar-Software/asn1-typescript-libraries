-- Module M3100ASN1TypeModule6 (M.3100:04/2005)
-- See also ITU-T M.3100 (04/2005)
-- See also the index of all ASN.1 assignments needed in this document

M3100ASN1TypeModule6 {itu-t recommendation m gnm(3100) informationModel(0)
  asn1Modules(2) asn1Module6(5)} DEFINITIONS IMPLICIT TAGS ::=
BEGIN

-- EXPORTS everything
IMPORTS
  ObjectInstance
    FROM CMIP-1 {joint-iso-itu-t ms(9) cmip(1) modules(0) protocol(3)}
  ManagementExtension, AdditionalInformation
    FROM Attribute-ASN1Module {joint-iso-itu-t ms(9) smi(3) part2(2)
      asn1Module(2) 1}
  Failed, ProblemCause, PointerOrNull
    FROM ASN1DefinedTypesModule {itu-t recommendation m gnm(3100)
      informationModel(0) asn1Modules(2) asn1DefinedTypesModule(0)};

CoincidentProtectedUnidirectionalConnections ::= SEQUENCE {
  protectedXC  ProtectedXC,
  multicastXC  MulticastXC
}

CoincidentUnidirectionalConnections ::= CHOICE {
  unprotected  [0]  CoincidentUnprotectedUnidirectionalConnections,
  protected    [1]  CoincidentProtectedUnidirectionalConnections
}

CoincidentUnprotectedUnidirectionalConnections ::= SEQUENCE {
  xcA  ObjectInstance,
  xcB  ObjectInstance
}

-- the term "coincident" is used to describe unidirectional connections between
-- the same bidirectional termination points.
ConvertMulticastToPtoPInfo ::= SEQUENCE OF ObjectInstance

ConvertMulticastToPtoPReply ::=
  SEQUENCE OF CHOICE {failed   Failed,
                      success  ObjectInstance}

-- the ith element of the reply corresponds to the ith element of
-- the information syntax
ConvertPtoPToMulticastInfo ::= SEQUENCE OF ObjectInstance

ConvertPtoPToMulticastReply ::=
  SEQUENCE OF
    CHOICE {failed   [0]  Failed,
            success  [1]  SEQUENCE {mpXC  ObjectInstance,
                                    xC    ObjectInstance}}

-- the ith element of the reply corresponds to the ith element of
-- the information syntax
JoinXCInfo ::= SEQUENCE OF CoincidentUnidirectionalConnections

JoinXCReply ::=
  SEQUENCE OF
    CHOICE {failed   [0]  Failed,
            success
              [1]  CHOICE {unprotected  ObjectInstance,
                           protected    ProtectedXC}}

-- the ith element of the reply corresponds to the ith element of
-- the information syntax
MulticastXC ::= SEQUENCE {
  mpXC  ObjectInstance,
  xcA   ObjectInstance,
  xcB   ObjectInstance
}

ProtectedXC ::= SEQUENCE {
  conProtGroup  ObjectInstance,
  conProtA      ObjectInstance,
  conProtB      ObjectInstance
}

SplitXCInfo ::= SEQUENCE OF ObjectInstance

SplitXCReply ::=
  SEQUENCE OF
    CHOICE {failed   Failed,
            success  CoincidentUnidirectionalConnections}

-- the ith element of the reply corresponds to the ith element of
-- the information syntax
END

-- Generated by Asnp, the ASN.1 pretty-printer of France Telecom R&D
