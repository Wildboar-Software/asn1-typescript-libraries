-- Module GMI-AttributeModule (X.723:11/1993)
-- See also ITU-T X.723 (11/1993)
-- See also the index of all ASN.1 assignments needed in this document

GMI-AttributeModule {joint-iso-itu-t ms(9) smi(3) part5(5) asn1Module(2)
  gmiAttributeModule(0)} DEFINITIONS IMPLICIT TAGS ::=
BEGIN

IMPORTS
  GroupObjects, ManagementExtension
    FROM Attribute-ASN1Module {joint-iso-itu-t ms(9) smi(3) part2(2)
      asn1Module(2) 1}
  RelativeDistinguishedName
    FROM CMIP-1 {joint-iso-itu-t(2) ms(9) cmip(1) modules(0) protocol(3)}; -- End of IMPORTS

ActionInfo ::= SET OF ManagementExtension

ActionReply ::= SET OF ManagementExtension

ApplicationProcessId ::= GraphicString

ApplicationProcessTitle ::= CHOICE {
  directory  [0]  SEQUENCE OF RelativeDistinguishedName,
  oid        [1]  OBJECT IDENTIFIER,
  notKnown   NULL
}

CommunicationsEntityId ::= GraphicString

CommunicationsInformation ::= SEQUENCE {
  informationType  InformationType,
  informationData  InformationData OPTIONAL
}

ConnectionId ::= GraphicString

GenericCounter ::= INTEGER

Generic64BitCounter ::= INTEGER(0..18446744073709551615)

InformationType ::= OBJECT IDENTIFIER

InformationData ::= SET OF ManagementExtension

ProtocolMachineId ::= GraphicString

Sap1Address ::= INTEGER

Sap2Address ::= SET OF OCTET STRING

SapId ::= GraphicString

SubsystemId ::= GraphicString

Timer ::= SEQUENCE {
  exponent  [1]  INTEGER(-62..63),
  mantissa  [2]  INTEGER(0..65535)
}

END

-- Generated by Asnp, the ASN.1 pretty-printer of France Telecom R&D
