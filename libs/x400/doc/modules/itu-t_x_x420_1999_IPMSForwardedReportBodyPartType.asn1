-- Module IPMSForwardedReportBodyPartType (X.420:06/1999)
-- See also ITU-T X.420 (06/1999)
-- See also the index of all ASN.1 assignments needed in this document

IPMSForwardedReportBodyPartType {joint-iso-itu-t mhs(6) ipms(1) modules(0)
  forwarded-report-body-part-type(12)} DEFINITIONS IMPLICIT TAGS ::=
BEGIN

-- Prologue
-- Exports everything.
IMPORTS
  -- MTS Abstract Service
  ReportDeliveryArgument
    --==
    FROM MTSAbstractService {joint-iso-itu-t mhs(6) mts(3) modules(0)
      mts-abstract-service(1) version-1999(1)}
  -- IPMS Information Objects
  EXTENDED-BODY-PART-TYPE, IPN, MessageParameters
    --==
    FROM IPMSInformationObjects {joint-iso-itu-t mhs(6) ipms(1) modules(0)
      information-objects(2) version-1999(1)}
  -- IPMS Object Identifiers
  id-ep-notification, id-et-report, id-et-notification
    --==
    FROM IPMSObjectIdentifiers {joint-iso-itu-t mhs(6) ipms(1) modules(0)
      object-identifiers(0) version-1999(1)};

-- Report body part
report-body-part EXTENDED-BODY-PART-TYPE ::= {
  DATA  {ReportDeliveryArgument
         IDENTIFIED BY  id-et-report}
}

-- Notification body part
notification-body-part EXTENDED-BODY-PART-TYPE ::= {
  PARAMETERS  {MessageParameters
               IDENTIFIED BY  id-ep-notification},
  DATA        {IPN IDENTIFIED BY  id-et-notification}
}

END -- of IPMSForwardedReportBodyPartType

-- Generated by Asnp, the ASN.1 pretty-printer of France Telecom R&D
