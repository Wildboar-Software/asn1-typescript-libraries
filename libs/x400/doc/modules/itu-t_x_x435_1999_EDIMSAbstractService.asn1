-- Module EDIMSAbstractService (X.435:06/1999)
-- See also ITU-T X.435 (06/1999)
-- See also the index of all ASN.1 assignments needed in this document

EDIMSAbstractService {joint-iso-itu-t mhs(6) edims(7) modules(0)
  abstract-service(3)} DEFINITIONS IMPLICIT TAGS ::=
BEGIN

--	Prologue
--	Exports everything
IMPORTS
  --	EDIMS Information Objects
  EDIM, EDIN, InformationObject
    --==
    FROM EDIMSInformationObjects {joint-iso-itu-t mhs(6) edims(7) modules(0)
      information-objects(2) version(2)}
  --	EDIMS Object Identifiers
  id-pt-origination, id-pt-reception
    --==
    FROM EDIMSObjectIdentifiers {joint-iso-itu-t mhs(6) edims(7) modules(0)
      object-identifiers(0) version(2)}
  --	MTS Abstract Service
  ABSTRACT-ERROR, ABSTRACT-OPERATION, MessageDeliveryEnvelope,
    MessageSubmissionEnvelope, MessageSubmissionIdentifier,
    MessageSubmissionTime, PORT, ProbeSubmissionEnvelope,
    ProbeSubmissionIdentifier, ProbeSubmissionTime,
    recipient-improperly-specified, ReportDeliveryEnvelope
    --==
    FROM MTSAbstractService {joint-iso-itu-t mhs(6) mts(3) modules(0)
      mts-abstract-service(1) version-1999(1)};

--	Primary Port Types
--	Origination
origination PORT ::= {
  CONSUMER INVOKES  {originate-probe | originate-edim | originate-edin}
  ID                id-pt-origination
}

--	Reception
reception PORT ::= {
  SUPPLIER INVOKES  {receive-report | receive-edim | receive-edin}
  ID                id-pt-reception
}

--	ABSTRACT OPERATIONS
--	Origination Abstract Operations
--	Originate Probe
originate-probe ABSTRACT-OPERATION ::= {
  ARGUMENT  SET {envelope  [0]  ProbeSubmissionEnvelope,
                 content   [1]  EDIM}
  RESULT
    SET {submission-identifier  [0]  ProbeSubmissionIdentifier,
         submission-time        [1]  ProbeSubmissionTime}
  ERRORS    {recipient-improperly-specified}
}

--	Originate EDIM
originate-edim ABSTRACT-OPERATION ::= {
  ARGUMENT  SET {envelope  [0]  MessageSubmissionEnvelope,
                 content   [1]  EDIM}
  RESULT
    SET {submission-identifier  [0]  MessageSubmissionIdentifier,
         submission-time        [1]  MessageSubmissionTime}
  ERRORS    {recipient-improperly-specified}
}

--	Originate EDIN
originate-edin ABSTRACT-OPERATION ::= {
  ARGUMENT  SET {envelope  [0]  MessageSubmissionEnvelope,
                 content   [1]  EDIN}
  RESULT
    SET {submission-identifier  [0]  MessageSubmissionIdentifier,
         submission-time        [1]  MessageSubmissionTime}
  ERRORS    {recipient-improperly-specified}
}

--	Reception Abstract Operations
--	Receive Report
receive-report ABSTRACT-OPERATION ::= {
  ARGUMENT
    SET {envelope            [0]  ReportDeliveryEnvelope,
         undelivered-object  [1]  InformationObject OPTIONAL}
}

--	Receive EDIM
receive-edim ABSTRACT-OPERATION ::= {
  ARGUMENT  SET {envelope  [0]  MessageDeliveryEnvelope,
                 content   [1]  EDIM}
}

--	Receive EDIN
receive-edin ABSTRACT-OPERATION ::= {
  ARGUMENT  SET {envelope  [0]  MessageDeliveryEnvelope,
                 content   [1]  EDIN}
}

END -- of EDIMSAbstractService

-- Generated by Asnp, the ASN.1 pretty-printer of France Telecom R&D
