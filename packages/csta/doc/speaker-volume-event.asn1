CSTA-speaker-volume-event
	{ iso( 1) identified-organization( 3) icd-ecma( 12)
		standard( 0) csta3( 285) speaker-volume-event( 47) }
DEFINITIONS ::=
BEGIN

IMPORTS	

-- Data Types --
SubjectDeviceID FROM CSTA-device-identifiers
	{ iso( 1) identified-organization( 3) icd-ecma( 12)
		standard( 0) csta3( 285) device-identifiers( 123) }
CSTACommonArguments FROM CSTA-extension-types
	{ iso( 1) identified-organization( 3) icd-ecma( 12)
		standard( 0) csta3( 285) extension-types( 129) }
AuditoryApparatusID, Volume FROM CSTA-physical-device-feature 
	{ iso( 1) identified-organization( 3) icd-ecma( 12)
		standard( 0) csta3( 285) physical-device-feature( 137) };

SpeakerVolumeEvent ::= SEQUENCE
{	invokingDevice			SubjectDeviceID,
	auditoryApparatus		AuditoryApparatusID,
	speakerVolume			Volume,
	extensions			CSTACommonArguments			OPTIONAL }

END  -- of CSTA-speaker-volume-event
