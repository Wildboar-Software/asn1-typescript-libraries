CSTA-set-forwarding
	{ iso( 1) identified-organization( 3) icd-ecma( 12)
		standard( 0) csta3( 285) set-forwarding( 317) }

DEFINITIONS ::=
BEGIN

IMPORTS
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
DeviceID FROM CSTA-device-identifiers
	{ iso( 1) identified-organization( 3) icd-ecma( 12)
		standard( 0) csta3( 285) device-identifiers( 123) }
ForwardingType FROM CSTA-device-feature-types
	{ iso( 1) identified-organization( 3) icd-ecma( 12)
		standard( 0) csta3( 285) device-feature-types( 127) }
CSTACommonArguments FROM CSTA-extension-types
	{ iso( 1) identified-organization( 3) icd-ecma( 12)
		standard( 0) csta3( 285) extension-types( 129) };

setForwarding OPERATION ::=
{	ARGUMENT 		SetForwardingArgument
	RESULT 			SetForwardingResult
	ERRORS 			{universalFailure }
	CODE			local: 317 }

SetForwardingArgument ::= SEQUENCE
{	device 				DeviceID,
	forwardingType	 		ForwardingType				OPTIONAL,
	activateForward			BOOLEAN,
	forwardDN 			DeviceID				OPTIONAL,
	ringCount 			INTEGER (1..100)			OPTIONAL,
	ringDuration			[3] IMPLICIT INTEGER			OPTIONAL,
	extensions			CSTACommonArguments			OPTIONAL }

SetForwardingResult ::= CHOICE
{	extensions 			CSTACommonArguments,
	noData 				NULL }

END -- of CSTA-set-forwarding
