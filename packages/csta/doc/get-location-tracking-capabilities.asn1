CSTA-get-location-tracking-capabilities
	{ iso( 1) identified-organization( 3) icd-ecma( 12)
		standard( 0) csta3( 285) get-location-tracking-capabilities( 539) }

DEFINITIONS ::=
BEGIN

IMPORTS
OPERATION, ERROR FROM Remote-Operations-Information-Objects 
	{joint-iso-itu-t remote-operations(4) informationObjects(5) version1(0) }

-- Data Types –-
universalFailure FROM CSTA-error-definitioneq
	{ iso( 1) identified-organization( 3) icd-ecma( 12)
		standard( 0) csta3( 285) error-definition( 120) }
CSTACommonArguments FROM CSTA-extension-types
	{ iso( 1) identified-organization( 3) icd-ecma( 12)
		standard( 0) csta3( 285) extension-types( 129) }
DeviceID FROM CSTA-device-identifiers
	{ iso( 1) identified-organization( 3) icd-ecma( 12)
		standard( 0) csta3( 285) device-identifiers( 123) }
LocCrossRefID FROM CSTA-device-feature-types
	{ iso( 1) identified-organization( 3) icd-ecma( 12)
		standard( 0) csta3( 285) device-feature-types( 127) };

getLocationTrackingCapabilities OPERATION ::=
{	ARGUMENT		GetLocationTrackingCapabilitiesArgument 
	RESULT     		GetLocationTrackingCapabilitiesResult
	ERRORS     		{universalFailure }
	CODE			local: 539 }

GetLocationTrackingCapabilitiesArgument ::= SEQUENCE
{	device					DeviceID,	
	extensions				CSTACommonArguments		OPTIONAL }

GetLocationTrackingCapabilitiesResult ::= SEQUENCE 
{	collectionTypeDefault			ENUMERATED
	{	periodic				(0),
		updatesOnly				(1),
		periodicWithUpdates			(2) },
	collectionTypePeriodic			BOOLEAN,
	collectionTypeUpdatesOnly		BOOLEAN,
	collectionTypePeriodicWithUpdates	BOOLEAN,
	collectionIntervalDefault		INTEGER,
	collectionIntervalMin			INTEGER,
	collectionIntervalMax			INTEGER,
	maxCollectionsDefault			INTEGER,
	maxCollectionsMin			INTEGER,
	maxCollectionsMax			INTEGER,
	collectionFilterDefault			ENUMERATED
	{	horizontalMovement			(0),
		verticalMovement			(1),
		civicAddressChange			(2),
		none					(3) },
	collectionFilterHorizontal		BOOLEAN,
	collectionFilterVertical		BOOLEAN,
	collectionFilterCivicAddress		BOOLEAN,
	reportingTypeDefault			ENUMERATED
	{	immediate				(0),
		periodic				(1),
		count					(2) },
	reportingTypeImmediate			BOOLEAN,
	reportingTypePeriodic			BOOLEAN,
	reportingTypeCount			INTEGER,
	reportingIntervalDefault		INTEGER,
	reportingIntervalMin			INTEGER,
	reportingIntervalMax			INTEGER,
	reportingCountDefault			INTEGER,
	reportingCountMin			INTEGER,
	reportingCountMax			INTEGER,
	supportsSuspendingTracking		BOOLEAN,
	supportsResumingTracking		BOOLEAN,
	extensions				CSTACommonArguments		OPTIONAL }

END -- of CSTA-get-location-tracking-capabilities
