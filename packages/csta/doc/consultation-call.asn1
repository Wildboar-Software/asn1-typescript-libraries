CSTA-consultation-call
	{ iso( 1) identified-organization( 3) icd-ecma( 12)
		standard( 0) csta3( 285) consultation-call( 7) }
DEFINITIONS ::=
BEGIN

IMPORTS
OPERATION, ERROR FROM Remote-Operations-Information-Objects
	{joint-iso-itu-t remote-operations(4) informationObjects(5) version1(0) }

-- Data Types –-
universalFailure FROM CSTA-error-definition
	{ iso( 1) identified-organization( 3) icd-ecma( 12)
		standard( 0) csta3( 285) error-definition( 120) }
DeviceID FROM CSTA-device-identifiers
	{ iso( 1) identified-organization( 3) icd-ecma( 12)
		standard( 0) csta3( 285) device-identifiers( 123) }
ConnectionID FROM CSTA-call-connection-identifiers
	{ iso( 1) identified-organization( 3) icd-ecma( 12)
		standard( 0) csta3( 285) call-connection-identifiers( 124) }
AccountInfo, AuthCode, CorrelatorData, UserData FROM CSTA-device-feature-types
	{ iso( 1) identified-organization( 3) icd-ecma( 12)
		standard( 0) csta3( 285) device-feature-types( 127) }
CSTACommonArguments FROM CSTA-extension-types
	{ iso( 1) identified-organization( 3) icd-ecma( 12)
		standard( 0) csta3( 285) extension-types( 129) }
CallCharacteristics, ConsultOptions, CallLinkageData FROM CSTA-call-control
	{ iso( 1) identified-organization( 3) icd-ecma( 12)
		standard( 0) csta3( 285) call-control( 130) }
SubjectOfCall,LanguagePreferences FROM CSTA-device-feature-types
	{ iso( 1) identified-organization( 3) icd-ecma( 12)
		standard( 0) csta3( 285) device-feature-types( 127) }
ConnectionInformation, MediaCallCharacteristics FROM CSTA-media-services
	{ iso( 1) identified-organization( 3) icd-ecma( 12)
		standard( 0) csta3( 285) media-services( 136) };

consultationCall OPERATION ::=
{ 	ARGUMENT 		ConsultationCallArgument
	RESULT 			ConsultationCallResult
	ERRORS 			{universalFailure }
	CODE 			local: 7 }

ConsultationCallArgument ::= SEQUENCE
{ 	existingCall 			[ 0] IMPLICIT ConnectionID,
	consultedDevice 		[ 1] DeviceID,
	connectionReservation 		[ 2] IMPLICIT BOOLEAN 				OPTIONAL,
	accountCode 			[ 3] IMPLICIT AccountInfo 			OPTIONAL,
	authCode 			[ 4] IMPLICIT AuthCode 				OPTIONAL,
	correlatorData 			[ 5] IMPLICIT CorrelatorData 			OPTIONAL,
	userData 			[ 6] IMPLICIT UserData 				OPTIONAL,
	callCharacteristics 		[ 7] IMPLICIT CallCharacteristics 		OPTIONAL,
	mediaCallCharacteristics 	[ 8] IMPLICIT MediaCallCharacteristics 		OPTIONAL,
	callingConnectionInfo 		[ 9] IMPLICIT ConnectionInformation 		OPTIONAL,
	consultOptions 			[10] IMPLICIT ConsultOptions 			DEFAULT unrestricted,
	subjectOfCall			[11] IMPLICIT SubjectOfCall			OPTIONAL,
	languagePreferences		[12] IMPLICIT LanguagePreferences		OPTIONAL,
	extensions 			CSTACommonArguments 				OPTIONAL }

ConsultationCallResult ::= SEQUENCE
{ 	initiatedCall 			ConnectionID,
	mediaCallCharacteristics 	[0] IMPLICIT MediaCallCharacteristics 		OPTIONAL,
	initiatedCallInfo 		[1] IMPLICIT ConnectionInformation 		OPTIONAL,
	callLinkageData 		[2] IMPLICIT CallLinkageData 			OPTIONAL,
	extensions 			CSTACommonArguments 				OPTIONAL }

END -- of CSTA-consultation-call
