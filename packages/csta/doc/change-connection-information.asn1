CSTA-change-connection-information
	{ iso( 1) identified-organization( 3) icd-ecma( 12)
		standard( 0) csta3( 285) change-connection-information(377) }

DEFINITIONS ::=
BEGIN

IMPORTS
OPERATION, ERROR FROM Remote-Operations-Information-Objects
	{joint-iso-itu-t remote-operations(4) informationObjects(5) version1(0) }

-- Data Types –-
universalFailure FROM CSTA-error-definition
	{ iso( 1) identified-organization( 3) icd-ecma( 12)
		standard( 0) csta3( 285) error-definition( 120) } 
ConnectionID FROM CSTA-call-connection-identifiers
	{ iso( 1) identified-organization( 3) icd-ecma( 12)
		standard( 0) csta3( 285) call-connection-identifiers( 124) }
ConnectionInformation, MediaCallCharacteristics FROM CSTA-media-services
	{ iso( 1) identified-organization( 3) icd-ecma( 12)
		standard( 0) csta3( 285) media-services( 136) }
CSTACommonArguments FROM CSTA-error-definition
	{ iso( 1) identified-organization( 3) icd-ecma( 12)
		standard( 0) csta3( 285) extension-types( 129) };

changeConnectionInformation OPERATION ::=
{ 	ARGUMENT 		ChangeConnectionInformationArgument
	RESULT 			ChangeConnectionInformationResult
	ERRORS 			{universalFailure }
	CODE 			local: 377 }

ChangeConnectionInformationArgument::= SEQUENCE
{	connectionToBeChanged		ConnectionID,
	requestedConnectionInfo		ConnectionInformation,
	extensions 			CSTACommonArguments 		OPTIONAL }

ChangeConnectionInformationResult::= SEQUENCE
{ 	actualConnectionInfo 		ConnectionInformation,
	extensions 			CSTACommonArguments 		OPTIONAL }

END -- of CSTA-change-connection-information
