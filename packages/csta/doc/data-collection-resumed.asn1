CSTA-data-collection-resumed
{ iso( 1) identified-organization( 3) icd-ecma( 12)
	standard( 0) csta3( 285) data-collection-resumed( 344) }

DEFINITIONS ::=
BEGIN

IMPORTS
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
CSTACommonArguments FROM CSTA-extension-types
	{ iso( 1) identified-organization( 3) icd-ecma( 12)
		standard( 0) csta3( 285) extension-types( 129) }
DcollCrossRefID FROM CSTA-data-collection
	{ iso( 1) identified-organization( 3) icd-ecma( 12)
	standard( 0) csta3( 285) data-collection( 138) };

dataCollectionResumed OPERATION ::=
{	ARGUMENT 		DataCollectionResumedArgument
	RESULT 			DataCollectionResumedResult
	ERRORS 			{universalFailure }
	CODE			local: 344 }

DataCollectionResumedArgument ::= SEQUENCE
{	dcollCrossRefID			DcollCrossRefID,
	extensions 			CSTACommonArguments			OPTIONAL }

DataCollectionResumedResult ::= CHOICE
{	extensions 			CSTACommonArguments,
	noData 				NULL }

END -- of CSTA-data-collection-resumed
