CSTA-dial-digits
	{ iso( 1) identified-organization( 3) icd-ecma( 12)
		standard( 0) csta3( 285) dial-digits( 219) }

DEFINITIONS ::=
BEGIN

IMPORTS
OPERATION, ERROR FROM Remote-Operations-Information-Objects
	{joint-iso-itu-t remote-operations(4) informationObjects(5) version1(0) }

-- Data Types –-
universalFailure FROM CSTA-error-definition
	{ iso( 1) identified-organization( 3) icd-ecma( 12)
		standard( 0) csta3( 285) error-definition( 120) }
DeviceID FROM CSTA-device-identifiers
	{ iso( 1) identified-organization( 3) icd-ecma( 12)
		standard( 0) csta3( 285) device-identifiers( 123) }
ConnectionID FROM CSTA-call-connection-identifiers
	{ iso( 1) identified-organization( 3) icd-ecma( 12)
		standard( 0) csta3( 285) call-connection-identifiers( 124) }
CorrelatorData FROM CSTA-device-feature-types
	{ iso( 1) identified-organization( 3) icd-ecma( 12)
		standard( 0) csta3( 285) device-feature-types( 127) }
CSTACommonArguments FROM CSTA-extension-types
	{ iso( 1) identified-organization( 3) icd-ecma( 12)
		standard( 0) csta3( 285) extension-types( 129) };

dialDigits OPERATION ::=
{ 	ARGUMENT 		DialDigitsArgument
	RESULT 			DialDigitsResult
	ERRORS 			{universalFailure }
	CODE 			local: 219 }

DialDigitsArgument ::= SEQUENCE
{ 	diallingConnection 		ConnectionID,
	diallingSequence 		DeviceID,
	correlatorData 			CorrelatorData 			OPTIONAL,
	extensions 			CSTACommonArguments 		OPTIONAL }

DialDigitsResult ::= CHOICE
{	extensions 			CSTACommonArguments,
	noData 				NULL }

END -- of CSTA-dial-digits
