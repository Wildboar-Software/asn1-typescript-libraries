CSTA-get-lamp-information
{ iso( 1) identified-organization( 3) icd-ecma( 12)
	standard( 0) csta3( 285) get-lamp-information( 265) }

DEFINITIONS ::=
BEGIN

IMPORTS
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
DeviceID FROM CSTA-device-identifiers
	{ iso( 1) identified-organization( 3) icd-ecma( 12)
		standard( 0) csta3( 285) device-identifiers( 123) }
CSTACommonArguments FROM CSTA-extension-types
	{ iso( 1) identified-organization( 3) icd-ecma( 12)
		standard( 0) csta3( 285) extension-types( 129) }
ButtonID, LampID, LampColor FROM CSTA-physical-device-feature 
	{ iso( 1) identified-organization( 3) icd-ecma( 12)
		standard( 0) csta3( 285) physical-device-feature( 137) };

getLampInformation OPERATION ::=
{	ARGUMENT 		GetLampInformationArgument
	RESULT			GetLampInformationResult
	ERRORS			{universalFailure }
	CODE			local: 265 }

GetLampInformationArgument ::= SEQUENCE
{	device 				DeviceID,
	lamp 				LampID					OPTIONAL,
	extensions 			CSTACommonArguments	 		OPTIONAL }

GetLampInformationResult ::= SEQUENCE
{	lampList 			LampList,
	extensions 			CSTACommonArguments			OPTIONAL }

LampList ::= SEQUENCE OF SEQUENCE
{	lamp				LampID,
	lampLabel			[0] IMPLICIT OCTET STRING		OPTIONAL,
	button				[1] IMPLICIT ButtonID			OPTIONAL,
	lampColor			LampColor				OPTIONAL }

END -- of CSTA-get-lamp-information
