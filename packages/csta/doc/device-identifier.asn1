CSTA-device-identifiers
	{ iso( 1) identified-organization( 3) icd-ecma( 12)
		standard( 0) csta3( 285) device-identifiers( 123) }

DEFINITIONS ::=
BEGIN

EXPORTS
DeviceID, NumberDigits, CallingDeviceID, CalledDeviceID,
SubjectDeviceID, RedirectionDeviceID, AssociatedCallingDeviceID,
AssociatedCalledDeviceID, NetworkCallingDeviceID, NetworkCalledDeviceID;

IMPORTS
MediaCallCharacteristics FROM CSTA-media-services
	{ iso( 1) identified-organization( 3) icd-ecma( 12)
		standard( 0) csta3( 285) media-services( 136) };

ExtendedDeviceID::= [APPLICATION 9] CHOICE
{	deviceIdentifier			DeviceID,
	notKnown				[ 7] IMPLICIT 	NULL,
	restricted				[ 8] IMPLICIT 	NULL }

CallingDeviceID::= [APPLICATION 1] CHOICE
{	deviceIdentifier			DeviceID,
	notKnown				[ 7] IMPLICIT 	NULL,
	restricted				[ 8] IMPLICIT 	NULL }

CallingDevice ::= CallingDeviceID

CalledDeviceID ::= [APPLICATION 2] CHOICE
{	deviceIdentifier			DeviceID,
	notKnown				[ 7] IMPLICIT 	NULL,
	restricted				[ 8] IMPLICIT 	NULL }

CalledDevice ::= CalledDeviceID

SubjectDeviceID ::= [APPLICATION 3] CHOICE
{	deviceIdentifier 			DeviceID,
	notKnown				[ 7] IMPLICIT 	NULL,
	restricted				[ 8] IMPLICIT 	NULL }

RedirectionDeviceID ::= [APPLICATION 4] CHOICE
{	numberdialed				DeviceID,
	notKnown				[ 7] IMPLICIT 	NULL,
	notRequired				[ 8] IMPLICIT 	NULL,
	notSpecified				[ 9] IMPLICIT 	NULL,
	restricted				[10] IMPLICIT 	NULL }

LastRedirectionDevice ::= RedirectionDeviceID

AssociatedCallingDeviceID::= [APPLICATION 5] CHOICE
{	deviceIdentifier 			DeviceID,
	notKnown				[ 7] IMPLICIT 	NULL,
	restricted				[ 8] IMPLICIT 	NULL }

AssociatedCallingDevice ::= AssociatedCallingDeviceID

AssociatedCalledDeviceID ::= [APPLICATION 6] CHOICE
{	deviceIdentifier			DeviceID,
	notKnown				[ 7] IMPLICIT 	NULL,
	restricted				[ 8] IMPLICIT 	NULL }

AssociatedCalledDevice ::= AssociatedCalledDeviceID

NetworkCallingDeviceID::= [APPLICATION 7] CHOICE
{	deviceIdentifier			DeviceID,
	notKnown				[ 7] IMPLICIT 	NULL,
	restricted				[ 8] IMPLICIT 	NULL }

NetworkCallingDevice ::= NetworkCallingDeviceID

NetworkCalledDeviceID ::= [APPLICATION 8] CHOICE
{	deviceIdentifier			DeviceID,
	notKnown				[ 7] IMPLICIT 	NULL,
	restricted				[ 8] IMPLICIT 	NULL }

NetworkCalledDevice ::= NetworkCalledDeviceID

DeviceID ::= SEQUENCE
{	deviceIdentifier CHOICE
	{	dialingNumber 			[ 0] IMPLICIT 	NumberDigits,
		deviceNumber 			[ 1] IMPLICIT 	DeviceNumber,
		implicitPublic 			[ 2] IMPLICIT 	NumberDigits,
		explicitPublic 			[ 3] PublicTON,
		implicitPrivate 		[ 4] IMPLICIT 	NumberDigits,
		explicitPrivate 		[ 5] PrivateTON,
		other 				[ 6] IMPLICIT 	OtherPlan },
	privateNumber			[ 0] NumberDigits			OPTIONAL,
	privateName			[ 1] IA5String				OPTIONAL,
	mediaCallCharacteristics 	MediaCallCharacteristics 		OPTIONAL }

PublicTON ::= CHOICE
{	unknown 				[ 0] IMPLICIT 	IA5String,
	international 				[ 1] IMPLICIT 	IA5String,
	national 				[ 2] IMPLICIT 	IA5String,
	networkspecific 			[ 3] IMPLICIT 	IA5String,
	subscriber 				[ 4] IMPLICIT 	IA5String,
	abbreviated 				[ 5] IMPLICIT 	IA5String }

PrivateTON ::= CHOICE
{	unknown 				[ 0] IMPLICIT 	IA5String,
	level3RegionalNumber 			[ 1] IMPLICIT 	IA5String,
	level2RegionalNumber 			[ 2] IMPLICIT 	IA5String,
	level1RegionalNumber 			[ 3] IMPLICIT 	IA5String,
	pTNSpecificNumber 			[ 4] IMPLICIT 	IA5String,
	localNumber 				[ 5] IMPLICIT 	IA5String,
	abbreviated 				[ 6] IMPLICIT 	IA5String }

OtherPlan ::= OCTET STRING 	-- Allows future expansion to cover other numbering
                                -- plans

NumberDigits::= IA5String

DeviceNumber::= INTEGER

END -- of CSTA-device-identifier
