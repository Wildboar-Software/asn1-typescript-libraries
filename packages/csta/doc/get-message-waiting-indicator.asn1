CSTA-get-message-waiting-indicator
{ iso( 1) identified-organization( 3) icd-ecma( 12)
	standard( 0) csta3( 285) get-message-waiting-indicator( 267) }

DEFINITIONS ::=
BEGIN

IMPORTS
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
DeviceID FROM CSTA-device-identifiers
	{ iso( 1) identified-organization( 3) icd-ecma( 12)
		standard( 0) csta3( 285) device-identifiers( 123) }
CSTACommonArguments FROM CSTA-extension-types
	{ iso( 1) identified-organization( 3) icd-ecma( 12)
		standard( 0) csta3( 285) extension-types( 129) };

getMessageWaitingIndicator OPERATION ::=
{	ARGUMENT 		GetMessageWaitingIndicatorArgument
	RESULT			GetMessageWaitingIndicatorResult
	ERRORS			{universalFailure }
	CODE			local: 267 }

GetMessageWaitingIndicatorArgument ::= SEQUENCE
{	device				DeviceID,
	extensions			CSTACommonArguments			OPTIONAL }

GetMessageWaitingIndicatorResult ::= SEQUENCE
{	messageWaitingOn		BOOLEAN,
	deviceForMessage		DeviceID				OPTIONAL,
	lampIsPresent			BOOLEAN					OPTIONAL,
	extensions			CSTACommonArguments			OPTIONAL }

END -- of CSTA-get-message-waiting-indicator
