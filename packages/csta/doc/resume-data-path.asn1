CSTA-resume-data-path
	{ iso( 1) identified-organization( 3) icd-ecma( 12)
		standard( 0) csta3( 285) resume-data-path( 117) }

DEFINITIONS ::=
BEGIN

IMPORTS	
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
IOCrossRefID, IORegisterReqID FROM CSTA-device-feature-types
	{ iso( 1) identified-organization( 3) icd-ecma( 12)
		standard( 0) csta3( 285) device-feature-types( 127) }
CSTACommonArguments FROM CSTA-extension-types
	{ iso( 1) identified-organization( 3) icd-ecma( 12)
		standard( 0) csta3( 285) extension-types( 129) };

resumeDataPath OPERATION ::=
{	ARGUMENT		ResumeDataPathArgument
	RESULT			ResumeDataPathResult
	ERRORS			{universalFailure }
	CODE			local: 117 }

ResumeDataPathArgument ::= SEQUENCE
{	ioCrossRefID			IOCrossRefID,
	ioRegisterReqID			IORegisterReqID				OPTIONAL,
	extensions			CSTACommonArguments			OPTIONAL }

ResumeDataPathResult ::= CHOICE
{	extensions			CSTACommonArguments,
	noData				NULL }

END  -- of CSTA-resume-data-path
