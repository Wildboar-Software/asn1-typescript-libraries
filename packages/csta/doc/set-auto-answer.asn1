CSTA-set-auto-answer
	{ iso( 1) identified-organization( 3) icd-ecma( 12)
		standard( 0) csta3( 285) set-auto-answer( 313) }

DEFINITIONS ::=
BEGIN

IMPORTS
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
DeviceID FROM CSTA-device-identifiers
	{ iso( 1) identified-organization( 3) icd-ecma( 12)
		standard( 0) csta3( 285) device-identifiers( 123) }
CSTACommonArguments FROM CSTA-extension-types
	{ iso( 1) identified-organization( 3) icd-ecma( 12)
		standard( 0) csta3( 285) extension-types( 129) };

setAutoAnswer OPERATION ::=
{	ARGUMENT 		SetAutoAnswerArgument
	RESULT 			SetAutoAnswerResult
	ERRORS 			{universalFailure }
	CODE			local: 313 }

SetAutoAnswerArgument ::= SEQUENCE
{	device 				DeviceID,
	autoAnswerOn			BOOLEAN,
	numberOfRings			INTEGER					OPTIONAL,
	extensions			CSTACommonArguments	 		OPTIONAL }

SetAutoAnswerResult ::= CHOICE
{	extensions 			CSTACommonArguments,
	noData 				NULL }

END -- of CSTA-set-auto-answer
