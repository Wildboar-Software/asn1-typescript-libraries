CSTA-camp-on-call
	{ iso( 1) identified-organization( 3) icd-ecma( 12)
		standard( 0) csta3( 285) camp-on-call( 217) }

DEFINITIONS ::=
BEGIN

IMPORTS
OPERATION, ERROR FROM Remote-Operations-Information-Objects
	{joint-iso-itu-t remote-operations(4) informationObjects(5) version1(0) }

-- Data Types –-
universalFailure FROM CSTA-error-definition
	{ iso( 1) identified-organization( 3) icd-ecma( 12)
		standard( 0) csta3( 285) error-definition( 120) }
ConnectionID FROM CSTA-call-connection-identifiers
	{ iso( 1) identified-organization( 3) icd-ecma( 12)
		standard( 0) csta3( 285) call-connection-identifiers( 124) }
CSTACommonArguments FROM CSTA-extension-types
	{ iso( 1) identified-organization( 3) icd-ecma( 12)
		standard( 0) csta3( 285) extension-types( 129) };

camponCall OPERATION ::=
{ 	ARGUMENT 		CamponCallArgument
	RESULT 			CamponCallResult
	ERRORS 			{universalFailure }
	CODE 			local: 217 }

CamponCallArgument ::= SEQUENCE
{ 	camponConnection 		ConnectionID,
	extensions 			CSTACommonArguments 		OPTIONAL }

CamponCallResult ::= CHOICE
{ 	extensions 			CSTACommonArguments,
	noData 				NULL }

END -- of CSTA-camp-on-call
