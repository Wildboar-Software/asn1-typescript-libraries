CSTA-route-reject
	{ iso( 1) identified-organization( 3) icd-ecma( 12)
		standard( 0) csta3( 285) route-reject( 86) }

DEFINITIONS ::=
BEGIN

IMPORTS
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
CorrelatorData, RouteRegisterReqID, RouteingCrossRefID
FROM CSTA-device-feature-types
	{ iso( 1) identified-organization( 3) icd-ecma( 12)
		standard( 0) csta3( 285) device-feature-types( 127) }
CSTACommonArguments FROM CSTA-extension-types 
	{ iso( 1) identified-organization( 3) icd-ecma( 12)
		standard( 0) csta3( 285) extension-types( 129) };

routeReject OPERATION ::=
{ 	ARGUMENT 		RouteRejectArgument
	ERRORS	 		{universalFailure }
	ALWAYS RESPONDS		FALSE
	CODE			local: 36 }

RouteRejectArgument ::= SEQUENCE
{	crossRefIdentifier		RouteingCrossRefID,
	routeRegisterReqID		[0] IMPLICIT RouteRegisterReqID 	OPTIONAL,
	rejectCause			[1] IMPLICIT RejectCause		OPTIONAL,
	correlatorData			[2] IMPLICIT CorrelatorData		OPTIONAL,
	extensions			CSTACommonArguments			OPTIONAL }

RejectCause ::= ENUMERATED
{	busyOverflow			(1),
	queueTimeOverflow		(2),
	capacityOverflow		(3),
	calendarOverflow		(4),
	unknownOverflow			(5) }

END  -- of CSTA-route-reject
