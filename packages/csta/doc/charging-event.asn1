CSTA-charging-event
	{ iso( 1) identified-organization( 3) icd-ecma( 12)
		standard( 0) csta3( 285) charging-event( 240) }

DEFINITIONS ::=
BEGIN

IMPORTS

-- Data Types --
EventCause FROM CSTA-event-causes
	{ iso( 1) identified-organization( 3) icd-ecma( 12)
		standard( 0) csta3( 285) event-causes( 121) }
DeviceID FROM CSTA-device-identifiers
	{ iso( 1) identified-organization( 3) icd-ecma( 12)
		standard( 0) csta3( 285) device-identifiers( 123) }
ConnectionID FROM CSTA-call-connection-identifiers
	{ iso( 1) identified-organization( 3) icd-ecma( 12)
		standard( 0) csta3( 285) call-connection-identifiers( 124) }
CSTACommonArguments FROM CSTA-extension-types
	{ iso( 1) identified-organization( 3) icd-ecma( 12)
		standard( 0) csta3( 285) extension-types( 129) }
ChargingInfo FROM CSTA-charge-info
	{ iso( 1) identified-organization( 3) icd-ecma( 12)
		standard( 0) csta3( 285) charge-info( 133) };

ChargingEvent ::= SEQUENCE
{	connection			ConnectionID,
	chargedDevice			DeviceID,
	chargingInfo			ChargingInfo,
	cause				EventCause				OPTIONAL,
	extensions 			CSTACommonArguments 			OPTIONAL }

END -- of CSTA-charging-event
