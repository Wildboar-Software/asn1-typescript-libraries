CSTA-telephony-tones-generated-event
	{ iso( 1) identified-organization( 3) icd-ecma( 12)
		standard( 0) csta3( 285) telephony-tones-generated-event( 242) }

DEFINITIONS ::=

BEGIN

IMPORTS

-- Data Types --
ConnectionID FROM CSTA-call-connection-identifiers
	{ iso( 1) identified-organization( 3) icd-ecma( 12)
		standard( 0) csta3( 285) call-connection-identifiers( 124) }
TelephonyTone FROM CSTA-device-feature-types
	{ iso( 1) identified-organization( 3) icd-ecma( 12)
		standard( 0) csta3( 285) device-feature-types( 127) }
CSTACommonArguments FROM CSTA-extension-types
	{ iso( 1) identified-organization( 3) icd-ecma( 12)
		standard( 0) csta3( 285) extension-types( 129) }
ConnectionInformation FROM CSTA-media-services
	{ iso( 1) identified-organization( 3) icd-ecma( 12)
		standard( 0) csta3( 285) media-services( 136) };

TelephonyTonesGeneratedEvent ::= SEQUENCE
{	connection			ConnectionID,
	toneGenerated			TelephonyTone			OPTIONAL,
	toneFrequency			[0] IMPLICIT INTEGER		OPTIONAL,
	toneDuration			[1] IMPLICIT INTEGER		OPTIONAL,
	pauseDuration			[2] IMPLICIT INTEGER		OPTIONAL,
	connectionInfo			ConnectionInformation		OPTIONAL,
	extensions 			CSTACommonArguments 		OPTIONAL }

END -- of CSTA-telephony-tones-generated-event
