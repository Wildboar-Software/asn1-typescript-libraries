CSTA-resume-location-tracking-session
	{ iso( 1) identified-organization( 3) icd-ecma( 12)
		standard( 0) csta3( 285) resume-location-tracking-session ( 534) }

DEFINITIONS ::=
BEGIN

IMPORTS
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
CSTACommonArguments FROM CSTA-extension-types
	{ iso( 1) identified-organization( 3) icd-ecma( 12)
		standard( 0) csta3( 285) extension-types( 129) }
LocCrossRefID FROM CSTA-device-feature-types
	{ iso( 1) identified-organization( 3) icd-ecma( 12)
		standard( 0) csta3( 285) device-feature-types( 127) };

resumeLocationTrackingSession OPERATION ::=
{ 	ARGUMENT		ResumeLocationTrackingSessionArgument
	RESULT			ResumeLocationTrackingSessionResult
	ERRORS			{universalFailure }
	CODE			local: 534}

ResumeLocationTrackingSessionArgument ::= SEQUENCE
{	locCrossRefID			LocCrossRefID,
	extensions			CSTACommonArguments			OPTIONAL }

ResumeLocationTrackingSessionResult ::= SEQUENCE 
{	extensions			CSTACommonArguments			OPTIONAL }

END -- of CSTA-resume-location-tracking-session
