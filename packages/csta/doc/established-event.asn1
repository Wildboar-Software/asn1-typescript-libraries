CSTA-established-event
	{ iso( 1) identified-organization( 3) icd-ecma( 12)
		standard( 0) csta3( 285) established-event( 27) }

DEFINITIONS ::=
BEGIN

IMPORTS

-- Data Types –-
EventCause FROM CSTA-event-causes
	{ iso( 1) identified-organization( 3) icd-ecma( 12)
		standard( 0) csta3( 285) event-causes( 121) }
SubjectDeviceID, CalledDeviceID, CallingDeviceID, RedirectionDeviceID,
AssociatedCalledDeviceID, AssociatedCallingDeviceID,
NetworkCalledDeviceID, NetworkCallingDeviceID
FROM CSTA-device-identifiers
	{ iso( 1) identified-organization( 3) icd-ecma( 12)
		standard( 0) csta3( 285) device-identifiers( 123) }
ConnectionID FROM CSTA-call-connection-identifiers
	{ iso( 1) identified-organization( 3) icd-ecma( 12)
		standard( 0) csta3( 285) call-connection-identifiers( 124) }
LocalConnectionState FROM CSTA-connection-states
	{ iso( 1) identified-organization( 3) icd-ecma( 12)
		standard( 0) csta3( 285) connection-states( 125) }
CorrelatorData, UserData FROM CSTA-device-feature-types
	{ iso( 1) identified-organization( 3) icd-ecma( 12)
		standard( 0) csta3( 285) device-feature-types( 127) }
CSTACommonArguments FROM CSTA-extension-types
	{ iso( 1) identified-organization( 3) icd-ecma( 12)
		standard( 0) csta3( 285) extension-types( 129) }
CallCharacteristics, CallLinkageData, ServicesPermitted FROM CSTA-call-control
	{ iso( 1) identified-organization( 3) icd-ecma( 12)
		standard( 0) csta3( 285) call-control( 130) }
LocationInfoList FROM CSTA-call-control
	{ iso( 1) identified-organization( 3) icd-ecma( 12)
		standard( 0) csta3( 285) call-control( 130) }
LanguagePreferences, SubjectOfCall, MessageInfo,
DeviceHistory FROM CSTA-device-feature-types
	{ iso( 1) identified-organization( 3) icd-ecma( 12)
		standard( 0) csta3( 285) device-feature-types( 127) }
ConnectionInformation, MediaCallCharacteristics FROM CSTA-media-services
	{ iso( 1) identified-organization( 3) icd-ecma( 12)
		standard( 0) csta3( 285) media-services( 136) };

EstablishedEvent ::= SEQUENCE
{ 	establishedConnection 		ConnectionID,
	answeringDevice 		SubjectDeviceID,
	callingDevice 			CallingDeviceID,
	calledDevice 			CalledDeviceID,
	lastRedirectionDevice 		RedirectionDeviceID,
	originatingNIDConnection 	ConnectionID 				OPTIONAL,
	localConnectionInfo 		LocalConnectionState 			OPTIONAL,
	correlatorData 			[ 1] IMPLICIT 	CorrelatorData 		OPTIONAL,
	userData 			UserData 				OPTIONAL,
	cause 				EventCause,
	servicesPermitted 		[ 2] IMPLICIT 	ServicesPermitted 	OPTIONAL,
	networkCallingDevice 		NetworkCallingDeviceID 			OPTIONAL,
	networkCalledDevice 		NetworkCalledDeviceID 			OPTIONAL,
	associatedCallingDevice 	AssociatedCallingDeviceID 		OPTIONAL,
	associatedCalledDevice 		AssociatedCalledDeviceID 		OPTIONAL,
	mediaCallCharacteristics 	[ 3] IMPLICIT MediaCallCharacteristics 	OPTIONAL,
	callCharacteristics 		[ 4] IMPLICIT CallCharacteristics 	OPTIONAL,
	establishedConnectionInfo 	[ 5] IMPLICIT ConnectionInformation 	OPTIONAL,
	callLinkageData 		[ 6] IMPLICIT CallLinkageData 		OPTIONAL,
	subjectOfCall			[ 7] IMPLICIT SubjectOfCall		OPTIONAL,
	messageInfo			[ 8] IMPLICIT MessageInfo		OPTIONAL,
	languagePreferences		[ 9] IMPLICIT LanguagePreferences	OPTIONAL,
	deviceHistory			[10] IMPLICIT DeviceHistory		OPTIONAL,
	locationInfo			[11] IMPLICIT LocationInfoList		OPTIONAL,
	extensions 			CSTACommonArguments 			OPTIONAL }

END -- of CSTA-established-event
