CSTA-get-hookswitch-status
	{ iso( 1) identified-organization( 3) icd-ecma( 12)
		standard( 0) csta3( 285) get-hookswitch-status( 264) }

DEFINITIONS ::=
BEGIN

IMPORTS
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
DeviceID FROM CSTA-device-identifiers
	{ iso( 1) identified-organization( 3) icd-ecma( 12)
		standard( 0) csta3( 285) device-identifiers( 123) }
CSTACommonArguments FROM CSTA-extension-types
	{ iso( 1) identified-organization( 3) icd-ecma( 12)
		standard( 0) csta3( 285) extension-types( 129) }
HookswitchID FROM CSTA-physical-device-feature 
	{ iso( 1) identified-organization( 3) icd-ecma( 12)
		standard( 0) csta3( 285) physical-device-feature( 137) };

getHookswitchStatus OPERATION ::=
{	ARGUMENT 		GetHookswitchStatusArgument
	RESULT			GetHookswitchStatusResult
	ERRORS			{universalFailure }
	CODE			local: 264 }

GetHookswitchStatusArgument ::= SEQUENCE
{	device 				DeviceID,
	hookswitch			HookswitchID				OPTIONAL,
	extensions 			CSTACommonArguments	 		OPTIONAL }

GetHookswitchStatusResult ::= SEQUENCE
{	hookswitchStatusList 		HookswitchStatusList,
	extensions 			CSTACommonArguments			OPTIONAL }

HookswitchStatusList ::= SEQUENCE OF SEQUENCE
{	hookswitch			HookswitchID,
	hookswitchOnHook		BOOLEAN }

END -- of CSTA-get-hookswitch-status
