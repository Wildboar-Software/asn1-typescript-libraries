CSTA-monitor-info
	{ iso( 1) identified-organization( 3) icd-ecma( 12)
		standard( 0) csta3( 285) monitor-info ( 374) }

DEFINITIONS ::=
BEGIN

IMPORTS
OPERATION, ERROR FROM Remote-Operations-Information-Objects
	{joint-iso-itu-t remote-operations(4) informationObjects(5) version1(0) }

-- Data Types –-
universalFailure FROM CSTA-error-definition
	{ iso( 1) identified-organization( 3) icd-ecma( 12)
		standard( 0) csta3( 285) error-definition( 120) }
MonitorList FROM CSTA-status-reporting
	{ iso( 1) identified-organization( 3) icd-ecma( 12)
		standard( 0) csta3( 285) status-reporting( 126) }
ServiceCrossRefID FROM CSTA-capability-exchange
	{ iso( 1) identified-organization( 3) icd-ecma( 12)
		standard( 0) csta3( 285) capability-exchange( 131) }
CSTACommonArguments FROM CSTA-extension-types
	{ iso( 1) identified-organization( 3) icd-ecma( 12)
		standard( 0) csta3( 285) extension-types( 129) };

monitorInfo OPERATION ::=
{ 	ARGUMENT 		MonitorInfoArgument
	ERRORS 			{universalFailure }
	CODE 			local: 374 }

MonitorInfoArgument ::= SEQUENCE
{ 	serviceCrossRefID		ServiceCrossRefID,
	segmentID			INTEGER				OPTIONAL,
	lastSegment			BOOLEAN,
	monitorList			MonitorList,
	extensions 			CSTACommonArguments 		OPTIONAL }

END -- of CSTA-monitor-info
