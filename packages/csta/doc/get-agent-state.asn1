CSTA-get-agent-state
	{ iso( 1) identified-organization( 3) icd-ecma( 12)
		standard( 0) csta3( 285) get-agent-state( 304) }

DEFINITIONS ::=
BEGIN

IMPORTS
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
DeviceID FROM CSTA-device-identifiers
	{ iso( 1) identified-organization( 3) icd-ecma( 12)
		standard( 0) csta3( 285) device-identifiers( 123) }
AgentID, AgentState, PendingAgentState FROM CSTA-device-feature-types
	{ iso( 1) identified-organization( 3) icd-ecma( 12)
		standard( 0) csta3( 285) device-feature-types( 127) }
CSTACommonArguments FROM CSTA-extension-types
	{ iso( 1) identified-organization( 3) icd-ecma( 12)
		standard( 0) csta3( 285) extension-types( 129) };

getAgentState OPERATION ::=
{	ARGUMENT 		GetAgentStateArgument
	RESULT 			GetAgentStateResult
	ERRORS 			{universalFailure }
	CODE			local: 304 }

GetAgentStateArgument ::= SEQUENCE
{	device 				DeviceID,
	acdGroup			DeviceID	 			OPTIONAL,
	extensions			CSTACommonArguments			OPTIONAL }

GetAgentStateResult ::= SEQUENCE
{	agentStateList 			AgentStateList,
	extensions 			CSTACommonArguments		 	OPTIONAL }

AgentStateList ::= SEQUENCE SIZE (1..32) OF AgentStateEntry

AgentStateEntry ::= SEQUENCE
{	agentID				AgentID					OPTIONAL,
	loggedOn			BOOLEAN,
	agentInfo			SEQUENCE OF AgentInfo 			OPTIONAL }

AgentInfo ::= SEQUENCE
{	acdGroup			DeviceID				OPTIONAL,
	agentState			AgentState,
	pendingAgentState		[0] IMPLICIT PendingAgentState		OPTIONAL,
	agentStateCondition		[1] IMPLICIT AgentStateCondition	OPTIONAL }

AgentStateCondition ::= ENUMERATED
{	forcedPause			(0),
	other				(1) }

END -- of CSTA-get-agent-state
