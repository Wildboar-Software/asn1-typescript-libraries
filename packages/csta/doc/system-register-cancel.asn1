CSTA-system-register-cancel
	{ iso( 1) identified-organization( 3) icd-ecma( 12)
		standard( 0) csta3( 285) system-register-cancel( 209) }

DEFINITIONS ::=
BEGIN

IMPORTS
OPERATION, ERROR FROM Remote-Operations-Information-Objects
	{joint-iso-itu-t remote-operations(4) informationObjects(5) version1(0) }

-- Data Types --
universalFailure FROM CSTA-error-definition
	{ iso( 1) identified-organization( 3) icd-ecma( 12)
		standard( 0) csta3( 285) error-definition( 120) }
SysStatRegisterID FROM CSTA-device-feature-types
	{ iso( 1) identified-organization( 3) icd-ecma( 12)
		standard( 0) csta3( 285) device-feature-types( 127) }
CSTACommonArguments FROM CSTA-extension-types
	{ iso( 1) identified-organization( 3) icd-ecma( 12)
		standard( 0) csta3( 285) extension-types( 129) };

systemRegisterCancel OPERATION ::=
{ 	ARGUMENT 		SystemRegisterCancelArgument
	RESULT 			SystemRegisterCancelResult
	ERRORS 			{universalFailure }
	CODE 			local: 209 }

SystemRegisterCancelArgument ::= SEQUENCE
{ 	sysStatRegisterID 		SysStatRegisterID,
	extensions 			CSTACommonArguments 		OPTIONAL }

SystemRegisterCancelResult ::= CHOICE
{ 	extensions 			CSTACommonArguments,
	noData 				NULL }

END -- of CSTA-system-register-cancel
