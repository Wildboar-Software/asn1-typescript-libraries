CSTA-reconnect-call
	{ iso( 1) identified-organization( 3) icd-ecma( 12)
		standard( 0) csta3( 285) reconnect-call( 13) }

DEFINITIONS ::=
BEGIN

IMPORTS
OPERATION, ERROR FROM Remote-Operations-Information-Objects
	{joint-iso-itu-t remote-operations(4) informationObjects(5) version1(0) }

-- Data Types –-
universalFailure FROM CSTA-error-definition
	{ iso( 1) identified-organization( 3) icd-ecma( 12)
		standard( 0) csta3( 285) error-definition( 120) }
ConnectionID FROM CSTA-call-connection-identifiers
	{ iso( 1) identified-organization( 3) icd-ecma( 12)
		standard( 0) csta3( 285) call-connection-identifiers( 124) }
CSTACommonArguments FROM CSTA-extension-types
	{ iso( 1) identified-organization( 3) icd-ecma( 12)
		standard( 0) csta3( 285) extension-types( 129) };

reconnectCall OPERATION ::=
{ 	ARGUMENT 		ReconnectCallArgument
	RESULT 			ReconnectCallResult
	ERRORS 			{universalFailure }
	CODE 			local: 13 }

ReconnectCallArgument ::= SEQUENCE
{ 	activeCall 			ConnectionID,
	heldCall 			ConnectionID,
	extensions 			CSTACommonArguments 		OPTIONAL }

ReconnectCallResult ::= CHOICE
{	extensions 			CSTACommonArguments,
	noData 				NULL }

END -- of CSTA-reconnect-call
