CSTA-media-attached-event
	{ iso( 1) identified-organization( 3) icd-ecma( 12)
		standard( 0) csta3( 285) media-attached-event( 246) }

DEFINITIONS ::=

BEGIN

IMPORTS
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
SubjectDeviceID FROM CSTA-device-identifiers
	{ iso( 1) identified-organization( 3) icd-ecma( 12)
		standard( 0) csta3( 285) device-identifiers( 123) }
ConnectionID FROM CSTA-call-connection-identifiers
	{ iso( 1) identified-organization( 3) icd-ecma( 12)
		standard( 0) csta3( 285) call-connection-identifiers( 124) }
LocalConnectionState FROM CSTA-connection-states
	{ iso( 1) identified-organization( 3) icd-ecma( 12)
		standard( 0) csta3( 285) connection-states( 125) }
CSTACommonArguments FROM CSTA-extension-types
	{ iso( 1) identified-organization( 3) icd-ecma( 12)
		standard( 0) csta3( 285) extension-types( 129) }
CallCharacteristics FROM CSTA-call-control 
	{ iso( 1) identified-organization( 3) icd-ecma( 12)
		standard( 0) csta3( 285) call-control( 130) }
MediaServiceType, MediaServiceInstanceID, MediaStreamID, 
MediaCallCharacteristics, ConnectionInformation FROM CSTA-media-services
	{ iso( 1) identified-organization( 3) icd-ecma( 12)
		standard( 0) csta3( 285) media-services( 136) };

MediaAttachedEvent ::= SEQUENCE
{	mediaConnection	 		ConnectionID,
	mediaDevice 			SubjectDeviceID,
	mediaServiceType	 	MediaServiceType,
	mediaServiceVersion		INTEGER					OPTIONAL,
	mediaServiceInstanceID		[0] IMPLICIT MediaServiceInstanceID 	OPTIONAL,
	mediaStreamID 			[1] IMPLICIT MediaStreamID		OPTIONAL,
	mediaCallCharacteristics	[2] IMPLICIT MediaCallCharacteristics	OPTIONAL,
	callCharacteristics		CallCharacteristics			OPTIONAL,
	localConnectionInfo		LocalConnectionState			OPTIONAL,
	mediaConnectionInfo	 	[3] IMPLICIT ConnectionInformation	OPTIONAL,
	extension			CSTACommonArguments			OPTIONAL }

END  -- of CSTA-media-attached-event
