CSTA-call-back-message-call-related
	{ iso( 1) identified-organization( 3) icd-ecma( 12)
		standard( 0) csta3( 285) call-back-message-call-related( 216) }

DEFINITIONS ::=
BEGIN

IMPORTS
OPERATION, ERROR FROM Remote-Operations-Information-Objects
	{joint-iso-itu-t remote-operations(4) informationObjects(5) version1(0) }

-- Data Types –-
universalFailure FROM CSTA-error-definition
	{ iso( 1) identified-organization( 3) icd-ecma( 12)
		standard( 0) csta3( 285) error-definition( 120) }
DeviceID FROM CSTA-device-identifiers
	{ iso( 1) identified-organization( 3) icd-ecma( 12)
		standard( 0) csta3( 285) device-identifiers( 123) }
ConnectionID FROM CSTA-call-connection-identifiers
	{ iso( 1) identified-organization( 3) icd-ecma( 12)
		standard( 0) csta3( 285) call-connection-identifiers( 124) }
CSTACommonArguments FROM CSTA-extension-types
	{ iso( 1) identified-organization( 3) icd-ecma( 12)
		standard( 0) csta3( 285) extension-types( 129) };
callBackMessage OPERATION ::=
{ 	ARGUMENT 		CallBackMessageArgument
	RESULT 			CallBackMessageResult
	ERRORS 			{universalFailure }
	CODE 			local: 216 }

CallBackMessageArgument ::= SEQUENCE
{ 	callbackMessageConnection 	ConnectionID,
	extensions 			CSTACommonArguments 		OPTIONAL }

CallBackMessageResult ::= SEQUENCE
{ 	targetDevice 			DeviceID 			OPTIONAL,
	extensions 			CSTACommonArguments 		OPTIONAL }

END -- of CSTA-call-back-message-call-related
