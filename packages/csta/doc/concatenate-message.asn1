CSTA-concatenate-message
	{ iso( 1) identified-organization( 3) icd-ecma( 12)
		standard( 0) csta3( 285) concatenate-message( 500) }

DEFINITIONS ::=
BEGIN

IMPORTS	
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
MessageID FROM CSTA-device-feature-types
	{ iso( 1) identified-organization( 3) icd-ecma( 12)
		standard( 0) csta3( 285) device-feature-types( 127) }
CSTACommonArguments FROM CSTA-extension-types
	{ iso( 1) identified-organization( 3) icd-ecma( 12)
		standard( 0) csta3( 285) extension-types( 129) };

concatenateMessage OPERATION ::=
{	ARGUMENT		ConcatenateMessageArgument
	RESULT			ConcatenateMessageResult
	ERRORS			{universalFailure }
	CODE			local: 500 }

ConcatenateMessageArgument ::= SEQUENCE
{	messagesToConcatenate		SEQUENCE OF MessageID,
 	extensions			CSTACommonArguments			OPTIONAL } 

ConcatenateMessageResult ::= SEQUENCE
{	concatenatedMessage		MessageID,
	extensions			CSTACommonArguments			OPTIONAL }

END  -- of CSTA-concatenate-message
