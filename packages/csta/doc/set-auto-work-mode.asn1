CSTA-set-auto-work-mode
	{ iso( 1) identified-organization( 3) icd-ecma( 12)
		standard( 0) csta3( 285) set-auto-work-mode( 314) }

DEFINITIONS ::=
BEGIN

IMPORTS
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
DeviceID FROM CSTA-device-identifiers
	{ iso( 1) identified-organization( 3) icd-ecma( 12)
		standard( 0) csta3( 285) device-identifiers( 123) }
CSTACommonArguments FROM CSTA-extension-types
	{ iso( 1) identified-organization( 3) icd-ecma( 12)
		standard( 0) csta3( 285) extension-types( 129) };

setAutoWorkMode OPERATION ::=
{	ARGUMENT 		SetAutoWorkModeArgument
	RESULT 			SetAutoWorkModeResult
	ERRORS 			{universalFailure }
	CODE			local: 314 }

SetAutoWorkModeArgument ::= SEQUENCE
{	device 				DeviceID,
	autoWorkOn			BOOLEAN,
	autoWorkInterval		INTEGER (0..6000)			OPTIONAL,
	extensions			CSTACommonArguments 			OPTIONAL }

SetAutoWorkModeResult  ::= CHOICE
{	extensions 			CSTACommonArguments,
	noData 				NULL }

END -- of CSTA-set-auto-work-mode
