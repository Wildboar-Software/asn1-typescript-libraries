CSTA-set-button-information
	{ iso( 1) identified-organization( 3) icd-ecma( 12)
		standard( 0) csta3( 285) set-button-information( 273) }

DEFINITIONS ::=
BEGIN

IMPORTS
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
DeviceID FROM CSTA-device-identifiers
	{ iso( 1) identified-organization( 3) icd-ecma( 12)
		standard( 0) csta3( 285) device-identifiers( 123) }
CSTACommonArguments FROM CSTA-extension-types
	{ iso( 1) identified-organization( 3) icd-ecma( 12)
		standard( 0) csta3( 285) extension-types( 129) }
ButtonID FROM CSTA-physical-device-feature 
	{ iso( 1) identified-organization( 3) icd-ecma( 12)
		standard( 0) csta3( 285) physical-device-feature( 137) };

setButtonInformation OPERATION ::=
{	ARGUMENT 		SetButtonInformationArgument
	RESULT			SetButtonInformationResult
	ERRORS			{universalFailure }
	CODE			local: 273 }

SetButtonInformationArgument ::= SEQUENCE
{	device 				DeviceID,
	button 				ButtonID,
	buttonLabel			IA5String (SIZE(0..64))			OPTIONAL,
	buttonAssociatedNumber		DeviceID				OPTIONAL,
	extensions 			CSTACommonArguments 			OPTIONAL }

SetButtonInformationResult ::= CHOICE
{	extensions 			CSTACommonArguments,
	noData 				NULL }

END -- of CSTA-set-button-information
