CSTA-resume
	{ iso( 1) identified-organization( 3) icd-ecma( 12)
		standard( 0) csta3( 285) resume( 505) }
DEFINITIONS ::=
BEGIN

IMPORTS	
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
ConnectionID FROM CSTA-call-connection-identifiers
	{ iso( 1) identified-organization( 3) icd-ecma( 12)
		standard( 0) csta3( 285) call-connection-identifiers( 124) }
ResourceID, MessageID FROM CSTA-device-feature-types
	{ iso( 1) identified-organization( 3) icd-ecma( 12)
		standard( 0) csta3( 285) device-feature-types( 127) }
CSTACommonArguments FROM CSTA-extension-types
	{ iso( 1) identified-organization( 3) icd-ecma( 12)
		standard( 0) csta3( 285) extension-types( 129) };

resume	OPERATION ::=
{	ARGUMENT		ResumeArgument
	RESULT			ResumeResult
	ERRORS			{universalFailure }
	CODE	 		local: 505 }

ResumeArgument ::= SEQUENCE
{	connection			ConnectionID,
	messageToResume			MessageID				OPTIONAL,   --corrected 06/2001
	resource			[0] IMPLICIT ResourceID			OPTIONAL,
	duration			INTEGER					OPTIONAL,
	extensions			CSTACommonArguments			OPTIONAL }

ResumeResult ::= CHOICE
{	extensions			CSTACommonArguments,
	noData				NULL }

END  -- of CSTA-resume
