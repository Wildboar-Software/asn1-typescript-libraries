CSTA-io-register-cancel
	{ iso( 1) identified-organization( 3) icd-ecma( 12)
		standard( 0) csta3( 285) io-register-cancel( 342) }

DEFINITIONS ::=
BEGIN

IMPORTS	
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
IORegisterReqID FROM CSTA-device-feature-types
	{ iso( 1) identified-organization( 3) icd-ecma( 12)
		standard( 0) csta3( 285) device-feature-types( 127) }
CSTACommonArguments FROM CSTA-extension-types
	{ iso( 1) identified-organization( 3) icd-ecma( 12)
		standard( 0) csta3( 285) extension-types( 129) };

ioRegisterCancel OPERATION ::=
{	ARGUMENT		IORegisterCancelArgument
	RESULT			IORegisterCancelResult
	ERRORS			{universalFailure }
	CODE			local: 342 }

IORegisterCancelArgument ::= SEQUENCE
{	ioRegisterReqID			IORegisterReqID,
	extensions			CSTACommonArguments			OPTIONAL }

IORegisterCancelResult ::= CHOICE
{	extensions			CSTACommonArguments,
	noData				NULL }

END  -- of CSTA-io-register-cancel
