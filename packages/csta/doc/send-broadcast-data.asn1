CSTA-send-broadcast-data
	{ iso( 1) identified-organization( 3) icd-ecma( 12)
		standard( 0) csta3( 285) send-broadcast-data( 114) }
DEFINITIONS ::=
BEGIN

IMPORTS	
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
DataPathType, DisplayAttributeList FROM CSTA-device-feature-types
	{ iso( 1) identified-organization( 3) icd-ecma( 12)
		standard( 0) csta3( 285) device-feature-types( 127) }
CSTACommonArguments FROM CSTA-extension-types
	{ iso( 1) identified-organization( 3) icd-ecma( 12)
		standard( 0) csta3( 285) extension-types( 129) };

sendBroadcastData OPERATION ::=
{	ARGUMENT		SendBroadcastDataArgument
	RESULT			SendBroadcastDataResult
	ERRORS			{universalFailure }
	CODE			local: 114 }

SendBroadcastDataArgument ::= SEQUENCE
{	ioData				OCTET STRING,
	dataPathType			DataPathType				OPTIONAL,
	displayAttributes		DisplayAttributeList			OPTIONAL,
	extensions 			CSTACommonArguments			OPTIONAL }

SendBroadcastDataResult ::= CHOICE
{	extensions 			CSTACommonArguments,
	noData				NULL }

END  -- of CSTA-send-broadcast-data
