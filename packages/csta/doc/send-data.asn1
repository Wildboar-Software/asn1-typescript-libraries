CSTA-send-data
	{ iso( 1) identified-organization( 3) icd-ecma( 12)
		standard( 0) csta3( 285) send-data( 112) }
DEFINITIONS ::=
BEGIN

IMPORTS	
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
EventCause FROM CSTA-event-causes
	{ iso( 1) identified-organization( 3) icd-ecma( 12)
		standard( 0) csta3( 285) event-causes( 121) }
IOCrossRefID, IORegisterReqID, DisplayAttributeList FROM CSTA-device-feature-types
	{ iso( 1) identified-organization( 3) icd-ecma( 12)
		standard( 0) csta3( 285) device-feature-types( 127) }
CSTACommonArguments FROM CSTA-extension-types
	{ iso( 1) identified-organization( 3) icd-ecma( 12)
		standard( 0) csta3( 285) extension-types( 129) };

sendData OPERATION ::=
{	ARGUMENT		SendDataArgument
	RESULT			SendDataResult
	ERRORS			{universalFailure }
	CODE			local: 112 }

SendDataArgument ::= SEQUENCE
{	ioCrossRefID			IOCrossRefID,
	ioRegisterReqID			[0] IMPLICIT IORegisterReqID		OPTIONAL,
	displayAttributes		DisplayAttributeList			OPTIONAL,
	ioData				OCTET STRING,
	ioCause				EventCause				OPTIONAL,
	extensions 			CSTACommonArguments			OPTIONAL }

SendDataResult ::= CHOICE
{	extensions			CSTACommonArguments,
	noData				NULL }

END  -- of CSTA-send-data
