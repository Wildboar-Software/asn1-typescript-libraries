CSTA-start
	{ iso( 1) identified-organization( 3) icd-ecma( 12)
		standard( 0) csta3( 285) start (516) }
DEFINITIONS ::=
BEGIN

IMPORTS	
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
ResourceID, MessageID FROM CSTA-device-feature-types
	{ iso( 1) identified-organization( 3) icd-ecma( 12)
		standard( 0) csta3( 285) device-feature-types( 127) }
ConnectionID FROM CSTA-call-connection-identifiers
{ iso( 1) identified-organization( 3) icd-ecma( 12)
	standard( 0) csta3( 285) call-connection-identifiers( 124) }
CSTACommonArguments FROM CSTA-extension-types
	{ iso( 1) identified-organization( 3) icd-ecma( 12)
		standard( 0) csta3( 285) extension-types( 129) };
start OPERATION ::=
{	ARGUMENT		StartArgument
	RESULT			StartResult
	ERRORS			{universalFailure }
	CODE			local: 516}

StartArgument ::= SEQUENCE
{	overConnection			ConnectionID,
	resource			[0] IMPLICIT ResourceID			OPTIONAL,
	text				[1] IMPLICIT IA5String			OPTIONAL,
	extensions			CSTACommonArguments			OPTIONAL } 

StartResult ::= SEQUENCE
{ 	extensions			CSTACommonArguments			OPTIONAL }

END  -- of CSTA-start
