CSTA-data-path-suspended
	{ iso( 1) identified-organization( 3) icd-ecma( 12)
		standard( 0) csta3( 285) data-path-suspended( 116) }

DEFINITIONS ::=
BEGIN

IMPORTS	
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
IOCrossRefID, IORegisterReqID FROM CSTA-device-feature-types
	{ iso( 1) identified-organization( 3) icd-ecma( 12)
		standard( 0) csta3( 285) device-feature-types( 127) }
CSTACommonArguments FROM CSTA-extension-types
	{ iso( 1) identified-organization( 3) icd-ecma( 12)
		standard( 0) csta3( 285) extension-types( 129) };

dataPathSuspended OPERATION ::=
{	ARGUMENT		DataPathSuspendedArgument
	RESULT			DataPathSuspendedResult
	ERRORS			{universalFailure }
	CODE			local: 116 }

DataPathSuspendedArgument ::= SEQUENCE
{	ioCrossRefID			IOCrossRefID,
	ioReqRegisterID			IORegisterReqID				OPTIONAL,
	extensions			CSTACommonArguments			OPTIONAL }

DataPathSuspendedResult ::= CHOICE
{	extensions			CSTACommonArguments,
	noData				NULL }

END  -- of CSTA-data-path-suspended
