CSTA-get-presence-state
	{ iso( 1) identified-organization( 3) icd-ecma( 12)
		standard( 0) csta3( 285) get-presence-state( 550) }

DEFINITIONS ::=
BEGIN

IMPORTS
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
DeviceID FROM CSTA-device-identifiers
	{ iso( 1) identified-organization( 3) icd-ecma( 12)
		standard( 0) csta3( 285) device-identifiers( 123) }
PresenceState FROM CSTA-device-feature-types
	{ iso( 1) identified-organization( 3) icd-ecma( 12)
		standard( 0) csta3( 285) device-feature-types( 127) }
TimeInfo FROM CSTA-security
{ iso( 1) identified-organization( 3) icd-ecma( 12)
standard( 0) csta3( 285) security( 128) }
CSTACommonArguments FROM CSTA-extension-types
	{ iso( 1) identified-organization( 3) icd-ecma( 12)
		standard( 0) csta3( 285) extension-types( 129) };

getPresenceState OPERATION ::=
{	ARGUMENT 		GetPresenceStateArgument
	RESULT 			GetPresenceStateResult
	ERRORS 			{universalFailure }
	CODE			local: 550 }

GetPresenceStateArgument ::= SEQUENCE
{	device 				DeviceID,
	extensions			CSTACommonArguments 			OPTIONAL }

GetPresenceStateResult ::= SEQUENCE
{ 	presenceState	 		PresenceState,
	fromTime			[0] IMPLICIT TimeInfo			OPTIONAL,
	untilTime			[1] IMPLICIT TimeInfo			OPTIONAL,
	place				[2] IMPLICIT OCTET STRING		OPTIONAL,
	mood				[3] IMPLICIT OCTET STRING		OPTIONAL,
	namedPresenceState 		[4] IMPLICIT OCTET STRING		OPTIONAL,
	extensions			CSTACommonArguments			OPTIONAL }

END -- of CSTA-get-presence-state
