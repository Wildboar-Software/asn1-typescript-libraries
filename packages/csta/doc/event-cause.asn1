CSTA-event-causes
	{ iso( 1) identified-organization( 3) icd-ecma( 12)
		standard( 0) csta3( 285) event-causes( 121) }

DEFINITIONS ::=
BEGIN

EXPORTS
EventCause;

EventCause ::= ENUMERATED
{ 	aCDBusy 				( 57),
	aCDForward 				( 58),
	aCDSaturated 				( 59),
	activation				( 88),
	activeParticipation 			(  1),
	alertTimeExpired 			( 60),
	alternate 				(  2),
	autoWork 				( 61),
	babble					( 89),
	badAttribute				( 90),
	badGrammar				( 91),
	badVoice				( 92),
	badUri					( 93),
	blocked 				( 35),
	busy 					(  3),
	busyOverflow				( 94),
	calendarOverflow			( 95),
	callBack 				(  4),
	callCancelled 				(  5),
	callForward 				(  9),
	callForwardImmediate 			(  6),
	callForwardBusy 			(  7),
	callForwardNoAnswer 			(  8),
	callInterception 			(116),
	callInterceptionBusy			(117),
	callInterceptionForwarded		(118),
	callInterceptionNoAnswer		(119),
	callInterceptionResourcesNotAvailable	(120),
	callNotAnswered 			( 10),
	callPickup 				( 11),
	campOn 					( 12),
	campOnTrunks 				( 62),
	capacityOverflow			( 96),
	characterCountReached	 		( 36),
	conference 				( 63),
	consultation 				( 37),
	destDetected 				( 64),
	destNotObtainable 			( 13),
	destOutOfOrder 				( 65),
	distributed 				( 38),
	distributionDelay 			( 66),
	doNotDisturb 				( 14),
	dTMFDigitDetected 			( 39),
	duplicateDTMF				( 97),
	durationExceeded 			( 40),
	earlyStop				( 98),
	emptyQueue				( 99),
	endOfMessageDetected 			( 41),
	enteringDistribution 			( 42),
	forcedPause 				( 43),
	forcedTransition 			( 67),
	incompatibleDestination 		( 15),
	interDigitTimeout			(100),
	intrude 				( 68),
	invalidAccountCode 			( 16),
	invalidConnection			(101),
	invalidConnectionState			(102),
	invalidNumberFormat 			( 69),
	joinCall 				( 70),
	keyOperation 				( 17),
	keyOperationInUse 			( 71),
	lawfulInterception 			(121),
	lockout 				( 18),
	maintenance 				( 19),
	makeCall 				( 44),
	makeConnection				(103),
	makePredictiveCall 			( 72),
	maxTimeout				(104),
	messageDurationExceeded 		( 73),
	messageSizeExceeded 			( 45),
	multipleAlerting 			( 74),
	multipleQueuing 			( 75),
	networkCongestion 			( 20),
	networkDialling 			( 76),
	networkNotObtainable 			( 21),
	networkOutOfOrder 			( 77),
	networkSignal 				( 46),
	newCall 				( 22),
	nextMessage 				( 47),
	noAudioSaved				(105),
	noAvailableAgents 			( 23),
	noQueue					(106),
	normal 					( 78),
	normalClearing 				( 48),
	noRule					(107),
	noSpeechDetected 			( 49),
	notAvaliableBearerService 		( 79),
	notSupportedBearerService 		( 80),
	numberChanged 				( 50),
	numberUnallocated 			( 81),
	outOfGrammar				(108),
	overflow 				( 26),
	override 				( 24),
	park 					( 25),
	pathReplacement				(109),
	queueCleared 				( 82),
	queueTimeOverflow			(110),
	recall 					( 27),
	recallBusy				(111),
	recallForwarded				(112),
	recallNoAnswer				(113),
	recallResourcesNotAvailable		(114),
	redirected 				( 28),
	remainsInQueue 				( 83),
	reorderTone 				( 29),
	reserved 				( 84),
	resourcesNotAvailable 			( 30),
	selectedTrunkBusy 			( 85),
	silentParticipation 			( 31),
	singleStepConference 			( 51),
	singleStepTransfer 			( 52),
	speechDetected 				( 53),
	suspend 				( 86),
	switchingFunctionTerminated 		( 54),
	terminationCharacterReceived 		( 55),
	timeout 				( 56),
	transfer 				( 32),
	trunksBusy 				( 33),
	unauthorisedBearerService 		( 87),
	unknownOverflow				(115) }
	-- voiceUnitInitiator 			( 34) 
	-- *** note that the voiceUnitOriginator ( 34) is no longer used (commented out) ***

END -- of CSTA-event-causes
