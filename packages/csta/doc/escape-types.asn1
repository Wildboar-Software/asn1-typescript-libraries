CSTA-escape-types
	{ iso( 1) identified-organization( 3) icd-ecma( 12)
		standard( 0) csta3( 285) escape-types( 135) }

DEFINITIONS ::=
BEGIN

EXPORTS
EscapeRegisterID;

EscapeRegisterID ::= [0] OCTET STRING

END -- of CSTA-escape-types
