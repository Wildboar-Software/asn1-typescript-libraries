CSTA-snapshot-device-data
	{ iso( 1) identified-organization( 3) icd-ecma( 12)
		standard( 0) csta3( 285) snapshot-device-data(107) }

DEFINITIONS ::=
BEGIN

IMPORTS
OPERATION, ERROR FROM Remote-Operations-Information-Objects
	{joint-iso-itu-t remote-operations(4) informationObjects(5) version1(0) }

-- Data Types –-
universalFailure FROM CSTA-error-definition
	{ iso( 1) identified-organization( 3) icd-ecma( 12)
		standard( 0) csta3( 285) error-definition( 120) }
SnapshotDeviceData FROM CSTA-status-reporting
	{ iso( 1) identified-organization( 3) icd-ecma( 12)
		standard( 0) csta3( 285) status-reporting( 126) }
CSTACommonArguments FROM CSTA-extension-types
	{ iso( 1) identified-organization( 3) icd-ecma( 12)
		standard( 0) csta3( 285) extension-types( 129) }
ServiceCrossRefID FROM CSTA-capability-exchange
	{ iso( 1) identified-organization( 3) icd-ecma( 12)
		standard( 0) csta3( 285) capability-exchange( 131) };

snapshotDeviceData OPERATION ::=
{ 	ARGUMENT 		SnapshotDeviceDataArgument
	ERRORS 			{universalFailure }
	ALWAYS RESPONDS 	FALSE
	CODE 			local: 77 }

SnapshotDeviceDataArgument ::= SEQUENCE
{	serviceCrossRefID 		ServiceCrossRefID,
	segmentID 			INTEGER 			OPTIONAL,
	lastSegment 			BOOLEAN,
	snapshotData 			SnapshotDeviceData,
	extensions 			CSTACommonArguments 		OPTIONAL }

END -- of CSTA-snapshot-device-data
