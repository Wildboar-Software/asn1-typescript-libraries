CSTA-get-routeing-mode
	{ iso( 1) identified-organization( 3) icd-ecma( 12)
		standard( 0) csta3( 285) get-routeing-mode( 311) }

DEFINITIONS ::=
BEGIN

IMPORTS
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
DeviceID FROM CSTA-device-identifiers
	{ iso( 1) identified-organization( 3) icd-ecma( 12)
		standard( 0) csta3( 285) device-identifiers( 123) }
CSTACommonArguments FROM CSTA-extension-types
	{ iso( 1) identified-organization( 3) icd-ecma( 12)
		standard( 0) csta3( 285) extension-types( 129) };

getRouteingMode OPERATION ::=
{	ARGUMENT 		GetRouteingModeArgument
	RESULT 			GetRouteingModeResult
	ERRORS 			{universalFailure }
	CODE			local: 311 }

GetRouteingModeArgument ::= SEQUENCE
{	device 				DeviceID,
	extensions			CSTACommonArguments 			OPTIONAL }

GetRouteingModeResult ::= SEQUENCE
{	routeingMode			BOOLEAN,
	extensions			CSTACommonArguments			OPTIONAL }

END -- of CSTA-get-routeing-mode
