CSTA-get-monitor
	{ iso( 1) identified-organization( 3) icd-ecma( 12)
		standard( 0) csta3( 285) get-monitor ( 373) }

DEFINITIONS ::=
BEGIN

IMPORTS
OPERATION, ERROR FROM Remote-Operations-Information-Objects
	{joint-iso-itu-t remote-operations(4) informationObjects(5) version1(0) }

-- Data Types –-
universalFailure FROM CSTA-error-definition
	{ iso( 1) identified-organization( 3) icd-ecma( 12)
		standard( 0) csta3( 285) error-definition( 120) }
MonitorList FROM CSTA-status-reporting
	{ iso( 1) identified-organization( 3) icd-ecma( 12)
		standard( 0) csta3( 285) status-reporting( 126) }
ServiceCrossRefID FROM CSTA-capability-exchange
	{ iso( 1) identified-organization( 3) icd-ecma( 12)
		standard( 0) csta3( 285) capability-exchange( 131) }
CSTACommonArguments FROM CSTA-extension-types
	{ iso( 1) identified-organization( 3) icd-ecma( 12)
		standard( 0) csta3( 285) extension-types( 129) };

getMonitors OPERATION ::=
{ 	ARGUMENT 		GetMonitorArgument
	RESULT 			GetMonitorResult
	ERRORS 			{universalFailure }
	CODE 			local: 373 }

GetMonitorArgument ::= SEQUENCE
{ 	extensions 			CSTACommonArguments 		OPTIONAL }

GetMonitorResult ::= SEQUENCE
{ 	crossRefIDorRegistrationData	CHOICE
	{	serviceCrossRefID	ServiceCrossRefID,	
		monitorList		MonitorList },
	extensions 			CSTACommonArguments 		OPTIONAL }

END -- of CSTA-get-monitor
