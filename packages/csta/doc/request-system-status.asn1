CSTA-request-system-status
	{ iso( 1) identified-organization( 3) icd-ecma( 12)
	standard( 0) csta3( 285) request-system-status( 210) }

DEFINITIONS ::=
BEGIN

IMPORTS
OPERATION, ERROR FROM Remote-Operations-Information-Objects
	{joint-iso-itu-t remote-operations(4) informationObjects(5) version1(0) }

-- Data Types –-
universalFailure FROM CSTA-error-definition
	{ iso( 1) identified-organization( 3) icd-ecma( 12)
		standard( 0) csta3( 285) error-definition( 120) }
SysStatRegisterID, SystemStatus FROM CSTA-device-feature-types
	{ iso( 1) identified-organization( 3) icd-ecma( 12)
		standard( 0) csta3( 285) device-feature-types( 127) }
CSTACommonArguments FROM CSTA-extension-types
	{ iso( 1) identified-organization( 3) icd-ecma( 12)
		standard( 0) csta3( 285) extension-types( 129) };

requestSysStat OPERATION ::=
{ 	ARGUMENT 		RequestSysStatArg
	RESULT 			RequestSysStatRes
	ERRORS 			{universalFailure }
	CODE 			local: 210 }

RequestSysStatArg ::= SEQUENCE
{ 	sysStatRegisterID 		SysStatRegisterID 		OPTIONAL,
	extensions 			CSTACommonArguments 		OPTIONAL }

RequestSysStatRes ::= SEQUENCE
{ 	systemStatus 			SystemStatus,
	extensions 			CSTACommonArguments 		OPTIONAL }

END -- of CSTA-request-system-status
