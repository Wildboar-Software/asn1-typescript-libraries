CSTA-route-used-request 
	{ iso( 1) identified-organization( 3) icd-ecma( 12) 
		standard( 0) csta3( 285) route-used-request( 84) }

DEFINITIONS::=
BEGIN

IMPORTS
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
CallingDeviceID, CalledDeviceID FROM CSTA-device-identifiers 
	{ iso( 1) identified-organization( 3) icd-ecma( 12)
		standard( 0) csta3( 285) device-identifiers( 123) }
CorrelatorData, RouteRegisterReqID, RouteingCrossRefID FROM CSTA-device-feature-types
	{ iso( 1) identified-organization( 3) icd-ecma( 12)
		standard( 0) csta3( 285) device-feature-types( 127) }
CSTACommonArguments FROM CSTA-extension-types 
	{ iso( 1) identified-organization( 3) icd-ecma( 12)
		standard( 0) csta3( 285) extension-types( 129) }
CallLinkageData FROM CSTA-call-control 
	{ iso( 1) identified-organization( 3) icd-ecma( 12)
		standard( 0) csta3( 285) call-control( 130) };

routeUsedRequest OPERATION ::=
{	ARGUMENT 		RouteUsedRequestArgument
	ERRORS	 		{universalFailure }
	ALWAYS RESPONDS		FALSE
	CODE			local: 34 }

RouteUsedRequestArgument ::= SEQUENCE
{	crossRefIdentifier		RouteingCrossRefID,
	routeRegisterReqID		[0] IMPLICIT RouteRegisterReqID		OPTIONAL,
	routeUsed			CalledDeviceID,
	callingDevice			CallingDeviceID				OPTIONAL,
	domain				BOOLEAN					OPTIONAL,
	correlatorData			[1] IMPLICIT CorrelatorData		OPTIONAL,
	callLinkageData			[2] IMPLICIT CallLinkageData		OPTIONAL,
	extensions			CSTACommonArguments			OPTIONAL }

END  -- of CSTA-route-used-request
