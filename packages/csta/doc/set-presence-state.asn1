CSTA-set-presence-state
	{ iso( 1) identified-organization( 3) icd-ecma( 12)
		standard( 0) csta3( 285) set-presence-state( 551) }

DEFINITIONS ::=
BEGIN

IMPORTS
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
DeviceID FROM CSTA-device-identifiers
	{ iso( 1) identified-organization( 3) icd-ecma( 12)
		standard( 0) csta3( 285) device-identifiers( 123) }
PresenceState FROM CSTA-device-feature-types
	{ iso( 1) identified-organization( 3) icd-ecma( 12)
		standard( 0) csta3( 285) device-feature-types( 127) }
TimeInfo FROM CSTA-security
{ iso( 1) identified-organization( 3) icd-ecma( 12)
standard( 0) csta3( 285) security( 128) }
CSTACommonArguments FROM CSTA-extension-types
	{ iso( 1) identified-organization( 3) icd-ecma( 12)
		standard( 0) csta3( 285) extension-types( 129) };

setPresenceState OPERATION ::=
{	ARGUMENT 		SetPresenceStateArgument
	RESULT 			SetPresenceStateResult
	ERRORS 			{universalFailure }
	CODE			local: 551 }

SetPresenceStateArgument ::= SEQUENCE
{	device 				DeviceID,
	requestedPresenceState	 	PresenceState,
	fromTime			[0] IMPLICIT TimeInfo			OPTIONAL,
	untilTime			[1] IMPLICIT TimeInfo			OPTIONAL,
	place				[2] IMPLICIT OCTET STRING		OPTIONAL,
	mood				[3] IMPLICIT OCTET STRING		OPTIONAL,
	namedPresenceState 		[4] IMPLICIT OCTET STRING		OPTIONAL,
	extensions			CSTACommonArguments			OPTIONAL }

SetPresenceStateResult ::= CHOICE
{	extensions 			CSTACommonArguments,
	noData 				NULL }

END -- of CSTA-set-presence-state
