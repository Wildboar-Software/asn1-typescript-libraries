CSTA-call-back-call-related
	{ iso( 1) identified-organization( 3) icd-ecma( 12)
		standard( 0) csta3( 285) call-back-call-related( 215) }

DEFINITIONS ::=
BEGIN

IMPORTS
OPERATION, ERROR FROM Remote-Operations-Information-Objects
	{joint-iso-itu-t remote-operations(4) informationObjects(5) version1(0) }

-- Data Types –-
universalFailure FROM CSTA-error-definition
	{ iso( 1) identified-organization( 3) icd-ecma( 12)
		standard( 0) csta3( 285) error-definition( 120) }
DeviceID FROM CSTA-device-identifiers
	{ iso( 1) identified-organization( 3) icd-ecma( 12)
		standard( 0) csta3( 285) device-identifiers( 123) }
ConnectionID FROM CSTA-call-connection-identifiers
	{ iso( 1) identified-organization( 3) icd-ecma( 12)
		standard( 0) csta3( 285) call-connection-identifiers( 124) }
CSTACommonArguments FROM CSTA-extension-types
	{ iso( 1) identified-organization( 3) icd-ecma( 12)
		standard( 0) csta3( 285) extension-types( 129) }
SubjectOfCall,LanguagePreferences FROM CSTA-device-feature-types
	{ iso( 1) identified-organization( 3) icd-ecma( 12)
		standard( 0) csta3( 285) device-feature-types( 127) }
CallCharacteristics FROM CSTA-call-control
	{ iso( 1) identified-organization( 3) icd-ecma( 12)
		standard( 0) csta3( 285) call-control( 130) };

callBack OPERATION ::=
{ 	ARGUMENT 		CallBackArgument
	RESULT 			CallBackResult
	ERRORS 			{universalFailure }
	CODE 			local: 215 }

CallBackArgument ::= SEQUENCE
{ 	callbackConnection 		ConnectionID,
	callCharacteristics 		CallCharacteristics 			OPTIONAL,
	subjectOfCall			[0] IMPLICIT SubjectOfCall		OPTIONAL,
	languagePreferences		[1] IMPLICIT LanguagePreferences	OPTIONAL,
	extensions 			CSTACommonArguments 			OPTIONAL }

CallBackResult ::= SEQUENCE
{ 	targetDevice 			DeviceID 				OPTIONAL,
	extensions 			CSTACommonArguments 			OPTIONAL }

END -- of CSTA-call-back-call-related
