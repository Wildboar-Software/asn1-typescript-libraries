CSTA-get-speaker-mute
	{ iso( 1) identified-organization( 3) icd-ecma( 12)
		standard( 0) csta3( 285) get-speaker-mute( 271) }

DEFINITIONS ::=
BEGIN

IMPORTS
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
DeviceID FROM CSTA-device-identifiers
	{ iso( 1) identified-organization( 3) icd-ecma( 12)
		standard( 0) csta3( 285) device-identifiers( 123) }
CSTACommonArguments FROM CSTA-extension-types
	{ iso( 1) identified-organization( 3) icd-ecma( 12)
		standard( 0) csta3( 285) extension-types( 129) }
AuditoryApparatusID FROM CSTA-physical-device-feature 
	{ iso( 1) identified-organization( 3) icd-ecma( 12)
		standard( 0) csta3( 285) physical-device-feature( 137) };

getSpeakerMute OPERATION ::=
{	ARGUMENT 		GetSpeakerMuteArgument
	RESULT			GetSpeakerMuteResult
	ERRORS			{universalFailure }
	CODE			local: 271 }

GetSpeakerMuteArgument ::= SEQUENCE
{	device 				DeviceID,
	auditoryApparatus		AuditoryApparatusID			OPTIONAL,
	extensions 			CSTACommonArguments	 		OPTIONAL }

GetSpeakerMuteResult ::= SEQUENCE
{	speakerMuteList			SpeakerMuteList,
	extensions 			CSTACommonArguments			OPTIONAL }

SpeakerMuteList ::= SEQUENCE OF SEQUENCE
{	auditoryApparatus		AuditoryApparatusID,
	speakerMuteOn			BOOLEAN }

END -- of CSTA-get-speaker-mute
