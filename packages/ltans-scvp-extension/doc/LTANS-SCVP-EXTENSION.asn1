LTANS-SCVP-EXTENSION
{iso(1) identified-organization(3) dod(6) internet(1) security(5) mechanisms(5)
ltans(11) id-mod(0) id-mod-ers-scvp(5) id-mod-ers-scvp-v1(1)}
DEFINITIONS IMPLICIT TAGS ::=
BEGIN
IMPORTS

    -- id-swb
    --     FROM SCVP
    --     {iso(1) identified-organization(3) dod(6) internet(1) security(5)
    --     mechanisms(5) pkix(7) id-mod(0) 21}

    EvidenceRecord
        FROM ERS
        {iso(1) identified-organization(3) dod(6) internet(1) security(5)
        mechanisms(5) ltans(11) id-mod(0) id-mod-ers88(2) id-mod-ers88-v1(1)}
    ;

id-swb OBJECT IDENTIFIER ::=
    { iso(1) identified-organization(3) dod(6) internet(1) security(5)
    mechanisms(5) pkix(7) 18 }

id-swb-partial-cert-path        OBJECT IDENTIFIER ::= {id-swb 15}

id-swb-ers-pkc-cert             OBJECT IDENTIFIER ::= {id-swb 16}
id-swb-ers-best-cert-path       OBJECT IDENTIFIER ::= {id-swb 17}
id-swb-ers-partial-cert-path    OBJECT IDENTIFIER ::= {id-swb 18}
id-swb-ers-revocation-info      OBJECT IDENTIFIER ::= {id-swb 19}
id-swb-ers-all                  OBJECT IDENTIFIER ::= {id-swb 20}

EvidenceRecordWantBack ::= SEQUENCE {
    targetWantBack    OBJECT IDENTIFIER,
    evidenceRecord    EvidenceRecord OPTIONAL
}

EvidenceRecordWantBacks ::= SEQUENCE SIZE (1..MAX) OF EvidenceRecordWantBack

EvidenceRecords ::= SEQUENCE SIZE (1..MAX) OF EvidenceRecord

END
