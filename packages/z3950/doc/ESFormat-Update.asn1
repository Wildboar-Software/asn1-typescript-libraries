ESFormat-Update
{z39-50-extendedService update(5)}
DEFINITIONS ::=
BEGIN
IMPORTS

    DiagRec, InternationalString
        FROM Z39-50-APDU-2001
    ;

Update ::= CHOICE {
    esRequest   [1] IMPLICIT SEQUENCE {
        toKeep      [1] ClientPartToKeep,
        notToKeep   [2] ClientPartNotToKeep},
    taskPackage [2] IMPLICIT SEQUENCE {
        clientPart  [1] ClientPartToKeep,
        serverPart  [2] ServerPart
    }
}

ClientPartToKeep ::= SEQUENCE {
    action          [1] IMPLICIT INTEGER{
        recordInsert    (1),
        recordReplace   (2),
        recordDelete    (3),
        elementUpdate   (4)
    },
    databaseName    [2] IMPLICIT InternationalString,
    schema          [3] IMPLICIT OBJECT IDENTIFIER OPTIONAL,
    elementSetName  [4] IMPLICIT InternationalString OPTIONAL
}

ClientPartNotToKeep ::= SuppliedRecords

ServerPart ::= SEQUENCE {
    updateStatus        [1] IMPLICIT INTEGER {
        success (1),
        partial (2),
        failure (3)
    },
    globalDiagnostics   [2] IMPLICIT SEQUENCE OF DiagRec OPTIONAL,
    --These are non-surrogate diagnostics relating
    --to the task, not to individual records.
    taskPackageRecords  [3] IMPLICIT SEQUENCE OF TaskPackageRecordStructure
    --See comment 1.
}

--Auxiliary definitions for Update
SuppliedRecords ::= SEQUENCE OF SEQUENCE {
    recordId        [1] CHOICE {
        number [1] IMPLICIT INTEGER,
        string [2] IMPLICIT InternationalString,
        opaque [3] IMPLICIT OCTET STRING
    } OPTIONAL,
    supplementalId  [2] CHOICE {
        timeStamp       [1] IMPLICIT GeneralizedTime,
        versionNumber   [2] IMPLICIT InternationalString,
        previousVersion [3] IMPLICIT EXTERNAL
    } OPTIONAL,
    correlationInfo [3] IMPLICIT CorrelationInfo OPTIONAL,
    record          [4] IMPLICIT EXTERNAL
}

CorrelationInfo ::= SEQUENCE {
    -- Client may supply one or both for any record:
    note      [1] IMPLICIT InternationalString OPTIONAL,
    id        [2] IMPLICIT INTEGER OPTIONAL
}

TaskPackageRecordStructure ::= SEQUENCE {
    recordOrSurDiag [1] CHOICE {
        record              [1] IMPLICIT EXTERNAL,
        -- Choose 'record' if recordStatus is 'success', and elementSetName was supplied.
        diagnostic         [2] DiagRec
        -- Choose 'diagnostic', if RecordStatus is failure
    } OPTIONAL,
    --See comment 2
    correlationInfo [2] IMPLICIT CorrelationInfo OPTIONAL,
    -- This should be included if it was supplied by the client
    recordStatus    [3] IMPLICIT INTEGER {
        success           (1),
        queued            (2),
        inProcess         (3),
        failure           (4)
    }
}

END
