DiagnosticFormatDiag1
{z39-50-diagnostic diag-1(2)}
DEFINITIONS ::=
BEGIN
IMPORTS

    Term, Specification, AttributeList, SortElement, DatabaseName,
    DefaultDiagFormat, InternationalString
        FROM Z39-50-APDU-2001
    ;

DiagnosticFormat ::=  SEQUENCE OF SEQUENCE {
    diagnostic  [1] CHOICE {
        defaultDiagRec      [1] IMPLICIT DefaultDiagFormat,
        explicitDiagnostic  [2] DiagFormat
    } OPTIONAL,
    message     [2] IMPLICIT InternationalString OPTIONAL
}

DiagFormat ::= CHOICE {
    tooMany         [1000] IMPLICIT SEQUENCE{
        tooManyWhat     [1] IMPLICIT INTEGER{
            argumentWords       (1),
            truncatedWords      (2),
            booleanOperators    (3),
            incompleteSubfields (4),
            characters          (5),
            recordsRetrieved    (6),
            dataBasesSpecified  (7),
            resultSetsCreated   (8),
            indexTermsProcessed (9)},
        max             [2] IMPLICIT INTEGER OPTIONAL
    },
    badSpec         [1001] IMPLICIT SEQUENCE {
        -- element set name or specification
        spec            [1] IMPLICIT Specification,
        -- esn or element spec not supported
        db              [2] IMPLICIT DatabaseName OPTIONAL,
        -- if db specified, above spec not
        -- supported for db; otherwise,
        -- spec not supported period.
        goodOnes        [3] IMPLICIT SEQUENCE OF Specification OPTIONAL
        -- target supplies ones that are
        -- supported
    },
    dbUnavail       [1002] IMPLICIT SEQUENCE { -- database unavailable
        db  [1] IMPLICIT DatabaseName,
        why [2] IMPLICIT SEQUENCE {
            reasonCode  [1] IMPLICIT INTEGER{
                doesNotExist        (0),
                existsButUnavail    (1),
                locked              (2),
                accessDenied        (3)
            } OPTIONAL,
            message     [2] IMPLICIT InternationalString OPTIONAL
        }
    },
    unSupOp         [1003] IMPLICIT INTEGER { -- unsupported operator
        and       (0),
        or        (1),
        and-not   (2),
        prox      (3)
    },
    attribute       [1004] IMPLICIT SEQUENCE{
        -- Applies for unsupported attribute set,
        -- attribute type, attribute value, or term (for
        -- a given attribute type or value).
        id      [1] IMPLICIT OBJECT IDENTIFIER,
        -- if only "id" occurs, then
        -- attribute set is not supported
        type    [2] IMPLICIT INTEGER OPTIONAL,
        -- must occur if value occurs.
        value   [3] IMPLICIT INTEGER OPTIONAL,
        -- if omitted, and Type occurs,
        -- then Type is what is unsupported
        term    [4] Term OPTIONAL
        -- If occurs, term is illegal or
        -- not supported, for attribute
        -- value, if value occurs;
        -- otherwise, for type.
    },
    attCombo        [1005] IMPLICIT SEQUENCE {
        -- attribute combination not supported
        unsupportedCombination  [1] IMPLICIT AttributeList,
        recommendedAlternatives [2] IMPLICIT SEQUENCE OF AttributeList OPTIONAL
    },
    term            [1006] IMPLICIT SEQUENCE{
        problem         [1] IMPLICIT INTEGER{
            codedValue   (1),
            unparsable   (2),
            tooShort     (3),
            type         (4)
        } OPTIONAL,
        term            [2] Term
    },
    proximity       [1007] CHOICE { -- proximity diagnostics:
        resultSets      [1] IMPLICIT NULL,
        -- proximity between sets not supported
        badSet          [2] IMPLICIT InternationalString,
        -- bad result set specified
        relation        [3] IMPLICIT INTEGER,
        -- 1 to 6 ; relation not supported
        unit            [4] IMPLICIT INTEGER,
        -- unsupported unit code
        distance        [5] IMPLICIT INTEGER,
        -- unsupported distance
        attributes      [6] AttributeList,
        --   proximity not supported with
        -- specified attribute combination
        ordered         [7] IMPLICIT NULL,
        -- ordered flag not supported
        exclusion       [8] IMPLICIT NULL
        -- exclusion flag not supported
    },
    scan            [1008] CHOICE {        -- scan diagnostics:
        nonZeroStepSize    [0] IMPLICIT NULL,
        -- only zero step size
        -- supported
        specifiedStepSize  [1] IMPLICIT NULL,
        -- specified step size not
        -- supported
        termList1          [3] IMPLICIT NULL,
        -- term list not supported
        -- (no alternative supplied)
        termList2          [4] IMPLICIT SEQUENCE OF AttributeList,
        -- term list not supported
        -- (alternatives supplied)
        posInResponse      [5] IMPLICIT INTEGER {
            -- value of positionIn-
            -- Response not supported
            mustBeOne              (1),
            mustBePositive         (2),
            mustBeNonNegative      (3),
            other                  (4)
        },
        resources         [6] IMPLICIT NULL,
        -- resources exhausted
        -- looking for satisfying
        -- terms
        endOfList         [7] IMPLICIT NULL
        -- beginning or end of term
        -- list
    },
    sort            [1009] CHOICE{
        sequence            [0] IMPLICIT NULL,
        -- cannot sort according to sequence
        noRsName            [1] IMPLICIT NULL,
        -- no result set name supplied
        tooMany             [2] IMPLICIT INTEGER,
        -- Too many input result sets, maximum supplied.
        incompatible        [3] IMPLICIT NULL,
        -- records with different formats not compatible for sorting
        generic             [4] IMPLICIT NULL,
        -- generic sort not supported (db specific only)
        dbSpecific          [5] IMPLICIT NULL,
        -- db specific sort not supported
        sortElement         [6] SortElement,
        key                 [7] IMPLICIT INTEGER {
            tooMany     (1),
            -- too many sort keys
            duplicate   (2)
        },
        -- duplicate sort keys
        action              [8] IMPLICIT NULL,
        -- unuspported missing data action
        illegal             [9] IMPLICIT INTEGER {
            relation    (1),
            -- illegal sort relation
            case        (2),
            -- illegal case value
            action      (3),
            -- illegal missing data action
            sort        (4)
        },
        -- illegal sort
        inputTooLarge       [10] IMPLICIT SEQUENCE OF InternationalString,
        -- one or more of the
        -- input result sets too
        -- large to sort
        aggregateTooLarge   [11] IMPLICIT NULL
        --  aggregate result set
        -- too large
    },
    segmentation    [1010]  CHOICE{
        segmentCount    [0] IMPLICIT NULL,
        -- Cannot guarantee record will fit
        -- within max segments. Target
        -- suggests that origin try again
        -- to retrieve record, without
        -- including max-segment-count.
        segmentSize     [1] IMPLICIT INTEGER
        -- record cannot be segmented into
        -- fragments such that the largest
        -- will fit within max segment
        -- size specified. Target supplies (in
        -- bytes) the smallest acceptable value.
        -- of Max-segment-size to retrieve
        -- the record.
    },
    extServices     [1011] CHOICE{
        req             [1] IMPLICIT INTEGER { -- bad request
            nameInUse       (1),
            -- package name already in use
            noSuchName      (2),
            -- no such package, on
            -- modify/delete
            quota           (3),
            -- quota exceeded
            type            (4)
        },
        -- extended service type not supported
        permission      [2] IMPLICIT INTEGER {
            -- permission denied on ES, because:
            id             (1),
            -- id not authorized, or
            modifyDelete   (2)
        },
        -- cannot modify or delete
        immediate       [3] IMPLICIT INTEGER {
            -- immediate execution:
            failed      (1),
            service     (2),
            -- not supported for this service,
            parameters  (3)
            -- not supported for these parameters.
        }
    },
    accessCtrl      [1012] CHOICE{
        noUser          [1] IMPLICIT NULL,
        -- no user to display challenge to
        refused         [2] IMPLICIT NULL,
        -- access control information refused by user
        simple          [3] IMPLICIT NULL,
        -- only simple form supported (target used externally defined)
        oid             [4] IMPLICIT SEQUENCE OF OBJECT IDENTIFIER,
        -- oid not supported (origin supplies alternative suggested oids)
        alternative     [5] IMPLICIT SEQUENCE OF OBJECT IDENTIFIER,
        -- origin insists that target use
        -- an alternative challenge for
        -- this data (e.g. stronger
        -- authentication or stronger
        -- Access control). The origin
        -- supplies suggested alternative oids.
        pwdInv          [6] IMPLICIT NULL,
        -- password invalid
        pwdExp          [7] IMPLICIT NULL
        -- password expired
    },
    recordSyntax    [1013] IMPLICIT SEQUENCE {
        -- record cannot be transferred in requested syntax
        unsupportedSyntax       [1] IMPLICIT OBJECT IDENTIFIER,
        suggestedAlternatives   [2] IMPLICIT SEQUENCE OF OBJECT IDENTIFIER OPTIONAL
    }
}

END
