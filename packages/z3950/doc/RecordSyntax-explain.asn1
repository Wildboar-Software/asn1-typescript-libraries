RecordSyntax-explain
{z39-50-recordSyntax explain(100)}
DEFINITIONS ::=
BEGIN
IMPORTS

    AttributeSetId, Term, OtherInformation, DatabaseName, ElementSetName,
    IntUnit, Unit, StringOrNumeric, Specification, InternationalString
        FROM Z39-50-APDU-2001
    ;

Explain-Record ::= CHOICE {
    -- Each of these may be used as search term when Use attribute is 'explain-category'.
    targetInfo              [0] IMPLICIT TargetInfo,
    databaseInfo            [1] IMPLICIT DatabaseInfo,
    schemaInfo              [2] IMPLICIT SchemaInfo,
    tagSetInfo              [3] IMPLICIT TagSetInfo,
    recordSyntaxInfo        [4] IMPLICIT RecordSyntaxInfo,
    attributeSetInfo        [5] IMPLICIT AttributeSetInfo,
    termListInfo            [6] IMPLICIT TermListInfo,
    extendedServicesInfo    [7] IMPLICIT ExtendedServicesInfo,
    attributeDetails        [8] IMPLICIT AttributeDetails,
    termListDetails         [9] IMPLICIT TermListDetails,
    elementSetDetails       [10] IMPLICIT ElementSetDetails,
    retrievalRecordDetails  [11] IMPLICIT RetrievalRecordDetails,
    sortDetails             [12] IMPLICIT SortDetails,
    processing              [13] IMPLICIT ProcessingInformation,
    variants                [14] IMPLICIT VariantSetInfo,
    units                   [15] IMPLICIT UnitInfo,
    categoryList            [100] IMPLICIT CategoryList
}
-- See Comment 1

TargetInfo ::= SEQUENCE {
    commonInfo          [0] IMPLICIT CommonInfo OPTIONAL,
    -- Key elements follow:
    name                [1] IMPLICIT InternationalString,
    -- See comment 2
    -- Non-key brief elements follow:
    recent-news         [2] IMPLICIT HumanString OPTIONAL,
    icon                [3] IMPLICIT IconObject OPTIONAL,
    -- Element set name “brief-1' is defined for use when client wants icon to be omitted;
    -- otherwise ‘brief-1' is identical to ‘brief’.
    namedResultSets     [4] IMPLICIT BOOLEAN,
    multipleDBsearch    [5] IMPLICIT BOOLEAN,
    maxResultSets       [6] IMPLICIT INTEGER OPTIONAL,
    maxResultSize       [7] IMPLICIT INTEGER OPTIONAL,
    maxTerms            [8] IMPLICIT INTEGER OPTIONAL,
    timeoutInterval     [9] IMPLICIT IntUnit OPTIONAL,
    welcomeMessage      [10] IMPLICIT HumanString OPTIONAL,
    -- Non-brief elements follow:
    -- 'description' esn retrieves the following two (as well as brief):
    contactInfo         [11] IMPLICIT ContactInfo OPTIONAL,
    description         [12] IMPLICIT HumanString OPTIONAL,
    nicknames           [13] IMPLICIT SEQUENCE OF InternationalString OPTIONAL,
    usage-restrictions  [14] IMPLICIT HumanString OPTIONAL,
    paymentAddr         [15] IMPLICIT HumanString OPTIONAL,
    hours               [16] IMPLICIT HumanString OPTIONAL,
    dbCombinations      [17] IMPLICIT SEQUENCE OF DatabaseList OPTIONAL,
    addresses           [18] IMPLICIT SEQUENCE OF NetworkAddress OPTIONAL,
    languages           [101] IMPLICIT SEQUENCE OF InternationalString OPTIONAL,
    -- Languages supported for message strings. Each is a three-character language code from Z39.53-1994.
    -- characterSets             [102]
    -- This tag reserved for "character sets supported for name and message strings"
    -- commonAccessInfo elements list objects the server supports.
    -- All objects listed in AccessInfo for any individual database should also be listed here.
    commonAccessInfo                     [19] IMPLICIT AccessInfo OPTIONAL
}

DatabaseInfo ::= SEQUENCE {
    -- A server may provide "virtual databases" that are combinations of individual database.
    -- These databases are indicated by the presence of subDbs in the combination database's
    -- DatabaseDescription.
    commonInfo              [0] IMPLICIT CommonInfo OPTIONAL,
    -- Key elements follow:
    name                    [1] IMPLICIT DatabaseName,
    -- Non-key brief elements follow:
    explainDatabase         [2] IMPLICIT NULL OPTIONAL,
    -- See comment 3
    nicknames               [3] IMPLICIT SEQUENCE OF DatabaseName OPTIONAL,
    icon                    [4] IMPLICIT IconObject OPTIONAL,
    -- Element set name “brief-1' is defined for use when client wants icon to be omitted;
    -- otherwise ‘brief-1' is identical to ‘brief’
    user-fee                [5] IMPLICIT BOOLEAN,
    available               [6] IMPLICIT BOOLEAN,
    titleString             [7] IMPLICIT HumanString OPTIONAL,
    -- Non-brief elements follow:
    keywords                [8] IMPLICIT SEQUENCE OF HumanString OPTIONAL,
    description             [9] IMPLICIT HumanString OPTIONAL,
    associatedDbs           [10] IMPLICIT DatabaseList OPTIONAL,
    -- Databases that may be searched in combination with this one
    subDbs                  [11] IMPLICIT DatabaseList OPTIONAL,
    -- When present, this database is a composite representing the combined databases 'subDbs'.
    -- The individual subDbs are also available
    disclaimers             [12] IMPLICIT HumanString OPTIONAL,
    news                    [13] IMPLICIT HumanString OPTIONAL,
    recordCount             [14] CHOICE {
        actualNumber            [0] IMPLICIT INTEGER,
        approxNumber            [1] IMPLICIT INTEGER
    } OPTIONAL,
    defaultOrder            [15] IMPLICIT HumanString OPTIONAL,
    avRecordSize            [16] IMPLICIT INTEGER OPTIONAL,
    maxRecordSize           [17] IMPLICIT INTEGER OPTIONAL,
    hours                   [18] IMPLICIT HumanString OPTIONAL,
    bestTime                [19] IMPLICIT HumanString OPTIONAL,
    lastUpdate              [20] IMPLICIT GeneralizedTime OPTIONAL,
    updateInterval          [21] IMPLICIT IntUnit OPTIONAL,
    coverage                [22] IMPLICIT HumanString OPTIONAL,
    proprietary             [23] IMPLICIT BOOLEAN OPTIONAL,
        -- mandatory in full record
    copyrightText           [24] IMPLICIT HumanString OPTIONAL,
    copyrightNotice         [25] IMPLICIT HumanString OPTIONAL,
    producerContactInfo     [26] IMPLICIT ContactInfo OPTIONAL,
    supplierContactInfo     [27] IMPLICIT ContactInfo OPTIONAL,
    submissionContactInfo   [28] IMPLICIT ContactInfo OPTIONAL,
    -- accessInfo lists items connected with the database.
    -- All listed items should be in the server's AccessInfo.
    accessInfo              [29] IMPLICIT AccessInfo OPTIONAL
}

SchemaInfo ::= SEQUENCE {
    commonInfo      [0] IMPLICIT CommonInfo OPTIONAL,
    -- Key elements follow:
    schema          [1] IMPLICIT OBJECT IDENTIFIER,
    -- Non-key brief elements follow:
    name            [2] IMPLICIT InternationalString,
    -- Non-brief elements follow:
    description     [3] IMPLICIT HumanString OPTIONAL,
    tagTypeMapping  [4] IMPLICIT SEQUENCE OF SEQUENCE {
        tagType         [0] IMPLICIT INTEGER,
        tagSet          [1] IMPLICIT OBJECT IDENTIFIER OPTIONAL,
        -- If tagSet is omitted, then this tagType is for a tagSet
        -- locally defined within the schema that cannot be referenced by another schema.
        defaultTagType  [2] IMPLICIT NULL OPTIONAL
    } OPTIONAL,
    recordStructure [5] IMPLICIT SEQUENCE OF ElementInfo OPTIONAL
}

-- ElementInfo referenced in SchemaInfo and RecordSyntaxInfo
ElementInfo ::= SEQUENCE {
    elementName     [1] IMPLICIT InternationalString,
    elementTagPath  [2] IMPLICIT Path,
    dataType        [3] ElementDataType OPTIONAL,
    -- If omitted, not specified
    required        [4] IMPLICIT BOOLEAN,
    repeatable      [5] IMPLICIT BOOLEAN,
    description     [6] IMPLICIT HumanString OPTIONAL
}

-- Path is referenced by ElementInfo as well as PerElementDetails
Path ::= SEQUENCE OF SEQUENCE {
    tagType     [1] IMPLICIT INTEGER,
    tagValue    [2] StringOrNumeric
}

ElementDataType ::= CHOICE {
    primitive  [0] IMPLICIT PrimitiveDataType,
    structured [1] IMPLICIT SEQUENCE OF ElementInfo
}

PrimitiveDataType ::= INTEGER {
    octetString    (0),
    numeric        (1),
    date           (2),
    external       (3),
    string         (4),
    trueOrFalse    (5),
    oid            (6),
    intUnit        (7),
    empty          (8),
    noneOfTheAbove (100) -- See 'description'
}

TagSetInfo ::= SEQUENCE {
    commonInfo  [0] IMPLICIT CommonInfo OPTIONAL,
    -- Key elements follow:
    tagSet      [1] IMPLICIT OBJECT IDENTIFIER,
    -- Non-key brief elements follow:
    name        [2] IMPLICIT InternationalString,
    -- Non-brief elements follow:
    description [3] IMPLICIT HumanString OPTIONAL,
    elements    [4] IMPLICIT SEQUENCE OF SEQUENCE {
        elementname     [1] IMPLICIT InternationalString,
        nicknames       [2] IMPLICIT SEQUENCE OF InternationalString OPTIONAL,
        elementTag      [3] StringOrNumeric,
        description     [4] IMPLICIT HumanString OPTIONAL,
        dataType        [5] PrimitiveDataType OPTIONAL,
        -- If the data type is expected to be structured,
        -- that is described in the schema info, and datatype is omitted here.
        otherTagInfo    OtherInformation OPTIONAL
    } OPTIONAL
}

RecordSyntaxInfo ::= SEQUENCE {
    commonInfo          [0] IMPLICIT CommonInfo OPTIONAL,
    -- Key elements follow:
    recordSyntax        [1] IMPLICIT OBJECT IDENTIFIER,
    -- Non-key brief elements follow:
    name                [2] IMPLICIT InternationalString,
    -- Non-brief elements follow:
    transferSyntaxes    [3] IMPLICIT SEQUENCE OF OBJECT IDENTIFIER OPTIONAL,
    description         [4] IMPLICIT HumanString OPTIONAL,
    asn1Module          [5] IMPLICIT InternationalString OPTIONAL,
    abstractStructure   [6] IMPLICIT SEQUENCE OF ElementInfo OPTIONAL
    -- Omitting abstractStructure only means server isn't using Explain
    -- to describe the structure, not that there is no structure
}

AttributeSetInfo ::= SEQUENCE {
    commonInfo      [0] IMPLICIT CommonInfo OPTIONAL,
    -- Key elements follow:
    attributeSet    [1] IMPLICIT AttributeSetId,
    -- Non-key brief elements follow:
    name            [2] IMPLICIT InternationalString,
    -- Non-brief elements follow:
    attributes      [3] IMPLICIT SEQUENCE OF AttributeType OPTIONAL,
    -- Mandatory in full record
    description     [4] IMPLICIT HumanString OPTIONAL
}

-- AttributeType referenced in AttributeSetInfo
AttributeType ::= SEQUENCE {
    name            [0] IMPLICIT InternationalString OPTIONAL,
    description     [1] IMPLICIT HumanString OPTIONAL,
    attributeType   [2] IMPLICIT INTEGER,
    attributeValues [3] IMPLICIT SEQUENCE OF AttributeDescription
}

AttributeDescription ::= SEQUENCE {
    name                    [0] IMPLICIT InternationalString OPTIONAL,
    description             [1] IMPLICIT HumanString OPTIONAL,
    attributeValue          [2] StringOrNumeric,
    equivalentAttributes    [3] IMPLICIT SEQUENCE OF StringOrNumeric OPTIONAL
    -- See comment 4
}

TermListInfo ::= SEQUENCE {
    commonInfo      [0] IMPLICIT CommonInfo OPTIONAL,
    -- Key elements follow:
    databaseName    [1] IMPLICIT DatabaseName,
    -- Non-key brief elements follow:
    termLists       [2] IMPLICIT SEQUENCE OF SEQUENCE {
        name            [1] IMPLICIT InternationalString,
        title           [2] IMPLICIT HumanString OPTIONAL,
        -- see comment 5
        searchCost      [3] IMPLICIT INTEGER {
            -- see comment 6
            optimized              (0),
            normal                 (1),
            expensive              (2),
            filter                 (3)
        } OPTIONAL,
        scanable        [4] IMPLICIT BOOLEAN,
        -- 'true' means this list can be scanned
        -- see comment 7
        broader         [5] IMPLICIT SEQUENCE OF InternationalString OPTIONAL,
        narrower        [6] IMPLICIT SEQUENCE OF InternationalString OPTIONAL
        -- Broader and narrower list alternative term lists related to this one.
        -- The term lists so listed should also be in this termLists structure.
    }
    -- No non-brief elements
}

ExtendedServicesInfo ::= SEQUENCE {
    commonInfo          [0] IMPLICIT CommonInfo OPTIONAL,
    -- Key elements follow:
    type                [1] IMPLICIT OBJECT IDENTIFIER,
    -- Non-key brief elements follow:
    name                [2] IMPLICIT InternationalString OPTIONAL,
    -- Should be supplied if privateType is 'true'
    privateType         [3] IMPLICIT BOOLEAN,
    restrictionsApply   [5] IMPLICIT BOOLEAN, -- if 'true' see 'description'
    feeApply            [6] IMPLICIT BOOLEAN, -- if 'true' see 'description'
    available           [7] IMPLICIT BOOLEAN,
    retentionSupported  [8] IMPLICIT BOOLEAN,
    waitAction          [9] IMPLICIT INTEGER {
        waitSupported       (1),
        waitAlways          (2),
        waitNotSupported    (3),
        depends             (4),
        notSaying           (5)
    },
    -- Non-brief elements follow:
    -- To get brief plus 'description' use esn 'description'
    description         [10] IMPLICIT HumanString OPTIONAL,
    -- To get above elements and 'specificExplain' use esn 'specificExplain'
    specificExplain     [11] IMPLICIT EXTERNAL OPTIONAL,
    -- Use oid of specific ES, and select choice [3] 'explain'.
    -- Format to be developed in conjunction with the specific ES definition.
    -- To get all elements except 'specificExplain', use esn 'asn'
    esASN               [12] IMPLICIT InternationalString OPTIONAL
    -- The ASN.1 for this ES
}

-- Detail records
-- See comment 8
AttributeDetails ::= SEQUENCE {
    commonInfo              [0] IMPLICIT CommonInfo OPTIONAL,
    -- Key elements follow:
    databaseName            [1] IMPLICIT DatabaseName,
    -- Non-brief elements follow:
    attributesBySet         [2] IMPLICIT SEQUENCE OF AttributeSetDetails OPTIONAL,
    -- Mandatory in full record
    attributeCombinations   [3] IMPLICIT AttributeCombinations OPTIONAL
}

-- AttributeSetDetails referenced by AttributeDetails
AttributeSetDetails ::= SEQUENCE {
    attributeSet        [0] IMPLICIT AttributeSetId,
    attributesByType    [1] IMPLICIT SEQUENCE OF AttributeTypeDetails
}

AttributeTypeDetails ::= SEQUENCE {
    attributeType       [0] IMPLICIT INTEGER,
    defaultIfOmitted    [1] IMPLICIT OmittedAttributeInterpretation OPTIONAL,
    attributeValues     [2] IMPLICIT SEQUENCE OF AttributeValue OPTIONAL
}

-- If no attributeValues are supplied, all values of this type are fully supported,
-- and the descriptions in AttributeSetInfo are adequate.

OmittedAttributeInterpretation ::= SEQUENCE {
    defaultValue        [0] StringOrNumeric OPTIONAL,
    -- A default value is listed if that's how the server works
    defaultDescription  [1] IMPLICIT HumanString OPTIONAL
}

-- See comment 9
AttributeValue ::= SEQUENCE {
    value           [0] StringOrNumeric,
    description     [1] IMPLICIT HumanString OPTIONAL,
    subAttributes   [2] IMPLICIT SEQUENCE OF StringOrNumeric OPTIONAL,
    superAttributes [3] IMPLICIT SEQUENCE OF StringOrNumeric OPTIONAL,
    partialSupport  [4] IMPLICIT NULL OPTIONAL
}

-- See comment 10
TermListDetails ::= SEQUENCE { -- one for each termList in TermListInfo
    commonInfo              [0] IMPLICIT CommonInfo OPTIONAL,
    -- Key elements follow:
    termListName            [1] IMPLICIT InternationalString,
    -- Non-key elements (all non-brief) follow:
    description             [2] IMPLICIT HumanString OPTIONAL,
    attributes              [3] IMPLICIT AttributeCombinations OPTIONAL,
    -- Pattern for attributes that hit this list. Mandatory in full record
    scanInfo                [4] IMPLICIT SEQUENCE {
        maxStepSize             [0] IMPLICIT INTEGER OPTIONAL,
        collatingSequence       [1] IMPLICIT HumanString OPTIONAL,
        increasing              [2] IMPLICIT BOOLEAN OPTIONAL
    } OPTIONAL,
    -- Occurs only if list is scanable.
    -- If list is scanable and if scanInfo is omitted, server doesn't consider these important.
    estNumberTerms          [5] IMPLICIT INTEGER OPTIONAL,
    sampleTerms             [6] IMPLICIT SEQUENCE OF Term OPTIONAL
}

ElementSetDetails ::= SEQUENCE {
    -- see comment 11
    commonInfo          [0] IMPLICIT CommonInfo OPTIONAL,
    -- Key elements follow:
    databaseName        [1] IMPLICIT DatabaseName,
    elementSetName      [2] IMPLICIT ElementSetName,
    recordSyntax        [3] IMPLICIT OBJECT IDENTIFIER,
    -- Non-key Brief elements follow:
    schema              [4] IMPLICIT OBJECT IDENTIFIER,
    -- Non-brief elements follow:
    description         [5] IMPLICIT HumanString OPTIONAL,
    detailsPerElement   [6] IMPLICIT SEQUENCE OF PerElementDetails OPTIONAL
    -- mandatory in full record
}

RetrievalRecordDetails ::= SEQUENCE {
    commonInfo          [0] IMPLICIT CommonInfo OPTIONAL,
    -- Key elements follow:
    databaseName        [1] IMPLICIT DatabaseName,
    schema              [2] IMPLICIT OBJECT IDENTIFIER,
    recordSyntax        [3] IMPLICIT OBJECT IDENTIFIER,
    -- Non-brief elements follow:
    description         [4] IMPLICIT HumanString OPTIONAL,
    detailsPerElement   [5] IMPLICIT SEQUENCE OF PerElementDetails OPTIONAL
    -- Mandatory in full record
}

-- PerElementDetails is referenced in RetrievalRecordDetails and ElementSetDetails.
PerElementDetails ::= SEQUENCE {
    name            [0] IMPLICIT InternationalString OPTIONAL,
    -- If the name is omitted, the record syntax's name for this element is appropriate.
    recordTag       [1] IMPLICIT RecordTag OPTIONAL,
    -- The record tag may be omitted if tags are inappropriate
    -- for the record syntax, or if the client can be expected to know it for some other reason.
    schemaTags      [2] IMPLICIT SEQUENCE OF Path OPTIONAL,
    -- The information from the listed schema elements is combined in some way to produce the data sent in the
    -- listed record tag. The 'contents' element below may describe the logic used.
    maxSize         [3] IMPLICIT INTEGER OPTIONAL,
    minSize         [4] IMPLICIT INTEGER OPTIONAL,
    avgSize         [5] IMPLICIT INTEGER OPTIONAL,
    fixedSize       [6] IMPLICIT INTEGER OPTIONAL,
    repeatable      [8] IMPLICIT BOOLEAN,
    required        [9] IMPLICIT BOOLEAN,
    -- 'required' really means that server will always supply the element
    description     [12] IMPLICIT HumanString OPTIONAL,
    contents        [13] IMPLICIT HumanString OPTIONAL,
    billingInfo     [14] IMPLICIT HumanString OPTIONAL,
    restrictions    [15] IMPLICIT HumanString OPTIONAL,
    alternateNames  [16] IMPLICIT SEQUENCE OF InternationalString OPTIONAL,
    genericNames    [17] IMPLICIT SEQUENCE OF InternationalString OPTIONAL,
    searchAccess    [18] IMPLICIT AttributeCombinations OPTIONAL
}

-- RecordTag referenced in PerElementDetails above
RecordTag ::= SEQUENCE {
    qualifier       [0] StringOrNumeric OPTIONAL,
    -- e.g. tag set for GRS-1
    tagValue        [1] StringOrNumeric
}

SortDetails ::= SEQUENCE {
    commonInfo      [0] IMPLICIT CommonInfo OPTIONAL,
    -- Key elements follow:
    databaseName    [1] IMPLICIT DatabaseName,
    -- No non-key brief elements
    -- Non-brief elements follow:
    sortKeys        [2] IMPLICIT SEQUENCE OF SortKeyDetails OPTIONAL
    -- Mandatory in full record
}

SortKeyDetails ::= SEQUENCE {
    description             [0] IMPLICIT HumanString OPTIONAL,
    elementSpecifications   [1] IMPLICIT SEQUENCE OF Specification OPTIONAL,
    -- Each specification is a way of specifying this same sort key
    attributeSpecifications [2] IMPLICIT AttributeCombinations OPTIONAL,
    -- Each combination is a way of specifying this same sort key
    sortType                [3] CHOICE {
        character   [0] IMPLICIT NULL,
        numeric     [1] IMPLICIT NULL,
        structured  [2] IMPLICIT HumanString
    } OPTIONAL,
    caseSensitivity         [4] IMPLICIT INTEGER {
        always      (0),       -- always case-sensitive
        never       (1),     -- never case-sensitive
        default-yes (2),     -- case-sensitivity is as specified on request,
        -- and if not specified, case-sensitive
        default-no  (3)
    } OPTIONAL -- case-sensitivity is as specified on request,
    -- and if not specified, not case-sensitive
}

ProcessingInformation ::= SEQUENCE {
    commonInfo          [0] IMPLICIT CommonInfo OPTIONAL,
    -- Key elements follow:
    databaseName        [1] IMPLICIT DatabaseName,

    processingContext   [2] IMPLICIT INTEGER {
        access              (0),     -- e.g. choosing databases
        search              (1),     -- e.g. "search strategies" or search
        -- forms
        retrieval           (2),     -- e.g. recommended element
        -- combinations
        record-presentation (3),     -- display of retrieved records
        record-handling     (4)      -- handling (e.g. saving) of retrieved
    -- records
    },
    name                [3] IMPLICIT InternationalString,
    oid                 [4] IMPLICIT OBJECT IDENTIFIER,
    -- No non-key brief elements
    -- Non-brief elements follow:
    description         [5] IMPLICIT HumanString OPTIONAL,
    -- Use element set name 'description' to retrieve all except instructions.
    instructions        [6] IMPLICIT EXTERNAL OPTIONAL
    -- mandatory in full record
}

VariantSetInfo ::= SEQUENCE {
    -- SEE COMMENT 12
    commonInfo  [0] IMPLICIT CommonInfo OPTIONAL,
    -- Key elements follow:
    variantSet  [1] IMPLICIT OBJECT IDENTIFIER,
    -- Non-key brief elements follow:
    name        [2] IMPLICIT InternationalString,
    -- Non-brief elements follow:
    variants    [3] IMPLICIT SEQUENCE OF VariantClass OPTIONAL
    -- Mandatory in full record
}

-- Subsidiary structures for VariantSetInfo
VariantClass ::= SEQUENCE {
    name            [0] IMPLICIT InternationalString OPTIONAL,
    description     [1] IMPLICIT HumanString OPTIONAL,
    variantClass    [2] IMPLICIT INTEGER,
    variantTypes    [3] IMPLICIT SEQUENCE OF VariantType
}

VariantType ::= SEQUENCE {
    name            [0] IMPLICIT InternationalString OPTIONAL,
    description     [1] IMPLICIT HumanString OPTIONAL,
    variantType     [2] IMPLICIT INTEGER,
    variantValue    [3] IMPLICIT VariantValue OPTIONAL
}

VariantValue ::= SEQUENCE {
    dataType    [0] PrimitiveDataType,
    values      [1] ValueSet OPTIONAL
}

ValueSet ::= CHOICE {
    range       [0] IMPLICIT ValueRange,
    enumerated  [1] IMPLICIT SEQUENCE OF ValueDescription
}

ValueRange ::= SEQUENCE {
    -- At last one the following must be supplied, both may be supplied.
    lower   [0] ValueDescription OPTIONAL,
    upper   [1] ValueDescription OPTIONAL
}

ValueDescription ::= CHOICE {
    integer         INTEGER,
    string          InternationalString,
    octets          OCTET STRING,
    oid             OBJECT IDENTIFIER,
    unit            [1] IMPLICIT Unit,
    valueAndUnit    [2] IMPLICIT IntUnit
    -- oid and unit can't be used in a ValueRange
}

UnitInfo ::= SEQUENCE {
    commonInfo  [0] IMPLICIT CommonInfo OPTIONAL,
    -- Key elements follow:
    unitSystem  [1] IMPLICIT InternationalString OPTIONAL,
    -- Changed to OPTIONAL in 2001 version as result of defect report
    -- No non-key brief elements
    -- Non-brief elements follow:
    description [2] IMPLICIT HumanString OPTIONAL,
    units       [3] IMPLICIT SEQUENCE OF UnitType OPTIONAL
    -- Mandatory in full record
}

-- Subsidiary structures for UnitInfo
UnitType ::= SEQUENCE {
    name        [0] IMPLICIT InternationalString OPTIONAL,
    description [1] IMPLICIT HumanString OPTIONAL,
    unitType    [2] StringOrNumeric,
    units       [3] IMPLICIT SEQUENCE OF Units
}

Units ::= SEQUENCE {
    name        [0] IMPLICIT InternationalString OPTIONAL,
    description [1] IMPLICIT HumanString OPTIONAL,
    unit        [2] StringOrNumeric
}

CategoryList ::= SEQUENCE {
    commonInfo  [0] IMPLICIT CommonInfo OPTIONAL,
    -- Only one record expected per Explain database. All elements appear in brief presentation
    categories  [1] IMPLICIT SEQUENCE OF CategoryInfo
}

CategoryInfo ::= SEQUENCE {
    category            [1] IMPLICIT InternationalString,
    originalCategory    [2] IMPLICIT InternationalString OPTIONAL,
    description         [3] IMPLICIT HumanString OPTIONAL,
    asn1Module          [4] IMPLICIT InternationalString OPTIONAL
}

-- Subsidiary definitions
CommonInfo ::= SEQUENCE {
    dateAdded               [0] IMPLICIT GeneralizedTime OPTIONAL,
    dateChanged             [1] IMPLICIT GeneralizedTime OPTIONAL,
    expiry                  [2] IMPLICIT GeneralizedTime OPTIONAL,
    humanString-Language    [3] IMPLICIT LanguageCode OPTIONAL,
    -- Following not to occur for brief:
    otherInfo               OtherInformation OPTIONAL
}

HumanString ::= SEQUENCE OF SEQUENCE {
    language    [0] IMPLICIT LanguageCode OPTIONAL,
    text        [1] IMPLICIT InternationalString}

IconObject ::= SEQUENCE OF SEQUENCE {
    -- Note that the "SEQUENCE OF" is to allow alternative
    -- representations of the same Icon; it is not intended to allow multiple icons.
    bodyType    [1] CHOICE {
        ianaType    [1] IMPLICIT InternationalString,
        z3950type   [2] IMPLICIT InternationalString,
        otherType   [3] IMPLICIT InternationalString},
    content     [2] IMPLICIT OCTET STRING
}

LanguageCode ::= InternationalString -- from ANSI/NISO Z39.53-1994

ContactInfo ::= SEQUENCE {
    name        [0] IMPLICIT InternationalString OPTIONAL,
    description [1] IMPLICIT HumanString OPTIONAL,
    address     [2] IMPLICIT HumanString OPTIONAL,
    email       [3] IMPLICIT InternationalString OPTIONAL,
    phone       [4] IMPLICIT InternationalString OPTIONAL
}

NetworkAddress ::= CHOICE {
    internetAddress [0] IMPLICIT SEQUENCE {
        hostAddress     [0] IMPLICIT InternationalString,
        port            [1] IMPLICIT INTEGER},
    depricated      [1] IMPLICIT SEQUENCE {
        depricated0       [0] IMPLICIT InternationalString,
        depricated1       [1] IMPLICIT InternationalString OPTIONAL,
        depricated2       [2] IMPLICIT InternationalString OPTIONAL,
        depricated3       [3] IMPLICIT InternationalString
    },
    -- This element depricated in Z39.50-2003
    other           [2] IMPLICIT SEQUENCE {
        type    [0] IMPLICIT InternationalString,
        address [1] IMPLICIT InternationalString
    }
}

AccessInfo ::= SEQUENCE {
    -- see comment 13
    queryTypesSupported [0] IMPLICIT SEQUENCE OF QueryTypeDetails OPTIONAL,
    diagnosticsSets     [1] IMPLICIT SEQUENCE OF OBJECT IDENTIFIER OPTIONAL,
    attributeSetIds     [2] IMPLICIT SEQUENCE OF AttributeSetId OPTIONAL,
    schemas             [3] IMPLICIT SEQUENCE OF OBJECT IDENTIFIER OPTIONAL,
    recordSyntaxes      [4] IMPLICIT SEQUENCE OF OBJECT IDENTIFIER OPTIONAL,
    resourceChallenges  [5] IMPLICIT SEQUENCE OF OBJECT IDENTIFIER OPTIONAL,
    restrictedAccess    [6] IMPLICIT AccessRestrictions OPTIONAL,
    costInfo            [8] IMPLICIT Costs OPTIONAL,
    variantSets         [9] IMPLICIT SEQUENCE OF OBJECT IDENTIFIER OPTIONAL,
    elementSetNames     [10] IMPLICIT SEQUENCE OF ElementSetName OPTIONAL,
    unitSystems         [11] IMPLICIT SEQUENCE OF InternationalString
}

-- Begin auxiliary definitions for AccessInfo
-- Begin Query Details
QueryTypeDetails ::= CHOICE {
    private     [0] IMPLICIT PrivateCapabilities,
    rpn         [1] IMPLICIT RpnCapabilities,
    iso8777     [2] IMPLICIT Iso8777Capabilities,
    z39-58      [100] IMPLICIT HumanString,
    erpn        [101] IMPLICIT RpnCapabilities,
    rankedList  [102] IMPLICIT HumanString
}

PrivateCapabilities ::= SEQUENCE {
    operators       [0] IMPLICIT SEQUENCE OF SEQUENCE {
        operator         [0] IMPLICIT InternationalString,
        description      [1] IMPLICIT HumanString OPTIONAL
    } OPTIONAL,
    searchKeys      [1] IMPLICIT SEQUENCE OF SearchKey OPTIONAL,
    -- field names that can be searched
    description     [2] IMPLICIT SEQUENCE OF HumanString OPTIONAL
}

RpnCapabilities ::= SEQUENCE {
    operators                   [0] IMPLICIT SEQUENCE OF INTEGER {
        and     (0),
        or      (1),
        and-not (2),
        prox    (3)
    } OPTIONAL,
    -- Omitted means all operators are supported
    resultSetAsOperandSupported [1] IMPLICIT BOOLEAN,
    restrictionOperandSupported [2] IMPLICIT BOOLEAN,
    proximity                   [3] IMPLICIT ProximitySupport OPTIONAL
}

Iso8777Capabilities ::= SEQUENCE {
    searchKeys      [0] IMPLICIT SEQUENCE OF SearchKey,
    -- field names that may be searched
    restrictions    [1] IMPLICIT HumanString OPTIONAL
    -- Omitted means supported, not specifying units
}

ProximitySupport ::= SEQUENCE {
    anySupport      [0] IMPLICIT BOOLEAN,
    -- 'false' means no proximity support, in which case unitsSupported not supplied
    unitsSupported  [1] IMPLICIT SEQUENCE OF CHOICE {
        known           [1] IMPLICIT INTEGER,
        -- Values from KnownProximityUnit
        private         [2] IMPLICIT SEQUENCE {
            unit            [0] IMPLICIT INTEGER,
            description     [1] HumanString OPTIONAL
        }
    } OPTIONAL
}

SearchKey ::= SEQUENCE {
    searchKey   [0] IMPLICIT InternationalString,
    description [1] IMPLICIT HumanString OPTIONAL
}

-- End Query details

AccessRestrictions ::= SEQUENCE OF SEQUENCE {
    accessType              [0] INTEGER {
        any                        (0),
        search                     (1),
        present                    (2),
        specific-elements          (3),
        extended-services          (4),
        by-database                (5)
    },
    accessText              [1] IMPLICIT HumanString OPTIONAL,
    accessChallenges        [2] IMPLICIT SEQUENCE OF OBJECT IDENTIFIER OPTIONAL
}

Costs ::= SEQUENCE {
    connectCharge   [0] IMPLICIT Charge OPTIONAL, -- Per-connection charge
    connectTime     [1] IMPLICIT Charge OPTIONAL, -- Time-based charge
    displayCharge   [2] IMPLICIT Charge OPTIONAL, -- Per-record charge
    searchCharge    [3] IMPLICIT Charge OPTIONAL, -- Per-search charge
    subscriptCharge [4] IMPLICIT Charge OPTIONAL, -- Subscription charges
    otherCharges    [5] IMPLICIT SEQUENCE OF SEQUENCE {
        forWhat         [1] IMPLICIT HumanString,
        charge          [2] IMPLICIT Charge
    } OPTIONAL
}

Charge ::= SEQUENCE {
    cost    [1] IMPLICIT IntUnit,
    perWhat [2] IMPLICIT Unit OPTIONAL,
    -- e.g. "second," "minute," "line," "record"...
    text    [3] IMPLICIT HumanString OPTIONAL
}

-- End Auxiliary definitions for AccessInfo

DatabaseList ::= SEQUENCE OF DatabaseName

AttributeCombinations ::= SEQUENCE {
    defaultAttributeSet [0] IMPLICIT AttributeSetId,
    -- Default for the combinations.
    -- Also probably a good choice for the default in searches, but that isn't required.
    legalCombinations   [1] IMPLICIT SEQUENCE OF AttributeCombination
}

AttributeCombination ::= SEQUENCE OF AttributeOccurrence

-- An AttributeCombination is a pattern for legal combination of attributes

AttributeOccurrence ::= SEQUENCE {
    -- An AttributeOccurrence lists the legal values for a specific attribute type in a combination
    attributeSet    [0] IMPLICIT AttributeSetId OPTIONAL,
    attributeType   [1] IMPLICIT INTEGER,
    mustBeSupplied  [2] IMPLICIT NULL OPTIONAL,
    attributeValues CHOICE {
        any-or-none     [3] IMPLICIT NULL,
                -- All supported values are OK
        specific        [4] IMPLICIT SEQUENCE OF StringOrNumeric
        -- Only these values allowed
    }
}

END
