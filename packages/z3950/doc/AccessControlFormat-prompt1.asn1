AccessControlFormat-prompt-1
{z39-50-accessControl prompt-1(1)}
DEFINITIONS ::=
BEGIN
IMPORTS

    InternationalString, DiagRec
        FROM Z39-50-APDU-2001
    ;

PromptObject ::= CHOICE{
    challenge   [1] IMPLICIT Challenge,
    response    [2] IMPLICIT Response
}

Challenge ::= SEQUENCE OF SEQUENCE {
    promptId            [1] PromptId,
    -- See comment 1
    defaultResponse     [2] IMPLICIT InternationalString OPTIONAL,
    promptInfo          [3] CHOICE{
    character               [1] IMPLICIT InternationalString,
    encrypted               [2] IMPLICIT Encryption} OPTIONAL,
    -- See comment 2
    regExpr             [4] IMPLICIT InternationalString OPTIONAL,
    -- See comment 3
    responseRequired    [5] IMPLICIT NULL OPTIONAL,
    allowedValues       [6] IMPLICIT SEQUENCE OF InternationalString OPTIONAL,
    --e.g. promptId="Desired color"; allowed = 'red', 'blue','Green'
    shouldSave          [7] IMPLICIT NULL OPTIONAL,
    -- See comment 4
    dataType            [8] IMPLICIT INTEGER {
        integer           (1),
        date              (2),
        float             (3),
        alphaNumeric      (4),
        url-urn           (5),
        boolean           (6)
    } OPTIONAL,
    -- See comment 5
    diagnostic          [9] IMPLICIT EXTERNAL OPTIONAL
    -- Intended for repeat requests when there is an error
    -- the client should report to the user from previous attempt.
}

Response ::= SEQUENCE OF SEQUENCE {
    promptId        [1] PromptId,
    -- See comment 6
    promptResponse  [2] CHOICE{
        string          [1] IMPLICIT InternationalString,
        accept          [2] IMPLICIT BOOLEAN,
        acknowledge     [3] IMPLICIT NULL,
        diagnostic      [4] DiagRec,
        encrypted       [5] IMPLICIT Encryption
    }
}

PromptId ::= CHOICE {
    enummeratedPrompt   [1] IMPLICIT SEQUENCE {
        type        [1] IMPLICIT INTEGER {
            groupId           (0),
            userId            (1),
            password          (2),
            newPassword       (3),
            copyright         (4),
            -- See comment 7
            sessionId         (5)
        },
    suggestedString [2] IMPLICIT InternationalString OPTIONAL},
    nonEnumeratedPrompt [2] IMPLICIT InternationalString
}

Encryption ::= SEQUENCE {
    cryptType   [1] IMPLICIT OCTET STRING OPTIONAL,
    credential  [2] IMPLICIT OCTET STRING OPTIONAL,
    -- Random number, SALT, or other factor
    data        [3] IMPLICIT OCTET STRING
}

END
