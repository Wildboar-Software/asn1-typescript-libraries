-- Module IN-CS3-SCF-CUSF-Protocol (Q.1238.7:06/2000)
-- See also ITU-T Q.1238.7 (06/2000)
-- See also the index of all ASN.1 assignments needed in this document

-- The table below lists all operation timers invoked in SCF-CUSF relationship and the value range for each timer.
-- The definitive value for each operation timer may be network specific and has to be defined by the network operator.
-- The following value range does apply for operation specific timers:
-- short:	1 - 10 seconds
--                          Table 7/Q.1238.7 - Operation timers and their value range
--	Operation Name	Timer	value range
--
--	ActivityTest	Tat	short
--	activationReceivedAndAuthorized	Tara	short
--	associationReleaseRequested	Tarr	short
--	ComponentReceived	Tcre 	short
--	ConnectAssociation	Tcoa	short
--	continueAssociation	Tcona	short
--	EventReportBCUSM	Terbce	short
--	initialAssociationDP	Tiadp	short
--	InitiateAssociation	Tia	short
--	ReleaseAssociation	Trel	short
--	requestReportBCUSMEvent	Trrbce	short
--	RequestReportUTSI	Trru	short
--	ReportUTSI	Tru 	short
--	SendSTUI	Tss 	short
--	SendComponent	Tsdc	short
-- 13.4	PACKAGES, CONTRACTS, APPLICATION CONTEXTS
--	AND ABSTRACT SYNTAXES
-- This clause specifies the operation packages, the contracts, the application contexts,
-- and the abstract syntaxes definitions used in CUSF-SCF relationship.
-- Refer to the other parts of this Recommendation for the other operation packages
-- definitions not specified in this clause.
-- Contracts:
--             cs3scfcusfDPSpecificContract
--             cs3cusfscfDPSpecificContract
--             cs3scfcusfGenericContract
--             cs3cusfscfGenericContract
--             Abstract Syntax:
-- General description for Abstract Syntax is in Q.1238.1.
-- The CUSF-SCF INAP ASEs that realize the operation packages specified as the below ASN.1 share the four abstract syntaxes:
--             cs3scfcusfDPSpecificAS,
--             cs3cusfscfDPSpecificAS,
--             cs3scfcusfGenericAS, and
--             cs3cusfscfGenericAS.
IN-CS3-SCF-CUSF-Protocol {itu-t recommendation q 1238 modules(1)
  in-cs3-scf-cusf-pkgs-contracts-acs(27) version1(0)} DEFINITIONS ::=
BEGIN

IMPORTS
  ros-InformationObjects, tc-Messages, tc-NotationExtensions, common-classes,
    ssf-scf-classes, scf-cusf-classes, ssf-scf-Protocol, ssf-scf-Operations,
    scf-cusf-Operations, id-ac-cs3scfcusfDPSpecific,
    id-ac-cs3cusfscfDPSpecific, id-ac-cs3scfcusfGeneric,
    id-ac-cs3cusfscfGeneric, id-contract-cs3scfcusfDPSpecific,
    id-contract-cs3cusfscfDPSpecific, id-contract-cs3scfcusfGeneric,
    id-contract-cs3cusfscfGeneric, id-package-cusfTDPSpecificInvocation,
    id-package-cusfTDPGenericInvocation,
    id-package-cusfDPSpecificEventHandling,
    id-package-cusfGenericEventHandling, id-package-cusfComponentHandling,
    id-package-cusfSCFInitiation, id-package-cusfContinue,
    id-package-cusfConnect, id-package-cusfRelease, id-as-cs3scfcusfDPSpecific,
    id-as-cs3cusfscfDPSpecific, id-as-cs3scfcusfGeneric,
    id-as-cs3cusfscfGeneric
    FROM IN-CS3-object-identifiers {itu-t recommendation q 1238 modules(1)
      in-cs3-object-identifiers(0) version1(0)}
  CONTRACT, OPERATION-PACKAGE, OPERATION
    FROM Remote-Operations-Information-Objects {joint-iso-itu-t
      remote-operations(4) informationObjects(5) version1(0)}
  TCMessage{}
    FROM TCAPMessages {itu-t recommendation q 773 modules(2) messages(1)
      version3(3)}
  APPLICATION-CONTEXT, dialogue-abstract-syntax
    FROM TC-Notation-Extensions {itu-t recommendation q 775 modules(2)
      notation-extension(4) version1(1)}
  COMMON-BOUNDS
    FROM IN-CS3-common-classes {itu-t recommendation q 1238 modules(1)
      in-cs3-common-classes(5) version1(0)}
  SCF-SSF-BOUNDS
    FROM IN-CS3-SSF-SCF-Classes {itu-t recommendation q 1238 modules(1)
      in-cs3-ssf-scf-classes(7) version1(0)}
  SCF-CUSF-BOUNDS, sCFCUSFBoundSet, sCFSSFBoundSetforCUSF,
    commonBoundSetforCUSF
    FROM IN-CS3-SCF-CUSF-Classes {itu-t recommendation q 1238 modules(1)
      in-cs3-scf-cusf-classes(25) version1(0)}
  activityTestPackage, uSIHandlingPackage
    FROM IN-CS3-SSF-SCF-pkgs-contracts-acs {itu-t recommendation q 1238
      modules(1) in-cs3-ssf-scf-pkgs-contracts-acs(9) version1(0)}
  activityTest, reportUTSI, requestReportUTSI, sendSTUI
    FROM IN-CS3-SSF-SCF-ops-args {itu-t recommendation q 1238 modules(1)
      in-cs3-ssf-scf-ops-args(8) version1(0)}
  activationReceivedAndAuthorized, initiateAssociation,
    associationReleaseRequested, componentReceived, releaseAssociation,
    requestReportBCUSMEvent, sendComponent, initialAssociationDP,
    connectAssociation, continueAssociation, eventReportBCUSM
    FROM IN-CS3-SCF-CUSF-Operations {itu-t recommendation q 1238 modules(1)
      in-cs3-scf-cusf-ops-args(26) version1(0)};

-- The following three definitions are local short-hand notation for convenience.
B1 ::=
  COMMON-BOUNDS -- defined in Recommendation Q.1238.1

B2 ::= SCF-SSF-BOUNDS -- defined in Recommendation Q.1238.2

B7 ::= SCF-CUSF-BOUNDS -- defined in Recommendation Q.1238.7

-- Operation package definition
-- activityTestPackage   OPERATION-PACKAGE
-- This package is described in Q.1238.2.
cusfTDPSpecificInvocationPackage OPERATION-PACKAGE ::=
{
  CONSUMER INVOKES
    {activationReceivedAndAuthorized | componentReceived |
      associationReleaseRequested}
  ID                id-package-cusfTDPSpecificInvocation
}

cusfTDPGenericInvocationPackage OPERATION-PACKAGE ::= {
  CONSUMER INVOKES  {initialAssociationDP}
  ID                id-package-cusfTDPGenericInvocation
}

cusfDPSpecificEventHandlingPackage OPERATION-PACKAGE ::=
{
  CONSUMER INVOKES  {requestReportBCUSMEvent}
  SUPPLIER INVOKES
    {componentReceived | associationReleaseRequested}
  ID                id-package-cusfDPSpecificEventHandling
}

cusfGenericEventHandlingPackage OPERATION-PACKAGE ::=
{
  CONSUMER INVOKES  {requestReportBCUSMEvent}
  SUPPLIER INVOKES  {eventReportBCUSM}
  ID                id-package-cusfGenericEventHandling
}

cusfComponentHandlingPackage OPERATION-PACKAGE ::= {
  CONSUMER INVOKES  {sendComponent}
  ID                id-package-cusfComponentHandling
}

cusfSCFInitiationPackage OPERATION-PACKAGE ::= {
  CONSUMER INVOKES  {initiateAssociation}
  ID                id-package-cusfSCFInitiation
}

cusfContinuePackage OPERATION-PACKAGE ::= {
  CONSUMER INVOKES  {continueAssociation}
  ID                id-package-cusfContinue
}

cusfConnectPackage OPERATION-PACKAGE ::= {
  CONSUMER INVOKES  {connectAssociation}
  ID                id-package-cusfConnect
}

cusfReleasePackage OPERATION-PACKAGE ::= {
  CONSUMER INVOKES  {releaseAssociation}
  ID                id-package-cusfRelease
}

-- uSIHandlingPackage OPERATION-PACKAGE
-- This package is described in Q.1238.2.
-- Contracts definition
cs3scfcusfDPSpecificContract CONTRACT ::= {
  INITIATOR CONSUMER OF
    {cusfSCFInitiationPackage |
      activityTestPackage |
      cusfDPSpecificEventHandlingPackage
      | cusfComponentHandlingPackage |
      cusfContinuePackage |
      cusfConnectPackage |
      cusfReleasePackage |
      uSIHandlingPackage}
  ID                     id-contract-cs3scfcusfDPSpecific
}

cs3cusfscfDPSpecificContract CONTRACT ::= {
  INITIATOR CONSUMER OF
    {cusfTDPSpecificInvocationPackage}
  RESPONDER CONSUMER OF
    {activityTestPackage |
      cusfDPSpecificEventHandlingPackage
      | cusfComponentHandlingPackage |
      cusfContinuePackage |
      cusfConnectPackage |
      cusfReleasePackage |
      uSIHandlingPackage}
  ID                     id-contract-cs3cusfscfDPSpecific
}

cs3scfcusfGenericContract CONTRACT ::= {
  INITIATOR CONSUMER OF
    {cusfSCFInitiationPackage |
      activityTestPackage |
      cusfGenericEventHandlingPackage |
      cusfComponentHandlingPackage |
      cusfContinuePackage |
      cusfConnectPackage |
      cusfReleasePackage |
      uSIHandlingPackage}
  ID                     id-contract-cs3scfcusfGeneric
}

cs3cusfscfGenericContract CONTRACT ::= {
  INITIATOR CONSUMER OF
    {cusfTDPGenericInvocationPackage}
  RESPONDER CONSUMER OF
    {activityTestPackage |
      cusfGenericEventHandlingPackage |
      cusfComponentHandlingPackage |
      cusfContinuePackage |
      cusfConnectPackage |
      cusfReleasePackage |
      uSIHandlingPackage}
  ID                     id-contract-cs3cusfscfGeneric
}

-- Application Contexts definition
cs3scfcusfDPSpecificAC APPLICATION-CONTEXT ::= {
  CONTRACT                  cs3scfcusfDPSpecificContract
  DIALOGUE MODE             structured
  TERMINATION               basic
  ABSTRACT SYNTAXES         {dialogue-abstract-syntax | cs3scfcusfDPSpecificAS}
  APPLICATION CONTEXT NAME  id-ac-cs3scfcusfDPSpecific
}

cs3cusf-scfDPSpecificAC APPLICATION-CONTEXT ::= {
  CONTRACT                  cs3cusfscfDPSpecificContract
  DIALOGUE MODE             structured
  TERMINATION               basic
  ABSTRACT SYNTAXES         {dialogue-abstract-syntax | cs3scfcusfDPSpecificAS}
  APPLICATION CONTEXT NAME  id-ac-cs3cusfscfDPSpecific
}

cs3scfcusfGenericAC APPLICATION-CONTEXT ::= {
  CONTRACT                  cs3scfcusfGenericContract
  DIALOGUE MODE             structured
  TERMINATION               basic
  ABSTRACT SYNTAXES         {dialogue-abstract-syntax | cs3scfcusfGenericAS}
  APPLICATION CONTEXT NAME  id-ac-cs3scfcusfGeneric
}

cs3cusf-scfGenericAC APPLICATION-CONTEXT ::= {
  CONTRACT                  cs3cusfscfGenericContract
  DIALOGUE MODE             structured
  TERMINATION               basic
  ABSTRACT SYNTAXES         {dialogue-abstract-syntax | cs3scfcusfGenericAS}
  APPLICATION CONTEXT NAME  id-ac-cs3cusfscfGeneric
}

-- Abstract Syntax definition
cs3scfcusfDPSpecificAS ABSTRACT-SYNTAX ::= {
  CS3SCFCUSFDPSpecificPDUs
  IDENTIFIED BY  id-as-cs3scfcusfDPSpecific
}

CS3SCFCUSFDPSpecificPDUs ::=
  TCMessage{{SCFCUSFDPSpecific-Invokable}, {SCFCUSFDPSpecific-Returnable}}

SCFCUSFDPSpecific-Invokable OPERATION ::=
  {initiateAssociation |
   activationReceivedAndAuthorized | activityTest |
   componentReceived |
   releaseAssociation |
   requestReportBCUSMEvent |
   sendComponent |
   associationReleaseRequested |
   continueAssociation |
   connectAssociation |
   sendSTUI |
   requestReportUTSI |
   reportUTSI}

SCFCUSFDPSpecific-Returnable OPERATION ::=
  {initiateAssociation |
   activationReceivedAndAuthorized | activityTest |
   componentReceived |
   requestReportBCUSMEvent |
   sendComponent |
   associationReleaseRequested |
   continueAssociation |
   connectAssociation |
   sendSTUI |
   requestReportUTSI}

cs3cusfscfDPSpecificAS ABSTRACT-SYNTAX ::= {
  CS3CUSFSCFDPSpecificPDUs
  IDENTIFIED BY  id-as-cs3cusfscfDPSpecific
}

CS3CUSFSCFDPSpecificPDUs ::=
  TCMessage{{CUSFSCFDPSpecific-Invokable}, {CUSFSCFDPSpecific-Returnable}}

CUSFSCFDPSpecific-Invokable OPERATION ::=
  {activationReceivedAndAuthorized | activityTest |
   componentReceived |
   releaseAssociation |
   requestReportBCUSMEvent |
   sendComponent |
   associationReleaseRequested |
   continueAssociation |
   connectAssociation |
   sendSTUI |
   requestReportUTSI |
   reportUTSI}

CUSFSCFDPSpecific-Returnable OPERATION ::=
  {activationReceivedAndAuthorized | activityTest |
   componentReceived |
   requestReportBCUSMEvent |
   sendComponent |
   associationReleaseRequested |
   continueAssociation |
   connectAssociation |
   sendSTUI |
   requestReportUTSI}

cs3scfcusfGenericAS ABSTRACT-SYNTAX ::= {
  CS3SCFCUSFGenericPDUs
  IDENTIFIED BY  id-as-cs3scfcusfGeneric
}

CS3SCFCUSFGenericPDUs ::=
  TCMessage{{SCFCUSFGeneric-Invokable}, {SCFCUSFGeneric-Returnable}}

SCFCUSFGeneric-Invokable OPERATION ::=
  {initiateAssociation |
   activityTest |
   eventReportBCUSM | releaseAssociation
   | requestReportBCUSMEvent |
   continueAssociation |
   connectAssociation |
   sendComponent |
   sendSTUI |
   requestReportUTSI |
   reportUTSI}

SCFCUSFGeneric-Returnable OPERATION ::=
  {initiateAssociation |
   activityTest |
   requestReportBCUSMEvent |
   continueAssociation |
   connectAssociation |
   sendComponent |
   sendSTUI |
   requestReportUTSI}

cs3cusfscfGenericAS ABSTRACT-SYNTAX ::= {
  CS3CUSFSCFGenericPDUs
  IDENTIFIED BY  id-as-cs3cusfscfGeneric
}

CS3CUSFSCFGenericPDUs ::=
  TCMessage{{CUSFSCFGeneric-Invokable}, {CUSFSCFGeneric-Returnable}}

CUSFSCFGeneric-Invokable OPERATION ::=
  {initialAssociationDP |
   activityTest |
   eventReportBCUSM | releaseAssociation
   | requestReportBCUSMEvent |
   continueAssociation |
   connectAssociation |
   sendComponent |
   sendSTUI |
   requestReportUTSI |
   reportUTSI}

CUSFSCFGeneric-Returnable OPERATION ::=
  {initialAssociationDP |
   activityTest |
   requestReportBCUSMEvent |
   continueAssociation |
   connectAssociation |
   sendComponent |
   sendSTUI |
   requestReportUTSI}

END

-- Generated by Asnp, the ASN.1 pretty-printer of France Telecom R&D
