-- Module IN-CS3-SCF-SRF-ops-args (Q.1238.3:06/2000)
-- See also ITU-T Q.1238.3 (06/2000)
-- See also the index of all ASN.1 assignments needed in this document

IN-CS3-SCF-SRF-ops-args {itu-t recommendation q 1238 modules(1)
  in-cs3-scf-srf-ops-args(12) version1(0)} DEFINITIONS IMPLICIT TAGS ::=
BEGIN

IMPORTS
  ros-InformationObjects, operationcodes, common-datatypes, errortypes,
    common-classes, scf-srf-classes, ssf-scf-classes, ssf-scf-datatypes,
    scf-srf-datatypes
    FROM IN-CS3-object-identifiers {itu-t recommendation q 1238 modules(1)
      in-cs3-object-identifiers(0) version1(0)}
  OPERATION
    FROM Remote-Operations-Information-Objects {joint-iso-itu-t
      remote-operations(4) informationObjects(5) version1(0)}
  opcode-playAnnouncement, opcode-promptAndCollectUserInformation,
    opcode-promptAndReceiveMessage, opcode-scriptClose, opcode-scriptEvent,
    opcode-scriptInformation, opcode-scriptRun,
    opcode-specializedResourceReport, opcode-activityTest, opcode-srfCallGap
    FROM IN-CS3-operationcodes {itu-t recommendation q 1238 modules(1)
      in-cs3-operationcodes(3) version1(0)}
  SCF-SSF-BOUNDS
    FROM IN-CS3-SSF-SCF-Classes {itu-t recommendation q 1238 modules(1)
      in-cs3-ssf-scf-classes(7) version1(0)}
  CallSegmentID, Digits, GenericNumber, LegID, ControlType, GapIndicators
    FROM IN-CS3-SSF-SCF-datatypes {itu-t recommendation q 1238 modules(1)
      in-cs3-ssf-scf-datatypes(6) version1(0)}
  InformationToSend, CollectedInfo, MailBoxID, InformationToRecord,
    Media, ReceivedStatus, RecordedMessageID, SRFGapCriteria
    FROM IN-CS3-SCF-SRF-datatypes {itu-t recommendation q 1238 modules(1)
      in-cs3-scf-srf-datatypes(10) version1(0)}
  canceled, improperCallerResponse, missingParameter, parameterOutOfRange,
    systemFailure, taskRefused, unavailableResource,
    unexpectedComponentSequence, unexpectedDataValue, unexpectedParameter,
    unknownLegID
    FROM IN-CS3-errortypes {itu-t recommendation q 1238 modules(1)
      in-cs3-errortypes(2) version1(0)}
  UISCRIPT, SupportedUIScripts, SCF-SRF-BOUNDS
    FROM IN-CS3-SCF-SRF-classes {itu-t recommendation q 1238 modules(1)
      in-cs3-scf-srf-classes(11) version1(0)}
  Extensions
    FROM IN-CS3-common-datatypes {itu-t recommendation q 1238 modules(1)
      in-cs3-common-datatypes(1) version1(0)}
  COMMON-BOUNDS
    FROM IN-CS3-common-classes {itu-t recommendation q 1238 modules(1)
      in-cs3-common-classes(5) version1(0)};

B1 ::= COMMON-BOUNDS

B2 ::= SCF-SSF-BOUNDS

B3 ::= SCF-SRF-BOUNDS

-- activityTest OPERATION
-- This operation is described in Recommendation Q.1238.2.
-- assistRequestInstruction OPERATION
-- This operation is described in Recommendation Q.1238.2.
--cancel OPERATION
-- This operation is described in Recommendation Q.1238.2.
--connectToResource OPERATION
-- This operation is described in Recommendation Q.1238.2.
--disconnectForwardConnection OPERATION
-- This operation is described in Recommendation Q.1238.2.
-- disconnectForwardConnectionWithArgument OPERATION
-- This operation is described in Recommendation Q.1238.2.
-- establishTemporaryConnection OPERATION
-- This operation is described in Recommendation Q.1238.2.
playAnnouncement OPERATION ::= {
  ARGUMENT         PlayAnnouncementArg
  RETURN RESULT    FALSE
  ERRORS
    {canceled | missingParameter | parameterOutOfRange | systemFailure |
      taskRefused | unexpectedComponentSequence | unexpectedDataValue |
      unexpectedParameter | unavailableResource | unknownLegID}
  LINKED           {specializedResourceReport}
  ALWAYS RESPONDS  FALSE
  CODE             opcode-playAnnouncement
}

-- Direction: SCF -> SRF, Timer: Tpa
-- This operation is to be used after Establish Temporary Connection (assist procedure with a second SSP)
-- or a Connect to Resource (no assist) operation. It may be used for inband interaction with an analogue user,
-- or for interaction with an ISDN user. In the former case, the SRF is usually collocated with the SSF for
-- standard tones (congestion tone ...) or standard announcements. In the latter case, the SRF is always
-- collocated with the SSF in the switch. Any error is returned to the SCF. The timer associated with this
-- operation must be of a sufficient duration to allow its linked operation to be correctly correlated.
PlayAnnouncementArg ::= SEQUENCE {
  informationToSend            [0]  InformationToSend,
  disconnectFromIPForbidden    [1]  BOOLEAN DEFAULT TRUE,
  requestAnnouncementComplete  [2]  BOOLEAN DEFAULT TRUE,
  extensions                   [3]  Extensions OPTIONAL,
  connectedParty
    CHOICE {legID          [4]  LegID,
            callSegmentID  [5]  CallSegmentID} OPTIONAL,
  ...
}

promptAndCollectUserInformation OPERATION ::= {
  ARGUMENT  PromptAndCollectUserInformationArg
  RESULT    ReceivedInformationArg
  ERRORS
    {canceled | improperCallerResponse | missingParameter | parameterOutOfRange
      | systemFailure | taskRefused | unexpectedComponentSequence |
      unavailableResource | unexpectedDataValue | unexpectedParameter}
  CODE      opcode-promptAndCollectUserInformation
}

-- Direction: SCF -> SRF, Timer: Tpc
-- This operation is used to interact with a user to collect information.
PromptAndCollectUserInformationArg ::= SEQUENCE {
  collectedInfo              [0]  CollectedInfo,
  disconnectFromIPForbidden  [1]  BOOLEAN DEFAULT TRUE,
  informationToSend          [2]  InformationToSend OPTIONAL,
  extensions                 [3]  Extensions OPTIONAL,
  callSegmentID              [4]  CallSegmentID OPTIONAL,
  ...
}

ReceivedInformationArg ::= CHOICE {
  digitsResponse  [0]  Digits,
  iA5Response     [1]  IA5String,
  modemdetected   [2]  BOOLEAN
}

promptAndReceiveMessage OPERATION ::= {
  ARGUMENT  PromptAndReceiveMessageArg
  RESULT    MessageReceivedArg
  ERRORS
    {canceled | improperCallerResponse | missingParameter | parameterOutOfRange
      | taskRefused | systemFailure | unavailableResource |
      unexpectedComponentSequence | unexpectedDataValue | unexpectedParameter}
  CODE      opcode-promptAndReceiveMessage
}

-- Direction: SCF ->SRF, Timer: Tprm
-- Used to prompt a user to store a message
PromptAndReceiveMessageArg ::= SEQUENCE {
  disconnectFromIPForbidden  [0]  BOOLEAN DEFAULT TRUE,
  informationToSend          [1]  InformationToSend OPTIONAL,
  extensions                 [3]  Extensions OPTIONAL,
  subscriberID               [4]  GenericNumber OPTIONAL,
  mailBoxID                  [5]  MailBoxID OPTIONAL,
  informationToRecord        [6]  InformationToRecord,
  media                      [7]  Media DEFAULT voiceMail,
  callSegmentID              [8]  CallSegmentID OPTIONAL,
  ...
}

MessageReceivedArg ::= SEQUENCE {
  receivedStatus        [0]  ReceivedStatus,
  recordedMessageID     [1]  RecordedMessageID OPTIONAL,
  recordedMessageUnits
    [2]  INTEGER OPTIONAL,
  extensions            [3]  Extensions OPTIONAL,
  ...
}

-- reportUTSI OPERATION
-- This operation is described in Recommendation Q.1238.2.
-- requestReportUTSI OPERATION
-- This operation is described in Recommendation Q.1238.2.
-- sendSTUI OPERATION
-- This operation is described in Recommendation Q.1238.2.
scriptClose OPERATION ::= {
  ARGUMENT         ScriptCloseArg
  RETURN RESULT    FALSE
  ERRORS
    {systemFailure | missingParameter | taskRefused | unavailableResource |
      unexpectedComponentSequence | unexpectedDataValue | unexpectedParameter}
  ALWAYS RESPONDS  FALSE
  CODE             opcode-scriptClose
}

-- Direction:SCF-> SRF. Timer :TCl
-- This operation is issued by the SCF to deallocate the resources used to perform the
-- instance of the "User Interaction" script: the context is released.
ScriptCloseArg ::= SEQUENCE {
  uIScriptId            UISCRIPT.&id({SupportedUIScripts}),
  uIScriptSpecificInfo
    [0]  UISCRIPT.&SpecificInfo({SupportedUIScripts}{@uIScriptId}) OPTIONAL,
  extensions            [1]  Extensions OPTIONAL,
  callSegmentID         [2]  CallSegmentID OPTIONAL,
  ...
}

scriptEvent OPERATION ::= {
  ARGUMENT         ScriptEventArg
  RETURN RESULT    FALSE
  ALWAYS RESPONDS  FALSE
  CODE             opcode-scriptEvent
}

-- Direction:SRF-> SCF. Timer :TRe
-- This operation is issued by the SRF to return information to the SCF on the results of the
-- execution of the instance of User Interaction script.
ScriptEventArg ::= SEQUENCE {
  uIScriptId          UISCRIPT.&id({SupportedUIScripts}),
  uIScriptResult
    [0]  UISCRIPT.&Result({SupportedUIScripts}{@uIScriptId}) OPTIONAL,
  extensions          [1]  Extensions OPTIONAL,
  callSegmentID       [2]  CallSegmentID OPTIONAL,
  lastEventIndicator  [3]  BOOLEAN DEFAULT FALSE,
  ...
}

scriptInformation OPERATION ::= {
  ARGUMENT         ScriptInformationArg
  RETURN RESULT    FALSE
  ERRORS
    {systemFailure | missingParameter | taskRefused | unavailableResource |
      unexpectedComponentSequence | unexpectedDataValue | unexpectedParameter}
  ALWAYS RESPONDS  FALSE
  CODE             opcode-scriptInformation
}

-- Direction:SCF-> SRF. Timer :Tinf
ScriptInformationArg ::= SEQUENCE {
  uIScriptId            UISCRIPT.&id({SupportedUIScripts}),
  uIScriptSpecificInfo
    [0]  UISCRIPT.&SpecificInfo({SupportedUIScripts}{@uIScriptId}) OPTIONAL,
  extensions            [1]  Extensions OPTIONAL,
  callSegmentID         [2]  CallSegmentID OPTIONAL,
  ...
}

scriptRun OPERATION ::= {
  ARGUMENT         ScriptRunArg
  RETURN RESULT    FALSE
  ERRORS
    {systemFailure | missingParameter | taskRefused | unavailableResource |
      unexpectedComponentSequence | unexpectedDataValue | unexpectedParameter}
  ALWAYS RESPONDS  FALSE
  CODE             opcode-scriptRun
}

-- Direction:SCF-> SRF. Timer :Tru
-- This operation is issued by the SCF to allocate the necessary resources to perform the
-- instance of the "User Interaction" script and then to activate this "User Interaction" script
-- instance. A context is partially defined for it if necessary.
ScriptRunArg ::= SEQUENCE {
  uIScriptId                 UISCRIPT.&id({SupportedUIScripts}),
  uIScriptSpecificInfo
    [0]  UISCRIPT.&SpecificInfo({SupportedUIScripts}{@uIScriptId}) OPTIONAL,
  extensions                 [1]  Extensions OPTIONAL,
  disconnectFromIPForbidden  [2]  BOOLEAN DEFAULT TRUE,
  callSegmentID              [3]  CallSegmentID OPTIONAL,
  ...
}

specializedResourceReport OPERATION ::= {
  ARGUMENT         SpecializedResourceReportArg
  RETURN RESULT    FALSE
  ALWAYS RESPONDS  FALSE
  CODE             opcode-specializedResourceReport
}

-- Direction: SRF -> SCF, Timer: Tsrr
-- This operation is used as the response to a PlayAnnouncement operation when the announcement completed
-- report indication is set.
SpecializedResourceReportArg ::= NULL

sRFCallGap OPERATION ::= {
  ARGUMENT         SRFCallGapArg
  RETURN RESULT    FALSE
  ALWAYS RESPONDS  FALSE
  CODE             opcode-srfCallGap
}

-- Direction: SRF -> SCF, Timer: Tcg
-- This operation is used to request the SCF to reduce the rate at which specific service requests are sent to
-- the SRF.
SRFCallGapArg ::= SEQUENCE {
  sRFgapCriteria  [0]  SRFGapCriteria,
  gapIndicators   [1]  GapIndicators,
  controlType     [2]  ControlType OPTIONAL,
  ...,
  ...,
  extensions      [30]  Extensions OPTIONAL
}

END

-- Generated by Asnp, the ASN.1 pretty-printer of France Telecom R&D
