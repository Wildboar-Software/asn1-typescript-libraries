-- Module IN-CS2-errortypes (Q.1228:09/1997)
-- See also ITU-T Q.1228 (09/1997)
-- See also the index of all ASN.1 assignments needed in this document

IN-CS2-errortypes {itu-t recommendation q 1228 modules(0) in-cs2-errortypes(1)
  version1(0)}
-- This module contains the type definitions for the IN CS-2 errors.
-- Where a parameter of type CHOICE is tagged with a specific tag value, the tag is automatically
-- replaced with an EXPLICIT tag of the same value.
DEFINITIONS IMPLICIT TAGS ::=
BEGIN

IMPORTS
  ros-InformationObjects, datatypes, errorcodes
    FROM IN-CS2-object-identifiers {itu-t recommendation q 1228 modules(0)
      in-cs2-object-identifiers(17) version1(0)}
  ERROR
    FROM Remote-Operations-Information-Objects {joint-iso-itu-t
      remote-operations(4) informationObjects(5) version1(0)}
  InvokeID, UnavailableNetworkResource
    FROM IN-CS2-datatypes {itu-t recommendation q 1228 modules(0)
      in-cs2-datatypes(0) version1(0)}
  errcode-cancelled, errcode-cancelFailed, errcode-chainingRefused,
    errcode-eTCFailed, errcode-improperCallerResponse,
    errcode-missingCustomerRecord, errcode-missingParameter,
    errcode-parameterOutOfRange, errcode-requestedInfoError,
    errcode-systemFailure, errcode-taskRefused, errcode-unavailableResource,
    errcode-unexpectedComponentSequence, errcode-unexpectedDataValue,
    errcode-unexpectedParameter,
    errcode-unknownLegID,
    -- errcode-unknownRecordedMessageID,
    errcode-unknownResource
    -- errcode-unknownSubscriber
    FROM IN-CS2-errorcodes {itu-t recommendation q 1228 modules(0)
      in-cs2-errorcodes(3) version1(0)};

-- TYPE DEFINITION FOR    IN CS-2    ERRORS FOLLOWS
cancelled ERROR ::= {CODE  errcode-cancelled
}

-- The operation has been cancelled.
cancelFailed ERROR ::= {
  PARAMETER
    SEQUENCE {problem
                [0]  ENUMERATED {unknownOperation(0), tooLate(1),
                                 operationNotCancellable(2)},
              operation  [1]  InvokeID}
  CODE       errcode-cancelFailed
}

-- The operation failed to be cancelled.
chainingRefused ERROR ::= {CODE  errcode-chainingRefused
}

eTCFailed ERROR ::= {CODE  errcode-eTCFailed
}

-- The establish temporary connection failed.
improperCallerResponse ERROR ::= {CODE  errcode-improperCallerResponse
}

-- The caller response was not as expected.
missingCustomerRecord ERROR ::= {CODE  errcode-missingCustomerRecord
}

-- The Service Logic Program could not be found in the SCF.
missingParameter ERROR ::= {CODE  errcode-missingParameter
}

-- An expected optional parameter was not received.
parameterOutOfRange ERROR ::= {CODE  errcode-parameterOutOfRange
}

-- The parameter was not as expected (e.g. missing or out-of-range).
requestedInfoError ERROR ::= {
  PARAMETER
    ENUMERATED {unknownRequestedInfo(1), requestedInfoNotAvailable(2)
                                         -- other values FFS
                                         }
  CODE       errcode-requestedInfoError
}

-- The requested information cannot be found.
systemFailure ERROR ::= {
  PARAMETER  UnavailableNetworkResource
  CODE       errcode-systemFailure
}

-- The operation could not be completed due to a system failure at the serving physical entity.
taskRefused ERROR ::= {
  PARAMETER
    ENUMERATED {generic(0), unobtainable(1), congestion(2)
                                             --other values FFS
                                             }
  CODE       errcode-taskRefused
}

-- An entity normally capable of the task requested cannot or chooses not to perform the task at this
-- time. This includes error situations like congestion and unobtainable address as used in e.g. the
-- connect operation.
unavailableResource ERROR ::= {CODE  errcode-unavailableResource
}

-- A requested resource is not available at the serving entity.
unexpectedComponentSequence ERROR ::= {
  CODE  errcode-unexpectedComponentSequence
}

-- An incorrect sequence of Components was received (e.g."DisconnectForwardConnection"
-- followed by "PlayAnnouncement").
unexpectedDataValue ERROR ::= {CODE  errcode-unexpectedDataValue
}

-- The data value was not as expected (e.g. routing number expected but billing number received)
unexpectedParameter ERROR ::= {CODE  errcode-unexpectedParameter
}

-- A parameter received was not expected.
unknownLegID ERROR ::= {CODE  errcode-unknownLegID
}

-- Leg not known to the SSF.
unknownResource ERROR ::= {CODE  errcode-unknownResource
}

-- Resource whose status is being requested is not known to the serving entity.
END

-- Generated by Asnp, the ASN.1 pretty-printer of France Telecom R&D
