-- Module IN-CS2-errorcodes (Q.1228:09/1997)
-- See also ITU-T Q.1228 (09/1997)
-- See also the index of all ASN.1 assignments needed in this document

IN-CS2-errorcodes {itu-t recommendation q 1228 modules(0) in-cs2-errorcodes(3)
  version1(0)} DEFINITIONS ::=
BEGIN

IMPORTS
  ros-InformationObjects
    FROM IN-CS2-object-identifiers {itu-t recommendation q 1228 modules(0)
      in-cs2-object-identifiers(17) version1(0)}
  Code
    FROM Remote-Operations-Information-Objects {joint-iso-itu-t
      remote-operations(4) informationObjects(5) version1(0)};

errcode-cancelled Code ::= local:0

errcode-cancelFailed Code ::= local:1

errcode-eTCFailed Code ::= local:3

errcode-improperCallerResponse Code ::= local:4

errcode-missingCustomerRecord Code ::= local:6

errcode-missingParameter Code ::= local:7

errcode-parameterOutOfRange Code ::= local:8

errcode-requestedInfoError Code ::= local:10

errcode-systemFailure Code ::= local:11

errcode-taskRefused Code ::= local:12

errcode-unavailableResource Code ::= local:13

errcode-unexpectedComponentSequence Code ::= local:14

errcode-unexpectedDataValue Code ::= local:15

errcode-unexpectedParameter Code ::= local:16

errcode-unknownLegID Code ::= local:17

errcode-unknownResource Code ::= local:18

-- Error codes for the new IN CS-2 error types follows
errcode-scfReferral Code ::=
  local:21

errcode-scfTaskRefused Code ::= local:22

errcode-chainingRefused Code ::= local:23

END

-- Generated by Asnp, the ASN.1 pretty-printer of France Telecom R&D
