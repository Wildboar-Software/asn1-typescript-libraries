-- Module SDFProtocolObjectIdentifiers (Q.1218:10/1995)
-- See also ITU-T Q.1218 (10/1995)
-- See also the index of all ASN.1 assignments needed in this document

SDFProtocolObjectIdentifiers {itu-t recommendation q 1218 module(0)
  sdfProtocolObjectIdentifiers(10) version1(0)} DEFINITIONS ::=
BEGIN

--  EXPORTS All
IMPORTS ;

--  useful definitions
in-ds OBJECT IDENTIFIER ::=
  {itu-t recommendation q 1218 sdf-objects(10)}

id-rosObject OBJECT IDENTIFIER ::= {in-ds 25}

id-contract OBJECT IDENTIFIER ::= {in-ds 26}

id-package OBJECT IDENTIFIER ::= {in-ds 27}

id-ac OBJECT IDENTIFIER ::= {in-ds 3}

id-as OBJECT IDENTIFIER ::= {in-ds 5}

--  ROS Objects
id-rosObject-dua OBJECT IDENTIFIER ::= {id-rosObject 1}

id-rosObject-directory OBJECT IDENTIFIER ::= {id-rosObject 2}

id-rosObject-dapDSA OBJECT IDENTIFIER ::= {id-rosObject 3}

--  contracts
id-contract-dap OBJECT IDENTIFIER ::= {id-contract 1}

--  packages
id-package-search OBJECT IDENTIFIER ::= {id-package 2}

id-package-modify OBJECT IDENTIFIER ::= {id-package 3}

id-package-dapConnection OBJECT IDENTIFIER ::= {id-package 10}

--  application contexts
id-ac-directoryAccessAC OBJECT IDENTIFIER ::=
  {id-ac 1}

--  abstract syntaxes
id-as-directoryOperationsAS OBJECT IDENTIFIER ::=
  {id-as 1}

id-as-directoryBindingAS OBJECT IDENTIFIER ::= {id-as 2}

END

-- Generated by Asnp, the ASN.1 pretty-printer of France Telecom R&D
