-- Module IN-SCF-CUSF-Operations (Q.1248.7:07/2001)
-- See also ITU-T Q.1248.7 (07/2001)
-- See also the index of all ASN.1 assignments needed in this document

IN-SCF-CUSF-Operations {itu-t recommendation q 1248 modules(1)
  in-scf-cusf-ops-args(26) version1(0)} DEFINITIONS IMPLICIT TAGS ::=
BEGIN

IMPORTS
  ros-InformationObjects, common-classes, common-datatypes, scf-cusf-classes,
    scf-cusf-datatypes, ssf-scf-datatypes, ssf-scf-classes, errortypes,
    operationcodes
    FROM IN-object-identifiers {itu-t recommendation q 1248 modules(1)
      in-object-identifiers(0) version1(0)}
  OPERATION
    FROM Remote-Operations-Information-Objects ros-InformationObjects
  COMMON-BOUNDS
    FROM IN-common-classes common-classes
  Extensions
    FROM IN-common-datatypes common-datatypes
  SCF-SSF-BOUNDS
    FROM IN-SSF-SCF-Classes ssf-scf-classes
  SCF-CUSF-BOUNDS
    FROM IN-SCF-CUSF-Classes scf-cusf-classes
  BCUSMEvent, CallUnrelatedDpSpecificCommonParameters, CUApplicationInd,
    EventSpecificInformationBCUSM, EventTypeBCUSM, Message
    FROM IN-SCF-CUSF-Datatypes scf-cusf-datatypes
  BearerCapability, CalledPartyNumber, CallingPartyNumber,
    CallingPartySubaddress, Cause, Component, ComponentType,
    ComponentCorrelationID, Duration, GenericNumbers,
    HighLayerCompatibility, LegID, LocationNumber, MiscCallInfo,
    MonitorMode, ServiceAddressInformation, ServiceKey, TerminalType,
    USIInformation, USIServiceIndicator
    FROM IN-SSF-SCF-datatypes ssf-scf-datatypes
  missingCustomerRecord, missingParameter, parameterOutOfRange, systemFailure,
    taskRefused, unexpectedComponentSequence, unexpectedDataValue,
    unexpectedParameter, unknownLegID
    FROM IN-errortypes errortypes
  opcode-activationReceivedAndAuthorized, opcode-initiateAssociation,
    opcode-associationReleaseRequested, opcode-componentReceived,
    opcode-releaseAssociation, opcode-requestReportBCUSMEvent,
    opcode-sendComponent, opcode-initialAssociationDP,
    opcode-connectAssociation, opcode-continueAssociation,
    opcode-eventReportBCUSM
    FROM IN-operationcodes operationcodes;

-- The following three definitions are local short-hand notation for convenience.
B1 ::=
  COMMON-BOUNDS --defined in Q.1248.1(Part 1 of Recommendation Q.1248)

B2 ::= SCF-SSF-BOUNDS --defined in Q.1248.2(Part 2 of Recommendation Q.1248)

B7 ::= SCF-CUSF-BOUNDS --defined in this Recommendation(Q.1248.7)

-- activityTest OPERATION
-- Direction: SCF -> CUSF, Timer: Tat
-- This operation is described in Q.1248.2.
activationReceivedAndAuthorized OPERATION ::= {
  ARGUMENT         ActivationReceivedAndAuthorizedArg
  RETURN RESULT    FALSE
  ERRORS
    {missingCustomerRecord | missingParameter | parameterOutOfRange |
      systemFailure | taskRefused | unexpectedComponentSequence |
      unexpectedDataValue | unexpectedParameter}
  ALWAYS RESPONDS  FALSE
  CODE             opcode-activationReceivedAndAuthorized
}

-- Direction: CUSF->SCF, Timer: Tara
ActivationReceivedAndAuthorizedArg ::= SEQUENCE {
  callUnrelatedDpSpecificCommonParameters
    [0]  CallUnrelatedDpSpecificCommonParameters,
  componentType                            [1]  ComponentType OPTIONAL,
  componentCorrelationID                   [3]  ComponentCorrelationID OPTIONAL,
  extensions                               [4]  Extensions OPTIONAL,
  component                                [5]  Component OPTIONAL,
  ...
}

associationReleaseRequested OPERATION ::= {
  ARGUMENT         AssociationReleaseRequestedArg
  RETURN RESULT    FALSE
  ERRORS
    {missingCustomerRecord | missingParameter | parameterOutOfRange |
      systemFailure | taskRefused | unexpectedComponentSequence |
      unexpectedDataValue | unexpectedParameter | unknownLegID}
  ALWAYS RESPONDS  FALSE
  CODE             opcode-associationReleaseRequested
}

-- Direction: CUSF -> SCF, Timer: Tarr
AssociationReleaseRequestedArg ::= SEQUENCE {
  callUnrelatedDpSpecificCommonParameters
    [0]  CallUnrelatedDpSpecificCommonParameters,
  componentType                            [1]  ComponentType OPTIONAL,
  componentCorrelationID                   [3]  ComponentCorrelationID OPTIONAL,
  extensions                               [4]  Extensions OPTIONAL,
  component                                [5]  Component OPTIONAL,
  legID                                    [6]  LegID OPTIONAL,
  ...
}

componentReceived OPERATION ::= {
  ARGUMENT         ComponentReceivedArg
  RETURN RESULT    FALSE
  ERRORS
    {missingCustomerRecord | missingParameter | parameterOutOfRange |
      systemFailure | taskRefused | unexpectedComponentSequence |
      unexpectedDataValue | unexpectedParameter | unknownLegID}
  ALWAYS RESPONDS  FALSE
  CODE             opcode-componentReceived
}

-- Direction: CUSF -> SCF, Timer: Tcre
ComponentReceivedArg ::= SEQUENCE {
  callUnrelatedDpSpecificCommonParameters
    [0]  CallUnrelatedDpSpecificCommonParameters,
  componentType                            [1]  ComponentType OPTIONAL,
  componentCorrelationID                   [3]  ComponentCorrelationID OPTIONAL,
  extensions                               [4]  Extensions OPTIONAL,
  component                                [5]  Component OPTIONAL,
  legID                                    [6]  LegID OPTIONAL,
  ...
}

connectAssociation OPERATION ::= {
  ARGUMENT         ConnectAssociationArg
  RETURN RESULT    FALSE
  ERRORS
    {missingParameter | parameterOutOfRange | systemFailure | taskRefused |
      unexpectedComponentSequence | unexpectedDataValue | unexpectedParameter}
  ALWAYS RESPONDS  FALSE
  CODE             opcode-connectAssociation
}

-- Direction: SCF->CUSF, Timer: Tcoa
ConnectAssociationArg ::= SEQUENCE {
  address         [0]  CalledPartyNumber,
  extensions      [1]  Extensions OPTIONAL,
  genericNumbers  [2]  GenericNumbers OPTIONAL,
  ...
}

continueAssociation OPERATION ::= {
  ARGUMENT         ContinueAssociationArg
  OPTIONAL         TRUE
  RETURN RESULT    FALSE
  ERRORS
    {missingParameter | parameterOutOfRange | systemFailure | taskRefused |
      unexpectedComponentSequence | unexpectedDataValue | unexpectedParameter}
  ALWAYS RESPONDS  FALSE
  CODE             opcode-continueAssociation
}

-- Direction: SCF->CUSF, Timer: Tcona
ContinueAssociationArg ::= SEQUENCE {
  extensions  [0]  Extensions OPTIONAL,
  ...
}

eventReportBCUSM OPERATION ::= {
  ARGUMENT         EventReportBCUSMArg
  RETURN RESULT    FALSE
  ALWAYS RESPONDS  FALSE
  CODE             opcode-eventReportBCUSM
}

-- Direction: CUSF -> SCF, Timer: Terbce
EventReportBCUSMArg ::= SEQUENCE {
  eventTypeBCUSM                 [0]  EventTypeBCUSM OPTIONAL,
  eventSpecificInformationBCUSM
    [1]  EventSpecificInformationBCUSM OPTIONAL,
  miscCallInfo
    [2]  MiscCallInfo DEFAULT {messageType request},
  cUApplicationInd               [3]  CUApplicationInd OPTIONAL,
  legID                          [4]  LegID OPTIONAL,
  extensions                     [5]  Extensions OPTIONAL,
  componentType                  [6]  ComponentType OPTIONAL,
  componentCorrelationID         [7]  ComponentCorrelationID OPTIONAL,
  component                      [8]  Component OPTIONAL,
  ...
}

initialAssociationDP OPERATION ::= {
  ARGUMENT         InitialAssociationDPArg
  RETURN RESULT    FALSE
  ERRORS
    {missingCustomerRecord | missingParameter | parameterOutOfRange |
      systemFailure | taskRefused | unexpectedComponentSequence |
      unexpectedDataValue | unexpectedParameter}
  ALWAYS RESPONDS  FALSE
  CODE             opcode-initialAssociationDP
}

-- Direction: CUSF->SCF, Timer: Tiadp
InitialAssociationDPArg ::= SEQUENCE {
  serviceKey              [0]  ServiceKey,
  cUApplicationInd        [1]  CUApplicationInd OPTIONAL,
  miscCallInfo            [2]  MiscCallInfo OPTIONAL,
  eventTypeBCUSM          [3]  EventTypeBCUSM OPTIONAL,
  calledPartyNumber       [4]  CalledPartyNumber OPTIONAL,
  callingPartyNumber      [5]  CallingPartyNumber OPTIONAL,
  callingPartySubaddress  [6]  CallingPartySubaddress OPTIONAL,
  highLayerCompatibility  [7]  HighLayerCompatibility OPTIONAL,
  bearerCapability        [8]  BearerCapability OPTIONAL,
  uSIServiceIndicator     [9]  USIServiceIndicator OPTIONAL,
  uSIInformation          [10]  USIInformation OPTIONAL,
  extensions              [11]  Extensions OPTIONAL,
  genericNumbers          [12]  GenericNumbers OPTIONAL,
  componentType           [13]  ComponentType OPTIONAL,
  componentCorrelationID  [14]  ComponentCorrelationID OPTIONAL,
  component               [15]  Component OPTIONAL,
  ...
}

initiateAssociation OPERATION ::= {
  ARGUMENT         InitiateAssociationArg
  RESULT           InitiateAssociationResultArg
  ERRORS
    {missingParameter | parameterOutOfRange | systemFailure | taskRefused |
      unexpectedComponentSequence | unexpectedDataValue | unexpectedParameter}
  ALWAYS RESPONDS  TRUE
  CODE             opcode-initiateAssociation
}

-- Direction: SCF->CUSF, Timer: Tia
InitiateAssociationArg ::= SEQUENCE {
  calledPartyNumber    [0]  CalledPartyNumber,
  extensions           [1]  Extensions OPTIONAL,
  uSIServiceIndicator  [2]  USIServiceIndicator OPTIONAL,
  uSIInformation       [3]  USIInformation OPTIONAL,
  genericNumbers       [4]  GenericNumbers OPTIONAL,
  ...
}

InitiateAssociationResultArg ::= NULL

releaseAssociation OPERATION ::= {
  ARGUMENT         ReleaseAssociationArg
  RETURN RESULT    FALSE
  ALWAYS RESPONDS  FALSE
  CODE             opcode-releaseAssociation
}

--  Direction: SCF->CUSF, Timer: Trel
ReleaseAssociationArg ::=
  Cause

-- reportUTSI  OPERATION
-- Direction: CUSF -> SCF, Timer: Tru
-- This operation is described in Q.1248.2.
requestReportBCUSMEvent OPERATION ::= {
  ARGUMENT         RequestReportBCUSMEventArg
  RETURN RESULT    FALSE
  ERRORS
    {missingParameter | parameterOutOfRange | systemFailure | taskRefused |
      unexpectedComponentSequence | unexpectedDataValue | unexpectedParameter |
      unknownLegID}
  ALWAYS RESPONDS  FALSE
  CODE             opcode-requestReportBCUSMEvent
}

-- Direction: SCF -> CUSF, Timer: Trrbce
RequestReportBCUSMEventArg ::= SEQUENCE {
  bCUSMEvents
    [0]  SEQUENCE OF BCUSMEvent,
  componentTypes
    [1]  SEQUENCE SIZE (1..3) OF ComponentType DEFAULT {any},
  componentCorrelationID  [2]  ComponentCorrelationID OPTIONAL,
  monitorDuration         [3]  Duration OPTIONAL,
  extensions              [4]  Extensions OPTIONAL,
  cUDPCriteria            [5]  CUApplicationInd OPTIONAL,
  legID                   [6]  LegID OPTIONAL,
  ...
}

-- requestReportUTSI  OPERAITON
-- Direction: SCF -> CUSF, Timer: Trru
-- This operation is described in Q.1248.2.
sendComponent OPERATION ::= {
  ARGUMENT         SendComponentArg
  RETURN RESULT    FALSE
  ERRORS
    {missingParameter | parameterOutOfRange | systemFailure | taskRefused |
      unexpectedComponentSequence | unexpectedDataValue | unexpectedParameter}
  ALWAYS RESPONDS  FALSE
  CODE             opcode-sendComponent
}

--	Direction: SCF -> CUSF, Timer: Tsdc
SendComponentArg ::= SEQUENCE {
  componentType           [0]  ComponentType,
  componentCorrelationID  [2]  ComponentCorrelationID OPTIONAL,
  message                 [3]  Message DEFAULT rELeaseCOMPlete,
  monitorDuration         [4]  Duration OPTIONAL,
  extensions              [5]  Extensions OPTIONAL,
  component               [6]  Component OPTIONAL,
  ...
}

-- sendSTUI  OPERATION
-- Direction: SCF -> CUSF, Timer: Tss
-- This operation is described in Q.1248.2.
END

-- Generated by Asnp, the ASN.1 pretty-printer of France Telecom R&D
