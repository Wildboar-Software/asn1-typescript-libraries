-- Module IN-CS3-SCF-SCF-datatypes (Q.1238.6:06/2000)
-- See also ITU-T Q.1238.6 (06/2000)
-- See also the index of all ASN.1 assignments needed in this document

-- 10	ASN.1 DEFINITIONS
--
-- 10.1	DATA TYPES
--
-- The following ASN.1 module defines the data types used in the specification
-- of the arguments and results of the operations invoked on the SCF-SCF interface.
IN-CS3-SCF-SCF-datatypes {itu-t recommendation q 1238 modules(1)
  in-cs3-scf-scf-datatypes(20) version1(0)} DEFINITIONS IMPLICIT TAGS ::=
BEGIN

IMPORTS
  Code
    FROM Remote-Operations-Information-Objects ros-InformationObjects
  Integer4
    FROM IN-CS3-common-datatypes {itu-t recommendation q 1238 modules(1)
      in-cs3-common-datatypes(1) version1(0)}
  COMMON-BOUNDS
    FROM IN-CS3-common-classes {itu-t recommendation q 1238 modules(1)
      in-cs3-common-classes(5) version1(0)}
  SCF-SSF-BOUNDS
    FROM IN-CS3-SSF-SCF-Classes {itu-t recommendation q 1238 modules(1)
      in-cs3-ssf-scf-classes(7) version1(0)}
  SCF-SCF-BOUNDS
    FROM IN-CS3-SCF-SCF-Classes {itu-t recommendation q 1238 modules(1)
      in-cs3-scf-scf-classes(21) version1(0)}
  CalledPartyNumber, CallingPartyNumber, Cause, DateAndTime,
    DestinationRoutingAddress, DisplayInformation, Duration,
    GenericNumber
    FROM IN-CS3-SSF-SCF-datatypes {itu-t recommendation q 1238 modules(1)
      in-cs3-ssf-scf-datatypes(6) version1(0)}
  Tone
    FROM IN-CS3-SCF-SRF-datatypes {itu-t recommendation q 1238 modules(1)
      in-cs3-scf-srf-datatypes(10) version1(0)}
  DistinguishedName
    FROM InformationFramework {joint-iso-itu-t ds(5) module(1)
      informationFramework(1) 3}
  ros-InformationObjects, ds-UsefulDefinitions, operationcodes, guls-Notation,
    guls-SecurityTransformations, errortypes, errorcodes, scf-scf-Protocol,
    ssf-scf-Operations, ssf-scf-datatypes, spkmGssTokens, common-datatypes,
    ssf-scf-classes, scf-scf-classes, common-classes, scf-srf-datatypes
    FROM IN-CS3-object-identifiers {itu-t recommendation q 1238 modules(1)
      in-cs3-object-identifiers(0) version1(0)}
  directoryAbstractService, enhancedSecurity, informationFramework,
    selectedAttributeTypes, distributedOperations, basicAccessControl
    FROM UsefulDefinitions {joint-iso-itu-t ds(5) module(1)
      usefulDefinitions(0) 3}
  PresentationAddress
    FROM SelectedAttributeTypes {joint-iso-itu-t ds(5) module(1)
      selectedAttributeTypes(5) 3};

-- The following short-hand notation is used to refer to ASN.1 Information Object Classes
-- representing parameters bounds.
B1 ::=
  COMMON-BOUNDS -- defined in Recommendation Q.1238.1

B2 ::= SCF-SSF-BOUNDS -- defined in Recommendation Q.1238.2

B6 ::= SCF-SCF-BOUNDS -- defined in this Recommendation Q.1238.6

AccountNumber ::= NumericString(SIZE (1..151))

Actions ::= ENUMERATED {play(0), playandcollect(1)}

AgreementFeatureIndicator ::= Code

--This AgreementFeatureIndicator indicates the service application for which the service data is to be provided.
AgreementID ::= OBJECT IDENTIFIER

BasicChargingParameters ::= SEQUENCE {
  unitsPerInterval         [0]  INTEGER,
  timePerInterval          [1]  INTEGER,
  scalingFactor            [2]  INTEGER,
  initialUnitIncrement
    [3]  INTEGER OPTIONAL,
  unitsPerDataInterval
    [4]  INTEGER OPTIONAL,
  segmentsPerDataInterval
    [5]  INTEGER OPTIONAL,
  initialTimeInterval
    [6]  INTEGER OPTIONAL
}

BearerCapabilities ::= BIT STRING {
  speech(0), bc64kbits(1), bc2x64kbits(2), bc384kbits(3), bc1536kbits(4),
  bc1920kbits(5), multirate(6), restrictedDigitalInfo(7), bc3-1khzAudio(8),
  bc7khzAudio(9), video(10)}

CallConditions ::= CHOICE {
  userAbandon         [0]  NULL,
  callFailure         [1]  Cause,
  noReply             [2]  INTEGER, -- time expressed in seconds
  callRelease         [3]  NULL,
  ss-invocation       [4]  InvokableService,
  creditLimitReached  [5]  INTEGER,
  callDuration        [6]  INTEGER,
  calledNumber        [7]  NumberMatch,
  answeredCall        [8]  NULL
}

CallIdentifier ::= Integer4

CallRecord ::= SEQUENCE {
  callDuration        [0]  Duration,
  callingPartyNumber  [1]  CallingPartyNumber,
  calledPartyNumber   [2]  CalledPartyNumber
}

ChargingParameters ::= CHOICE {
  basic    [1]  BasicChargingParameters,
  tariffs  [20]  Tariffs,
  mutual   [21]  Code--indicated an indexed charging rule--
  -- agreed between operator
}

ChargingSignallingInformation ::= SEQUENCE {
  partyToBeCharged  PartyToBeCharged,
  percentage        INTEGER(0..100)
}

CollectedInfo ::= CHOICE {
  collectedDigits  [0]  CollectedDigits,
  iA5Information   [1]  BOOLEAN
}

CollectedDigits ::= SEQUENCE {
  minimumNbOfDigits    [0]  INTEGER(1..127) DEFAULT 1,
  maximumNbOfDigits    [1]  INTEGER(1..127),
  endOfReplyDigit      [2]  IA5String(SIZE (1)) OPTIONAL,
  cancelDigit          [3]  IA5String(SIZE (1)) OPTIONAL,
  startDigit           [4]  IA5String(SIZE (1)) OPTIONAL,
  firstDigitTimeOut    [5]  INTEGER(1..127) OPTIONAL,
  interDigitTimeOut    [6]  INTEGER(1..127) OPTIONAL,
  errorTreatment       [7]  ErrorTreatment DEFAULT reportErrorToScf,
  interruptableAnnInd  [8]  BOOLEAN DEFAULT TRUE,
  voiceInformation     [9]  BOOLEAN DEFAULT FALSE,
  voiceBack            [10]  BOOLEAN DEFAULT FALSE
}

ConsumedCreditAction ::= ENUMERATED {disconnect(0), message(1), tone(2)}

Credit ::= CHOICE {currency  CurrencyValue,
                          units     CreditUnit
}

CreditUnit ::= INTEGER(0..maxCreditUnit)

maxCreditUnit INTEGER ::= 65536

CurrencyID ::= PrintableString(SIZE (3)) -- ISO 639 code


CurrencyValue ::= SEQUENCE {
  currency  CurrencyID,
  amount    INTEGER
}

Destination ::= SEQUENCE {
  type     [1]  ENUMERATED {e164(0), x121(1)},
  genadd   [2]  GenericNumber OPTIONAL,
  presadd  [3]  PresentationAddress OPTIONAL
}

ErrorTreatment ::= ENUMERATED {reportErrorToScf(0), help(1), repeatPrompt(2)}

Event ::= CHOICE {
  duration  [1]  INTEGER(0..maxTimeInterval),
  event
    [2]  ENUMERATED {now(0), answer(1), user-interaction(2), failure(3)}
}

maxTimeInterval INTEGER ::= 65536

FreeContainer ::= OCTET STRING

HighLayerCompatibilities ::= BIT STRING {
  telephony(0), facsimileGroup2-3(1), facsimileGroup4classeI(2),
  teletexMixedMode(3), teletexProcessableMode(4), teletexBasicMode(5),
  syntaxBasedVideotex(6), internationalVideotex(7), telexService(8),
  messageHandlingSystem(9), osiApplication(10), audioVisual(11)}

InbandInfo ::= SEQUENCE {
  messageId            [0]  MessageID,
  numberOfRepetitions  [1]  INTEGER(1..127) OPTIONAL,
  duration             [2]  INTEGER(1..32767) OPTIONAL,
  interval             [3]  INTEGER(1..32767) OPTIONAL
}

InformationToSend ::= CHOICE {
  inbandInfo          [0]  InbandInfo,
  tone                [1]  Tone,
  displayInformation  [2]  DisplayInformation
}

InfoType ::= ENUMERATED {numericString(0), characterString(1), iA5String(2)}

InvokableService ::= ENUMERATED {
  callingLineIdentificationRestriction(1),
  connectedLineIdentificationRestriction(2), callWaiting(3), callHold(4),
  reverseCharging(5), explicitCallTransfer(6),
  callCompletionOnBusySubscriber(7)}

MessageID ::= OBJECT IDENTIFIER

Meters ::= SEQUENCE OF Meter

Meter ::= SEQUENCE {
  meternum    [1]  INTEGER(0..nbrOfMeters) OPTIONAL,
  metervalue  [2]  INTEGER
}

nbrOfMeters INTEGER ::= 128

Notification ::= ENUMERATED {
  userAbandon(0), callFailure(1), noReply(2), callRelease(3), ssInvocation(4),
  creditLimitReached(5), callDuration(6), calledNumber(7), answeredCall(8)
}

NotificationInformation ::= CHOICE {
  userAbandonSpecificInfo         [0]  SEQUENCE {...},
  callFailureSpecificInfo
    [1]  SEQUENCE {failureCause  [0]  Cause OPTIONAL,
                   ...},
  noReplySpecificInfo             [2]  SEQUENCE {...},
  callReleaseSpecificInfo
    [3]  SEQUENCE {releaseCause  [0]  Cause OPTIONAL,
                   timeStamp     [1]  DateAndTime OPTIONAL,
                   ...},
  ssInvocationSpecificInfo
    [4]  SEQUENCE {invokedService  [0]  InvokableService,
                   ...},
  creditLimitReachedSpecificInfo
    [5]  SEQUENCE {timeStamp  [0]  DateAndTime OPTIONAL,
                   ...},
  callDurationSpecificInfo
    [6]  SEQUENCE {timeStamp  [0]  DateAndTime OPTIONAL,
                   ...},
  calledNumberSpecificInfo
    [7]  SEQUENCE {calledNumber  [0]  CalledPartyNumber OPTIONAL,
                   ...},
  answeredCallSpecificInfo
    [8]  SEQUENCE {timeStamp  [0]  DateAndTime OPTIONAL,
                   ...}
}

NumberMatch ::= CHOICE {
  initialMatch  [0]  CalledPartyNumber,
  totalMatch    [1]  CalledPartyNumber
}

PartyToBeCharged ::= ENUMERATED {orignating(0), terminating(1)}

ProtocolInfo ::= CHOICE {sdf  [1]  SDFProtocolInfo,
                         scf  [2]  SCFProtocolInfo
}

ReceivedInformation ::=
  SEQUENCE OF IA5String

ReportConditionEvent ::= SEQUENCE {
  now                 [1]  NULL OPTIONAL,
  endOfCall           [2]  NULL OPTIONAL,
  period              [3]  INTEGER(0..maxPeriodTime),
  remainingthreshold  [5]  UserCredit OPTIONAL,
  eachNumOfUnit       [6]  INTEGER OPTIONAL
}

maxPeriodTime INTEGER ::= 32767

ReportDestinationInformation ::= SEQUENCE {
  destination   [1]  Destination,
  protocolInfo  [2]  ProtocolInfo
}

RequestedNotifications ::= SET OF CallConditions

RequestedType ::= INTEGER(0..127)

RoutingAddress ::= CHOICE {
  routingProhibited          [0]  NULL,
  destinationRoutingAddress  [1]  DestinationRoutingAddress
}

Rule ::= BasicChargingParameters

ScfAddress ::=
  OCTET STRING

SCFProtocolInfo ::= AgreementID

SDFProtocolInfo ::= SEQUENCE {
  entryname  DistinguishedName,
  attribute  OBJECT IDENTIFIER
}

SSIInfo ::= SEQUENCE {
  agreementFeatureIndicator  [0]  AgreementFeatureIndicator OPTIONAL,
  sTSIInformation            [1]  STSIInformation
}

STSIInformation ::=
  OCTET STRING

-- The STSIInformation contains the service information associated with the agreementFeatureIndicator.
-- provided by the Service Logic of the invoking SCF to be transferred to the Service Logic
-- of the responding  SCF.s
SupplementaryServices ::= BIT STRING {
  callingLineIdentificationPresentation(1),
  callingLineIdentificationRestriction(2),
  connectedLineIdentificationPresentation(3),
  connectedLineIdentificationRestriction(4), callForwardingOnNoReply(5),
  callForwardingUnconditional(6), callForwardingOnBusy(7),
  callForwardingOnNotReachable(8), callWaiting(9), callHold(10),
  reverseCharging(11), explicitCallTransfer(12),
  callCompletionOnBusySubscriber(13), adviceOfChargeOnStart(14),
  adviceOfChargeAtEnd(15), adviceOfChargeDuringCall(16),
  timeDependentRouting(17), callingPartingDependentRouting(18),
  outgoingCallBarring(19), incomingCallBarring(20)}

Tariff ::= SEQUENCE {
  condition      [1]  Event,
  meternum       [2]  INTEGER(0..nbrOfMeters) OPTIONAL,
  rule           [3]  Rule OPTIONAL,
  resetAfterRCI  [4]  BOOLEAN DEFAULT FALSE
}

Tariffs ::= SEQUENCE OF Tariff

UserInteractionModes ::= BIT STRING {voiceMessage(0), tone(1), display(2)}

UserCredit ::= Credit

UserToConnect ::= ENUMERATED {first(0), nofirst(1), newone(2), previous(3)}

END

-- Generated by Asnp, the ASN.1 pretty-printer of France Telecom R&D
