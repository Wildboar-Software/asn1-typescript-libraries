-- Module IN-SCF-SCF-pkgs-contracts-acs (Q.1248.6:07/2001)
-- See also ITU-T Q.1248.6 (07/2001)
-- See also the index of all ASN.1 assignments needed in this document

IN-SCF-SCF-pkgs-contracts-acs {itu-t recommendation q 1248 modules(1)
  in-scf-scf-pkgs-contracts-acs(23) version1(0)} DEFINITIONS ::=
BEGIN

-- This module describes the operation-packages, contracts and application-contexts used
-- over the SCF-SCF interface.
IMPORTS
  networkSpecificBoundSet, COMMON-BOUNDS
    FROM IN-common-classes common-classes
  ROS-OBJECT-CLASS, CONTRACT, OPERATION-PACKAGE, CONNECTION-PACKAGE, OPERATION
    FROM Remote-Operations-Information-Objects ros-InformationObjects
  Bind{}, Unbind{}
    FROM Remote-Operations-Generic-ROS-PDUs ros-genericPDUs
  TCMessage{}
    FROM TCAPMessages tc-Messages
  APPLICATION-CONTEXT, dialogue-abstract-syntax
    FROM TC-Notation-Extensions tc-NotationExtensions
  announcementCompletionReport, establishChargingRecord,
    confirmedReportChargingInformation, confirmedNotificationProvided,
    handlingInformationRequest, handlingInformationResult,
    initiateCallRequest, networkCapability, notificationProvided,
    provideAnnouncementRequest, provideUserInformation,
    reportChargingInformation, requestNotification, runUserScript,
    transferSTSI, chainedHandlingInformationRequest,
    chainedNotificationProvided, chainedConfirmedNotificationProvided,
    chainedReportChargingInformation,
    chainedConfirmedReportChargingInformation,
    chainedEstablishChargingRecord, chainedHandlingInformationResult,
    chainedNetworkCapability, chainedProvideUserInformation,
    chainedRequestNotification, chainedRunUserScript, scfBind
    FROM IN-SCF-SCF-ops-args scf-scf-Operations
  id-ac, id-rosObject, id-contract, id-package, id-as,
    id-ac-scfc-scfsOperationsAC, id-ac-scfs-scfcOperationsAC,
    id-ac-distributedSCFSystemAC, id-ac-scfc-scfsOperationsWith3seAC,
    id-ac-scfs-scfcOperationsWith3seAC, id-ac-distributedSCFSystemWith3seAC,
    id-contract-scfc-scfs, id-contract-scfs-scfc, id-contract-dssp,
    id-package-dsspConnection, id-package-scf-scfConnection,
    id-package-handlingInformation, id-package-initiateCall,
    id-package-notification, id-package-chargingInformation,
    id-package-userInformation, id-package-networkCapability,
    id-package-transferStsi, id-package-chainedSCFOperations,
    id-as-scfc-scfsOperationsAS, id-as-scfs-scfcOperationsAS,
    id-as-distributedSCFSystemAS, id-as-scf-scfBindingAS, ds-UsefulDefinitions,
    scf-scf-classes, ssf-scf-classes, common-classes, tc-Messages,
    tc-NotationExtensions, ros-InformationObjects, ros-genericPDUs,
    scf-scf-Operations, scf-sdf-Protocol, ssf-scf-Operations, ssf-scf-Protocol,
    scf-srf-classes
    FROM IN-object-identifiers {itu-t recommendation q 1248 modules(1)
      in-object-identifiers(0) version1(0)}
  activityTest
    FROM IN-SSF-SCF-ops-args ssf-scf-Operations
  activityTestPackage
    FROM IN-SSF-SCF-pkgs-contracts-acs ssf-scf-Protocol
  inSESEAbstractSyntax
    FROM IN-SCF-SDF-Protocol scf-sdf-Protocol
  id-se-threewayse
    FROM ProtocolObjectIdentifiers protocolObjectIdentifiers
  protocolObjectIdentifiers
    FROM UsefulDefinitions ds-UsefulDefinitions
  inUnbind
    FROM IN-common-classes common-classes
  SCF-SSF-BOUNDS
    FROM IN-SSF-SCF-Classes ssf-scf-classes
  nsb1, nsb2, nsb3, nsb6, SCF-SCF-BOUNDS
    FROM IN-SCF-SCF-Classes scf-scf-classes
  SCF-SRF-BOUNDS
    FROM IN-SCF-SRF-Classes scf-srf-classes;

-- The following short-hand notation is used to refer to ASN.1 Information Object Classes
-- representing parameters bounds.
B1 ::=
  COMMON-BOUNDS -- defined in Recommendation Q.1248.1

B2 ::= SCF-SSF-BOUNDS -- defined in Recommendation Q.1248.2

B3 ::= SCF-SRF-BOUNDS -- defined in Recommendation Q.1248.3

B6 ::= SCF-SCF-BOUNDS -- defined in Recommendation Q.1248.6

-- Application Contexts
scfc-scfsOperationsAC APPLICATION-CONTEXT ::= {
  CONTRACT                  scfc-scfsContract
  DIALOGUE MODE             structured
  TERMINATION               basic
  ABSTRACT SYNTAXES
    {dialogue-abstract-syntax | scfBindingAbstractSyntax |
      scfc-scfsOperationsAbstractSyntax}
  APPLICATION CONTEXT NAME  id-ac-scfc-scfsOperationsAC
}

scfs-scfcOperationsAC APPLICATION-CONTEXT ::= {
  CONTRACT                  scfs-scfcContract
  DIALOGUE MODE             structured
  TERMINATION               basic
  ABSTRACT SYNTAXES
    {dialogue-abstract-syntax | scfBindingAbstractSyntax |
      scfs-scfcOperationsAbstractSyntax}
  APPLICATION CONTEXT NAME  id-ac-scfs-scfcOperationsAC
}

distributedSCFSystemAC APPLICATION-CONTEXT ::= {
  CONTRACT                  dsspContract
  DIALOGUE MODE             structured
  TERMINATION               basic
  ABSTRACT SYNTAXES
    {dialogue-abstract-syntax | distributedSCFSystemAbstractSyntax |
      scfBindingAbstractSyntax}
  APPLICATION CONTEXT NAME  id-ac-distributedSCFSystemAC
}

scfc-scfsOperationsWith3seAC APPLICATION-CONTEXT ::= {
  CONTRACT                  scfc-scfsContract
  DIALOGUE MODE             structured
  TERMINATION               basic
  ADDITIONAL ASES           {id-se-threewayse}
  ABSTRACT SYNTAXES
    {dialogue-abstract-syntax | scfBindingAbstractSyntax |
      scfc-scfsOperationsAbstractSyntax | inSESEAbstractSyntax}
  APPLICATION CONTEXT NAME  id-ac-scfc-scfsOperationsWith3seAC
}

scfs-scfcOperationsWith3seAC APPLICATION-CONTEXT ::= {
  CONTRACT                  scfs-scfcContract
  DIALOGUE MODE             structured
  TERMINATION               basic
  ADDITIONAL ASES           {id-se-threewayse}
  ABSTRACT SYNTAXES
    {dialogue-abstract-syntax | scfBindingAbstractSyntax |
      scfs-scfcOperationsAbstractSyntax | inSESEAbstractSyntax}
  APPLICATION CONTEXT NAME  id-ac-scfs-scfcOperationsWith3seAC
}

distributedSCFSystemWith3seAC APPLICATION-CONTEXT ::= {
  CONTRACT                  dsspContract
  DIALOGUE MODE             structured
  TERMINATION               basic
  ADDITIONAL ASES           {id-se-threewayse}
  ABSTRACT SYNTAXES
    {dialogue-abstract-syntax | distributedSCFSystemAbstractSyntax |
      scfBindingAbstractSyntax | inSESEAbstractSyntax}
  APPLICATION CONTEXT NAME  id-ac-distributedSCFSystemWith3seAC
}

-- trafficFlowControlAC  APPLICATION-CONTEXT
-- defined in Recommendation Q.1248.4
-- Contracts
scfc-scfsContract CONTRACT ::= {
  CONNECTION             scf-scfConnectionPackage
  INITIATOR CONSUMER OF
    {activityTestPackage | handlingInformationPackage |
      transferStsiPackage}
  RESPONDER CONSUMER OF
    {activityTestPackage | chargingInformationPackage |
      networkCapabilityPackage | notificationPackage |
      transferStsiPackage |
      userInformationPackage}
  ID                     id-contract-scfc-scfs
}

scfs-scfcContract CONTRACT ::= {
  CONNECTION             scf-scfConnectionPackage
  INITIATOR CONSUMER OF
    {activityTestPackage | chargingInformationPackage |
      initiateCallPackage | networkCapabilityPackage |
      notificationPackage | transferStsiPackage |
      userInformationPackage}
  RESPONDER CONSUMER OF
    {activityTestPackage | handlingInformationPackage |
      transferStsiPackage}
  ID                     id-contract-scfs-scfc
}

dsspContract CONTRACT ::= {
  CONNECTION             dsspConnectionPackage
  INITIATOR CONSUMER OF  {chainedSCFOperationPackage}
  ID                     id-contract-dssp
}

-- Connection Package
scf-scfConnectionPackage CONNECTION-PACKAGE ::= {
  BIND              scfBind
  UNBIND            inUnbind
  RESPONDER UNBIND  TRUE
  ID                id-package-scf-scfConnection
}

dsspConnectionPackage CONNECTION-PACKAGE ::= {
  BIND              scfBind
  UNBIND            inUnbind
  RESPONDER UNBIND  FALSE
  ID                id-package-dsspConnection
}

--  handlingInformation package
handlingInformationPackage OPERATION-PACKAGE ::=
{
  CONSUMER INVOKES  {handlingInformationRequest}
  SUPPLIER INVOKES  {handlingInformationResult}
  ID                id-package-handlingInformation
}

--  notification package
notificationPackage OPERATION-PACKAGE ::= {
  CONSUMER INVOKES  {requestNotification}
  SUPPLIER INVOKES
    {notificationProvided | confirmedNotificationProvided}
  ID                id-package-notification
}

--  chargingInformation package
chargingInformationPackage OPERATION-PACKAGE ::=
{
  CONSUMER INVOKES  {establishChargingRecord}
  SUPPLIER INVOKES
    {confirmedReportChargingInformation |
      reportChargingInformation}
  ID                id-package-chargingInformation
}

--  userInformation package
userInformationPackage OPERATION-PACKAGE ::= {
  CONSUMER INVOKES
    {provideUserInformation | provideAnnouncementRequest |
      runUserScript}
  SUPPLIER          INVOKES{announcementCompletionReport}
  ID                id-package-userInformation
}

--  initiateCall package
initiateCallPackage OPERATION-PACKAGE ::= {
  CONSUMER INVOKES  {initiateCallRequest}
  ID                id-package-initiateCall
}

--  networkCapability package
networkCapabilityPackage OPERATION-PACKAGE ::= {
  CONSUMER  INVOKES{networkCapability}
  ID        id-package-networkCapability
}

-- transferSTSI package
transferStsiPackage OPERATION-PACKAGE ::= {
  OPERATIONS{transferSTSI}
  ID  id-package-transferStsi
}

--  chainedSCFOperation package
chainedSCFOperationPackage OPERATION-PACKAGE ::=
{
  CONSUMER INVOKES
    {chainedHandlingInformationRequest |
      chainedNotificationProvided |
      chainedConfirmedNotificationProvided |
      chainedReportChargingInformation |
      chainedConfirmedReportChargingInformation}
  SUPPLIER INVOKES
    {chainedEstablishChargingRecord |
      chainedHandlingInformationResult |
      chainedNetworkCapability |
      chainedProvideUserInformation |
      chainedRunUserScript |
      chainedRequestNotification}
  ID                id-package-chainedSCFOperations
}

-- abstract syntaxes
scfc-scfsOperationsAbstractSyntax ABSTRACT-SYNTAX ::= {
  BasicSCFc-SCFs-PDUs
  IDENTIFIED BY  id-as-scfc-scfsOperationsAS
}

BasicSCFc-SCFs-PDUs ::=
  TCMessage{{SCFc-SCFs-Invokable}, {SCFc-SCFs-Returnable}}

SCFc-SCFs-Invokable OPERATION ::=
  {activityTest | announcementCompletionReport |
   confirmedNotificationProvided |
   confirmedReportChargingInformation |
   establishChargingRecord |
   handlingInformationRequest |
   handlingInformationResult | networkCapability |
   notificationProvided | provideAnnouncementRequest |
   provideUserInformation |
   reportChargingInformation |
   requestNotification | runUserScript |
   transferSTSI}

SCFc-SCFs-Returnable OPERATION ::=
  {activityTest | confirmedNotificationProvided |
   confirmedReportChargingInformation |
   establishChargingRecord |
   handlingInformationRequest |
   handlingInformationResult | networkCapability |
   notificationProvided | provideAnnouncementRequest |
   provideUserInformation |
   reportChargingInformation |
   requestNotification | runUserScript |
   transferSTSI}

scfs-scfcOperationsAbstractSyntax ABSTRACT-SYNTAX ::= {
  BasicSCFs-SCFc-PDUs
  IDENTIFIED BY  id-as-scfs-scfcOperationsAS
}

BasicSCFs-SCFc-PDUs ::=
  TCMessage{{SCFs-SCFc-Invokable}, {SCFs-SCFc-Returnable}}

SCFs-SCFc-Invokable OPERATION ::=
  {activityTest | confirmedNotificationProvided |
   confirmedReportChargingInformation |
   establishChargingRecord |
   handlingInformationRequest |
   handlingInformationResult | initiateCallRequest |
   networkCapability | notificationProvided |
   provideAnnouncementRequest |
   provideUserInformation |
   reportChargingInformation |
   requestNotification | runUserScript |
   transferSTSI}

SCFs-SCFc-Returnable OPERATION ::=
  {activityTest | announcementCompletionReport |
   confirmedNotificationProvided |
   confirmedReportChargingInformation |
   establishChargingRecord |
   handlingInformationRequest |
   handlingInformationResult | initiateCallRequest |
   networkCapability | notificationProvided |
   provideAnnouncementRequest |
   provideUserInformation |
   reportChargingInformation |
   requestNotification | runUserScript |
   transferSTSI}

distributedSCFSystemAbstractSyntax ABSTRACT-SYNTAX ::= {
  BasicDSSP-PDUs
  IDENTIFIED BY  id-as-distributedSCFSystemAS
}

BasicDSSP-PDUs ::= TCMessage{{DSSP-Invokable}, {DSSP-Returnable}}

DSSP-Invokable OPERATION ::=
  {chainedHandlingInformationRequest |
   chainedNotificationProvided |
   chainedConfirmedNotificationProvided |
   chainedReportChargingInformation |
   chainedConfirmedReportChargingInformation |
   chainedRunUserScript}

DSSP-Returnable OPERATION ::=
  {chainedHandlingInformationRequest |
   chainedConfirmedNotificationProvided |
   chainedConfirmedReportChargingInformation |
   chainedRunUserScript}

scfBindingAbstractSyntax ABSTRACT-SYNTAX ::= {
  SCF-SCFBinding-PDUs
  IDENTIFIED BY  id-as-scf-scfBindingAS
}

SCF-SCFBinding-PDUs ::= CHOICE {
  bind    Bind{scfBind},
  unbind  Unbind{inUnbind}
}

END

-- Generated by Asnp, the ASN.1 pretty-printer of France Telecom R&D
