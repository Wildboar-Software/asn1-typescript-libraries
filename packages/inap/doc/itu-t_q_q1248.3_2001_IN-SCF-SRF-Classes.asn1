-- Module IN-SCF-SRF-Classes (Q.1248.3:07/2001)
-- See also ITU-T Q.1248.3 (07/2001)
-- See also the index of all ASN.1 assignments needed in this document

IN-SCF-SRF-Classes {itu-t recommendation q 1248 modules(1)
  in-scf-srf-classes(11) version1(0)} DEFINITIONS ::=
BEGIN

IMPORTS
  id-package-emptyConnection, id-rosObject-srf, id-rosObject-ssf,
    ros-InformationObjects, ros-UsefulDefinitions, scf-srf-Protocol,
    scf-srf-datatypes, ssf-scf-datatypes
    FROM IN-object-identifiers {itu-t recommendation q 1248 modules(1)
      in-object-identifiers(0) version1(0)}
  ROS-OBJECT-CLASS, CONTRACT, OPERATION-PACKAGE, Code, OPERATION,
    CONNECTION-PACKAGE
    FROM Remote-Operations-Information-Objects ros-InformationObjects
  emptyBind, emptyUnbind
    FROM Remote-Operations-Useful-Definitions ros-UsefulDefinitions;

UISCRIPT ::= CLASS {
  &SpecificInfo  OPTIONAL,
  &Result        OPTIONAL,
  &id            Code
}
WITH SYNTAX {
  [WITH-SPECIFICINFO &SpecificInfo]
  [WITH-RESULT &Result]
  IDENTIFIED BY &id
}

-- SpecificInfo is used for ScriptRun and ScriptInformation and ScriptClose
--Result is used for ScritEvent
firstScript UISCRIPT ::= {IDENTIFIED BY  local:1
}

-- firstScript is just an example.
SupportedUIScripts UISCRIPT ::=
  {firstScript, ...
  --full set of User Interaction script
  }

-- SupportedUIScripts is the full set of User Interaction scripts.
SCF-SRF-BOUNDS ::= CLASS {
  &minAttributesLength           INTEGER OPTIONAL,
  &maxAttributesLength           INTEGER OPTIONAL,
  &minMailBoxIDLength            INTEGER OPTIONAL,
  &maxMailBoxIDLength            INTEGER OPTIONAL,
  &minMessageContentLength       INTEGER OPTIONAL,
  &maxMessageContentLength       INTEGER OPTIONAL,
  &minReceivedInformationLength  INTEGER OPTIONAL,
  &maxReceivedInformationLength  INTEGER OPTIONAL,
  &maxRecordingTime              INTEGER OPTIONAL,
  &numOfMessageIDs               INTEGER OPTIONAL,
  &maxRecordedMessageUnits       INTEGER OPTIONAL,
  &maxVariableParts              INTEGER OPTIONAL
}
WITH SYNTAX {
  [MINIMUM-FOR-ATTRIBUTES &minAttributesLength]
  [MAXIMUM-FOR-ATTRIBUTES &maxAttributesLength]
  [MINIMUM-FOR-MAIL-BOX-ID &minMailBoxIDLength]
  [MAXIMUM-FOR-MAIL-BOX-ID &maxMailBoxIDLength]
  [MINIMUM-FOR-MESSAGE-CONTENT &minMessageContentLength]
  [MAXIMUM-FOR-MESSAGE-CONTENT &maxMessageContentLength]
  [MINIMUM-FOR-RECEIVED-INFORMATION &minReceivedInformationLength]
  [MAXIMUM-FOR-RECEIVED-INFORMATION &maxReceivedInformationLength]
  [MAXIMUM-FOR-RECORDING-TIME &maxRecordingTime]
  [NUM-OF-MESSAGE-IDS &numOfMessageIDs]
  [MAXIMUM-FOR-RECORDED-MESSAGE-UNITS &maxRecordedMessageUnits]
  [NUM-OF-VARIABLE-PARTS &maxVariableParts]
}

-- The following instance of the parameter bound is just an example
networkSpecificB3 SCF-SRF-BOUNDS ::= {
  MINIMUM-FOR-ATTRIBUTES              1 -- example value
  MAXIMUM-FOR-ATTRIBUTES              5 -- example value
  MINIMUM-FOR-MAIL-BOX-ID             1 -- example value
  MAXIMUM-FOR-MAIL-BOX-ID             5 -- example value
  MINIMUM-FOR-MESSAGE-CONTENT         1 -- example value
  MAXIMUM-FOR-MESSAGE-CONTENT         5 -- example value
  MINIMUM-FOR-RECEIVED-INFORMATION    1 -- example value
  MAXIMUM-FOR-RECEIVED-INFORMATION    5 -- example value
  MAXIMUM-FOR-RECORDING-TIME          5 -- example value
  NUM-OF-MESSAGE-IDS                  2 -- example value
  MAXIMUM-FOR-RECORDED-MESSAGE-UNITS  5 -- example value
  NUM-OF-VARIABLE-PARTS               5 -- example value

-- must be 5 or
-- greater.
}

END

-- Generated by Asnp, the ASN.1 pretty-printer of France Telecom R&D
