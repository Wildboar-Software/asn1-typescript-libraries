-- Module IN-SCF-CUSF-Datatypes (Q.1248.7:07/2001)
-- See also ITU-T Q.1248.7 (07/2001)
-- See also the index of all ASN.1 assignments needed in this document

IN-SCF-CUSF-Datatypes {itu-t recommendation q 1248 modules(1)
  in-scf-cusf-datatypes(24) version1(0)} DEFINITIONS IMPLICIT TAGS ::=
BEGIN

IMPORTS
  ros-InformationObjects, common-classes, common-datatypes, ssf-scf-classes,
    scf-cusf-classes, ssf-scf-datatypes
    FROM IN-object-identifiers {itu-t recommendation q 1248 modules(1)
      in-object-identifiers(0) version1(0)}
  COMMON-BOUNDS
    FROM IN-common-classes common-classes
  Extensions
    FROM IN-common-datatypes common-datatypes
  SCF-SSF-BOUNDS
    FROM IN-SSF-SCF-Classes ssf-scf-classes
  SCF-CUSF-BOUNDS
    FROM IN-SCF-CUSF-Classes scf-cusf-classes
  BearerCapability, CalledPartyNumber, CallingPartyNumber,
    CallingPartySubaddress, Cause, GenericNumbers,
    HighLayerCompatibility, LocationNumber, MonitorMode,
    ServiceAddressInformation, TerminalType, USIInformation,
    USIServiceIndicator
    FROM IN-SSF-SCF-datatypes ssf-scf-datatypes;

-- The following three definitions are local short-hand notation for convenience.
B1 ::=
  COMMON-BOUNDS --defined in Q.1248.1(Part 1 of Recommendation Q.1248)

B2 ::= SCF-SSF-BOUNDS --defined in Q.1248.2(Part 2 of Recommendation Q.1248)

B7 ::= SCF-CUSF-BOUNDS --defined in this Recommendation(Q.1248.7)

BCUSMEvent ::= SEQUENCE {
  eventType    [0]  EventTypeBCUSM,
  monitorMode  [1]  MonitorMode,
  ...
}

CallUnrelatedDpSpecificCommonParameters ::= SEQUENCE {
  serviceAddressInformation  [0]  ServiceAddressInformation,
  callingPartyNumber         [1]  CallingPartyNumber OPTIONAL,
  locationNumber             [2]  LocationNumber OPTIONAL,
  terminalType               [3]  TerminalType DEFAULT isdn,
  extensions                 [4]  Extensions OPTIONAL,
  uSIServiceIndicator        [5]  USIServiceIndicator OPTIONAL,
  uSIInformation             [6]  USIInformation OPTIONAL,
  cUApplicationInd           [7]  CUApplicationInd OPTIONAL,
  calledPartyNumber          [8]  CalledPartyNumber OPTIONAL,
  callingPartySubadress      [9]  CallingPartySubaddress OPTIONAL,
  highLayerCompatibility     [10]  HighLayerCompatibility OPTIONAL,
  bearerCapability           [11]  BearerCapability OPTIONAL,
  genericNumbers             [12]  GenericNumbers OPTIONAL,
  ...
}

CUApplicationInd ::= CHOICE {
  localValue   [0]  INTEGER,
  globalValue  [1]  OBJECT IDENTIFIER
}

EventSpecificInformationBCUSM ::= CHOICE {
  componentReceivedSpecificInfo
    [0]  SEQUENCE {componentReceivedInfo
                     [0]  OCTET STRING
                             OPTIONAL,
                   ...},
  associationReleaseRequestedSpecificInfo
    [1]  SEQUENCE {associationReleaseInfo
                     [0]  OCTET STRING
                             OPTIONAL,
                   releaseCause            [1]  Cause OPTIONAL,
                   ...}
}

--For the OCTET STRING type parameters (componentReceivedInfo and associationReleaseInfo),
--its content is network operator specific. The internal coding of this parameter can be defined using ASN.1 and
--the related Basic Encoding Rules (BER). In such a case the value of this parameter (after the first tag and length
--information) is the BER encoding of the defined ASN.1 internal structure. The tag of this parameter as defined by
--ITU-T is never replaced.
EventTypeBCUSM ::= ENUMERATED {
  componentReceived(127), associationReleaseRequested(126),
  activationReceivedAndAuthorized(125)}

Message ::= ENUMERATED {rELease(77), rELeaseCOMPlete(90), fACility(98)}

END

-- Generated by Asnp, the ASN.1 pretty-printer of France Telecom R&D
