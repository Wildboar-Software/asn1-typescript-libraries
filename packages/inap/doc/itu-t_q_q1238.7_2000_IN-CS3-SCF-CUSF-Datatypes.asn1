-- Module IN-CS3-SCF-CUSF-Datatypes (Q.1238.7:06/2000)
-- See also ITU-T Q.1238.7 (06/2000)
-- See also the index of all ASN.1 assignments needed in this document

-- 13	ASN.1 DEFINITIONS
--
-- 13.1	DATA TYPES
-- This clause specifies the data type definitions of parameters used in CUSF-SCF relationship.
-- Refer to the other parts of this Recommendation for the other data type definitions
-- not specified in this clause.
IN-CS3-SCF-CUSF-Datatypes {itu-t recommendation q 1238 modules(1)
  in-cs3-scf-cusf-datatypes(24) version1(0)} DEFINITIONS IMPLICIT TAGS ::=
BEGIN

IMPORTS
  ros-InformationObjects, common-classes, common-datatypes, ssf-scf-classes,
    scf-cusf-classes, ssf-scf-datatypes
    FROM IN-CS3-object-identifiers {itu-t recommendation q 1238 modules(1)
      in-cs3-object-identifiers(0) version1(0)}
  COMMON-BOUNDS
    FROM IN-CS3-common-classes {itu-t recommendation q 1238 modules(1)
      in-cs3-common-classes(5) version1(0)}
  Extensions
    FROM IN-CS3-common-datatypes {itu-t recommendation q 1238 modules(1)
      in-cs3-common-datatypes(1) version1(0)}
  SCF-SSF-BOUNDS
    FROM IN-CS3-SSF-SCF-Classes {itu-t recommendation q 1238 modules(1)
      in-cs3-ssf-scf-classes(7) version1(0)}
  SCF-CUSF-BOUNDS
    FROM IN-CS3-SCF-CUSF-Classes {itu-t recommendation q 1238 modules(1)
      in-cs3-scf-cusf-classes(25) version1(0)}
  BearerCapability, CalledPartyNumber, CallingPartyNumber,
    CallingPartySubaddress, Cause, GenericNumbers,
    HighLayerCompatibility, LocationNumber, MonitorMode,
    ServiceAddressInformation, TerminalType, USIInformation,
    USIServiceIndicator
    FROM IN-CS3-SSF-SCF-datatypes {itu-t recommendation q 1238 modules(1)
      in-cs3-ssf-scf-datatypes(6) version1(0)};

-- The following three definitions are local short-hand notation for convenience.
B1 ::=
  COMMON-BOUNDS --defined in Recommendation Q.1238.1

B2 ::= SCF-SSF-BOUNDS --defined in Recommendation Q.1238.2

B7 ::= SCF-CUSF-BOUNDS --defined in Recommendation Q.1238.7

BCUSMEvent ::= SEQUENCE {
  eventType    [0]  EventTypeBCUSM,
  monitorMode  [1]  MonitorMode,
  ...
}

CallUnrelatedDpSpecificCommonParameters ::= SEQUENCE {
  serviceAddressInformation  [0]  ServiceAddressInformation,
  callingPartyNumber         [1]  CallingPartyNumber OPTIONAL,
  locationNumber             [2]  LocationNumber OPTIONAL,
  terminalType               [3]  TerminalType DEFAULT isdn,
  extensions                 [4]  Extensions OPTIONAL,
  uSIServiceIndicator        [5]  USIServiceIndicator OPTIONAL,
  uSIInformation             [6]  USIInformation OPTIONAL,
  cUApplicationInd           [7]  CUApplicationInd OPTIONAL,
  calledPartyNumber          [8]  CalledPartyNumber OPTIONAL,
  callingPartySubadress      [9]  CallingPartySubaddress OPTIONAL,
  highLayerCompatibility     [10]  HighLayerCompatibility OPTIONAL,
  bearerCapability           [11]  BearerCapability OPTIONAL,
  genericNumbers             [12]  GenericNumbers OPTIONAL,
  ...
}

CUApplicationInd ::= CHOICE {
  localValue   [0]  INTEGER,
  globalValue  [1]  OBJECT IDENTIFIER
}

EventSpecificInformationBCUSM ::= CHOICE {
  componentReceivedSpecificInfo
    [0]  SEQUENCE {componentReceivedInfo
                     [0]  OCTET STRING
                             OPTIONAL,
                   ...},
  associationReleaseRequestedSpecificInfo
    [1]  SEQUENCE {associationReleaseInfo
                     [0]  OCTET STRING
                             OPTIONAL,
                   releaseCause            [1]  Cause OPTIONAL,
                   ...}
}

-- For the OCTET STRING type parameters (componentReceivedInfo and associationReleaseInfo),
-- its content is network operator specific. The internal coding of this parameter can be defined using ASN.1 and
-- the related Basic Encoding Rules (BER). In such a case the value of this parameter (after the first tag and length
-- information) is the BER encoding of the defined ASN.1 internal structure. The tag of this parameter as defined by
-- ITU-T is never replaced.
EventTypeBCUSM ::= ENUMERATED {
  componentReceived(127), associationReleaseRequested(126),
  activationReceivedAndAuthorized(125)}

Message ::= ENUMERATED {rELease(77), rELeaseCOMPlete(90), fACility(98)}

END

-- Generated by Asnp, the ASN.1 pretty-printer of France Telecom R&D
