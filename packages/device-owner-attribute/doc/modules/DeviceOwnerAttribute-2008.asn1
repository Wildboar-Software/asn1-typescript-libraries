DeviceOwnerAttribute-2008
    { joint-iso-ccitt(2) country(16) us(840) organization(1) gov(101)
    dod(2) infosec(1) module(0) id-deviceOwnerAttribute-2008(34) }

DEFINITIONS IMPLICIT TAGS ::=

BEGIN

-- EXPORTS ALL --

IMPORTS

-- IMPORTS from New PKIX ASN.1 [RFC5912]

    ATTRIBUTE
    FROM PKIX-CommonTypes-2009
        { iso(1) identified-organization(3) dod(6) internet(1)
        security(5) mechanisms(5) pkix(7) id-mod(0)
        id-mod-pkixCommon-02(57) }

-- Imports from ITU-T X.501 [X.501]

    objectIdentifierMatch
    FROM InformationFramework
        { joint-iso-itu-t ds(5) module(1) informationFramework(1) 4 }

;

-- device owner attribute OID and syntax

id-deviceOwner OBJECT IDENTIFIER ::= {
    joint-iso-ccitt(2) country(16) us(840) organization(1) gov(101)
    dod(2) infosec(1) attributes(5) 69
}

at-deviceOwner ATTRIBUTE ::= {
    TYPE                     OBJECT IDENTIFIER
    EQUALITY MATCHING RULE   objectIdentifierMatch
    IDENTIFIED BY            id-deviceOwner
}

END
