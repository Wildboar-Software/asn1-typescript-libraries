IEC61850 DEFINITIONS ::= BEGIN

SampledValues ::= CHOICE {
	savPdu	[APPLICATION 0]	IMPLICIT SavPdu,
	...
}

SavPdu ::= SEQUENCE {
	noASDU	[0] IMPLICIT INTEGER(0..65535),
	seqASDU	[2] IMPLICIT SEQUENCE OF ASDU
}

ASDU ::= SEQUENCE {
	svID		[0] IMPLICIT VisibleString,
	datSet		[1] IMPLICIT VisibleString OPTIONAL,
	smpCnt		[2] IMPLICIT INTEGER(0..65535),
	confRev		[3] IMPLICIT INTEGER(0..4294967295),
	refrTm		[4] IMPLICIT UtcTime OPTIONAL,
	smpSynch	[5] IMPLICIT INTEGER{none(0),local(1),global(2)} OPTIONAL,
	smpRate		[6] IMPLICIT INTEGER(0..65535) OPTIONAL,
	seqData		[7] IMPLICIT Data,
	smpMod		[8] IMPLICIT INTEGER{
		samplesPerNormalPeriod(0),
		samplesPerSecond(1),
		secondsPerSample(2)
	} OPTIONAL,
	gmidData	[9] IMPLICIT GmidData OPTIONAL,
	...
}

UtcTime ::= OCTET STRING
Data ::= OCTET STRING
GmidData ::= OCTET STRING

END
