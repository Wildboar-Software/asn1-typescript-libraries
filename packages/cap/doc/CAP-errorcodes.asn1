CAP-errorcodes {itu-t(0) identified-organization(4) etsi(0) mobileDomain(0) umts-network(1) modules(3) cap-errorcodes(57) version8(7)}

DEFINITIONS ::= BEGIN

IMPORTS

	ros-InformationObjects
FROM CAP-object-identifiers {itu-t(0) identified-organization(4) etsi(0) mobileDomain(0)
umts-network(1) modules(3) cap-object-identifiers(100) version8(7)}

	Code
FROM Remote-Operations-Information-Objects ros-InformationObjects

;

errcode-canceled				Code ::= local: 0
errcode-cancelFailed				Code ::= local: 1
errcode-eTCFailed				Code ::= local: 3
errcode-improperCallerResponse			Code ::= local: 4
errcode-missingCustomerRecord			Code ::= local: 6
errcode-missingParameter			Code ::= local: 7
errcode-parameterOutOfRange			Code ::= local: 8
errcode-requestedInfoError			Code ::= local: 10
errcode-systemFailure				Code ::= local: 11
errcode-taskRefused				Code ::= local: 12
errcode-unavailableResource			Code ::= local: 13
errcode-unexpectedComponentSequence		Code ::= local: 14
errcode-unexpectedDataValue			Code ::= local: 15
errcode-unexpectedParameter			Code ::= local: 16
errcode-unknownLegID				Code ::= local: 17
errcode-unknownPDPID				Code ::= local: 50
errcode-unknownCSID				Code ::= local: 51

END
