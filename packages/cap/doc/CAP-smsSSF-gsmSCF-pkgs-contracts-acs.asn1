CAP-smsSSF-gsmSCF-pkgs-contracts-acs {itu-t(0) identified-organization(4) etsi(0) mobileDomain(0) umts-network(1) modules(3) cap-smsSSF-gsmSCF-pkgs-contracts-acs(106) version8(7)}

DEFINITIONS ::= BEGIN

-- This module specifies the Operation Packages, Contracts, Application Contexts
-- and Abstract Syntaxes used for the smsSSF – gsmSCF interface, for the
-- control of MO-SMS and MT-SMS.

-- The table in subclause 2.1 lists the specifications that contain the modules
-- that are used by CAP.

IMPORTS

	PARAMETERS-BOUND,
	cAPSpecificBoundSet
FROM CAP-classes classes 
-- Elements that exist in cAPSpecificBoundSet in Rel-5 are not changed in Rel-6. As a
-- result, the value range of data type definitions in Rel-5 are not changed in Rel-6.

	CONTRACT,
	OPERATION-PACKAGE,
	OPERATION
FROM Remote-Operations-Information-Objects ros-InformationObjects

	TCMessage {} 
FROM TCAPMessages tc-Messages

	APPLICATION-CONTEXT,
	dialogue-abstract-syntax
FROM TC-Notation-Extensions tc-NotationExtensions

	connectSMS{},
	continueSMS,
	eventReportSMS{},
	furnishChargingInformationSMS{},
	initialDPSMS{},
	releaseSMS,
	requestReportSMSEvent{},
	resetTimerSMS{}
FROM CAP-SMS-ops-args sms-Operations
-- Object Identifier 'sms-Operations' is updated to version8(7) in Rel-6. As a result,
-- the present module, 'CAP-smsSSF-gsmSCF-pkgs-contracts-acs', IMPORTS CAP Operation
-- definitions from CAP-SMS-ops-args version8(7). Operation definitions are used in the
-- ABSTRACT SYNTAX definitions and in the OPERATION PACKAGE definitions.

	id-ac-cap3-sms-AC,
	id-ac-cap4-sms-AC,
-- The APPLICATION-CONTEXT Identifiers for CAP V3 and CAP V4 for SMS in Rel-6 are the same as
-- in Rel-5.

	id-cap3SmsSsfTogsmScf,
	id-cap4SmsSsfTogsmScf,
-- The CONTRACT Identifiers for CAP V3 and CAP V4 for SMS in Rel-6 are the same as in Rel-5.

	id-package-smsActivation,
	id-package-smsConnect,
	id-package-smsContinue,
	id-package-smsRelease,
	id-package-smsEventHandling, 
	id-package-smsBilling, 
	id-package-smsTimer,
-- The OPERATION-PACKAGE Identifiers for CAP V3 and CAP V4 for SMS in Rel-6 are the same as
-- in Rel-5.

	sms-Operations,
-- Object Identifier sms-Operations is updated to version8(7) in Rel-6. As a result, the present
-- module, 'CAP-smsSSF-gsmSCF-pkgs-contracts-acs', IMPORTS Rel-6 versions of the CAP Operation
-- definitions.

	tc-NotationExtensions,
	tc-Messages,
	ros-InformationObjects,
	classes,

	id-as-smsSSF-gsmSCF-AS
-- The ABSTRACT-SYNTAX Identifiers for CAP V3 and CAP V4 for SMS in Rel-6 are the same as
-- in Rel-5.

FROM CAP-object-identifiers {itu-t(0) identified-organization(4) etsi(0) mobileDomain(0)
umts-network(1) modules(3) cap-object-identifiers(100) version8(7)}

;

-- Application Contexts

-- Rel-6 uses the same Application Context versions for SMS as Rel-5. The CONTRACT and ABSTRACT
-- SYNTAXES for SMS are defined in Rel-6.

-- Refer to ITU-T Recommendation Q.775 for the formal definition of APPLICATION-CONTEXT.
-- The structured DIALOGUE MODE is defined in ITU-T Recommendation Q.771; the
-- dialogue-abstract-syntax ABSTRACT SYNTAX is defined in ITU-T Recommendation Q.775.

cap3-sms-AC APPLICATION-CONTEXT ::= {
	CONTRACT			cap3SMS
	DIALOGUE MODE		structured
	ABSTRACT SYNTAXES		{dialogue-abstract-syntax |
				sms-AbstractSyntax} 
	APPLICATION CONTEXT NAME	id-ac-cap3-sms-AC}
-- This application context shall be used for CAMEL support of MO-SMS.
-- 'cap3SMS' and 'sms-AbstractSyntax' are defined in the present module.

cap4-sms-AC APPLICATION-CONTEXT ::= {
	CONTRACT			cap4SMS
	DIALOGUE MODE		structured
	ABSTRACT SYNTAXES		{dialogue-abstract-syntax |
				sms-AbstractSyntax} 
	APPLICATION CONTEXT NAME	id-ac-cap4-sms-AC}
-- This application context shall be used for CAMEL support of MT-SMS.
-- 'cap4SMS' and 'sms-AbstractSyntax' are defined in the present module.


-- Contracts
-- The CONTRACT definitions for SMS in Rel-6 use OPERATION-PACKAGE definitions which are
-- defined in Rel-6.

cap3SMS CONTRACT ::= {
-- dialogue initiated by gprsSSF or gsmSSF with InitialDPSMS Operation
	INITIATOR CONSUMER OF	{smsActivationPackage {cAPSpecificBoundSet}}
	RESPONDER CONSUMER OF	{smsConnectPackage {cAPSpecificBoundSet} |
				smsReleasePackage |
				smsEventHandlingPackage {cAPSpecificBoundSet} |
				smsTimerPackage {cAPSpecificBoundSet} |
				smsBillingPackage {cAPSpecificBoundSet} |
				smsProcessingPackage}
	ID				id-cap3SmsSsfTogsmScf}
-- The OPERATION-PACKAGEs are defined in the present module.

cap4SMS CONTRACT ::= {
-- dialogue initiated by gprsSSF or gsmSSF with InitialDPSMS Operation
	INITIATOR CONSUMER OF	{smsActivationPackage {cAPSpecificBoundSet}}
	RESPONDER CONSUMER OF	{smsConnectPackage {cAPSpecificBoundSet} |
				smsReleasePackage |
				smsEventHandlingPackage {cAPSpecificBoundSet} |
				smsTimerPackage {cAPSpecificBoundSet} |
				smsBillingPackage {cAPSpecificBoundSet} |
				smsProcessingPackage }
	ID				id-cap4SmsSsfTogsmScf}
-- The OPERATION-PACKAGEs are defined in the present module.


-- Operation Packages
-- The OPERATION-PACKAGE definitions for SMS in Rel-6 use Operation definitions from Rel-6. The
-- OPERATION definitions are IMPORTED from CAP-SMS-ops-args.

smsActivationPackage {PARAMETERS-BOUND : bound} OPERATION-PACKAGE ::= {
	CONSUMER INVOKES	{initialDPSMS {bound}}
	ID			id-package-smsActivation}

smsConnectPackage {PARAMETERS-BOUND : bound} OPERATION-PACKAGE ::= {
	CONSUMER INVOKES	{connectSMS {bound}}
	ID			id-package-smsConnect}

smsProcessingPackage OPERATION-PACKAGE ::= {
	CONSUMER INVOKES	{continueSMS}
	ID			id-package-smsContinue}

smsReleasePackage OPERATION-PACKAGE ::= {
	CONSUMER INVOKES	{releaseSMS}
	ID			id-package-smsRelease}

smsEventHandlingPackage {PARAMETERS-BOUND : bound} OPERATION-PACKAGE ::= {
	CONSUMER INVOKES	{requestReportSMSEvent {bound}}
	SUPPLIER INVOKES	{eventReportSMS {bound}}
	ID			id-package-smsEventHandling}

smsBillingPackage {PARAMETERS-BOUND : bound} OPERATION-PACKAGE ::= {
	CONSUMER INVOKES	{furnishChargingInformationSMS {bound}}
	ID			id-package-smsBilling}

smsTimerPackage {PARAMETERS-BOUND : bound} OPERATION-PACKAGE ::= {
	CONSUMER INVOKES	{resetTimerSMS {bound}}
	ID			id-package-smsTimer}


-- Abstract Syntaxes

-- SmsInvokable and SmsReturnable use OPERATION definitions with version8(7). As a result,
-- Generic-sms-PDUs uses version8(7) OPERATION definitions. As a subsequent result,
-- sms-AbstractSyntax uses version8(7) OPERATION definitions. That ABSTRACT-SYNTAX is used
-- in the cap3-sms-AC APPLICATION-CONTEXT definition and in the and cap4-sms-AC APPLICATION-
-- CONTEXT definition (CAP from smsSSF to gsmSCF).

sms-AbstractSyntax ABSTRACT-SYNTAX ::= {
	Generic-sms-PDUs
	IDENTIFIED BY	id-as-smsSSF-gsmSCF-AS }
-- 'Generic-sms-PDUs' is defined in the present module.

Generic-sms-PDUs ::= TCMessage {{SmsInvokable},
				{SmsReturnable}}
-- 'SmsInvokable' and 'SmsReturnable' are defined in the present module.

SmsInvokable OPERATION ::= {
	connectSMS {cAPSpecificBoundSet} |
	eventReportSMS {cAPSpecificBoundSet} |
	furnishChargingInformationSMS {cAPSpecificBoundSet} |
	initialDPSMS {cAPSpecificBoundSet} |
	requestReportSMSEvent {cAPSpecificBoundSet} |
	resetTimerSMS {cAPSpecificBoundSet}}
-- The OPERATION definitions are IMPORTED from CAP-SMS-ops-args version8(7).

SmsReturnable OPERATION ::= {
	connectSMS {cAPSpecificBoundSet} |
	continueSMS |
	furnishChargingInformationSMS {cAPSpecificBoundSet} |
	initialDPSMS {cAPSpecificBoundSet} |
	releaseSMS |
	requestReportSMSEvent {cAPSpecificBoundSet} |
	resetTimerSMS {cAPSpecificBoundSet}}
-- The OPERATION definitions are IMPORTED from CAP-SMS-ops-args version8(7).

END
