-- Module IPMSExtendedVoiceBodyPartType (X.420:06/1999)
-- See also ITU-T X.420 (06/1999)
-- See also the index of all ASN.1 assignments needed in this document

IPMSExtendedVoiceBodyPartType {joint-iso-itu-t mhs(6) ipms(1) modules(0)
  extended-voice-body-part-type(11)} DEFINITIONS IMPLICIT TAGS ::=
BEGIN

-- Prologue
-- Exports everything.
IMPORTS
  -- IPMS Information Objects
  EXTENDED-BODY-PART-TYPE
    --==
    FROM IPMSInformationObjects {joint-iso-itu-t mhs(6) ipms(1) modules(0)
      information-objects(2) version-1999(1)}
  -- IPMS Object Identifiers
  id-ep-voice, id-et-voice
    --==
    FROM IPMSObjectIdentifiers {joint-iso-itu-t mhs(6) ipms(1) modules(0)
      object-identifiers(0) version-1999(1)};

-- Extended Voice body part
voice-body-part EXTENDED-BODY-PART-TYPE ::= {
  PARAMETERS  {VoiceParameters
               IDENTIFIED BY  id-ep-voice},
  DATA        {VoiceData
               IDENTIFIED BY  id-et-voice}
}

VoiceParameters ::= SEQUENCE {
  voice-message-duration     [0]  INTEGER OPTIONAL, -- In seconds
  voice-encoding-type        [1]  OBJECT IDENTIFIER,
  supplementary-information  [2]  IA5String OPTIONAL
}

VoiceData ::= OCTET STRING

END -- of IPMSExtendedVoiceBodyPartType

-- Generated by Asnp, the ASN.1 pretty-printer of France Telecom R&D
