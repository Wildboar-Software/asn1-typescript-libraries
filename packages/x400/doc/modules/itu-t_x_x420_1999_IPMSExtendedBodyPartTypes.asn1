-- Module IPMSExtendedBodyPartTypes (X.420:06/1999)
-- See also ITU-T X.420 (06/1999)
-- See also the index of all ASN.1 assignments needed in this document

IPMSExtendedBodyPartTypes {joint-iso-itu-t mhs(6) ipms(1) modules(0)
  extended-body-part-types(7) version-1994(0)} DEFINITIONS IMPLICIT TAGS ::=
BEGIN

-- Prologue
-- Exports everything.
IMPORTS
  -- IPMS Information Objects
  BilaterallyDefinedBodyPart, EncryptedData, EncryptedParameters,
    EXTENDED-BODY-PART-TYPE, G3FacsimileData, G3FacsimileParameters,
    G4Class1BodyPart, IA5TextData, IA5TextParameters, MessageData,
    MessageParameters, MixedModeBodyPart, NationallyDefinedBodyPart,
    TeletexData, TeletexParameters, VideotexData, VideotexParameters
    --==
    FROM IPMSInformationObjects {joint-iso-itu-t mhs(6) ipms(1) modules(0)
      information-objects(2) version-1999(1)}
  -- IPMS Object Identifiers
  id-ep-encrypted, id-ep-g3-facsimile, id-ep-ia5-text, id-ep-message,
    id-ep-teletex, id-ep-videotex, id-et-bilaterally-defined, id-et-encrypted,
    id-et-g3-facsimile, id-et-g4-class1, id-et-ia5-text, id-et-message,
    id-et-mixed-mode, id-et-nationally-defined, id-et-teletex, id-et-videotex
    --==
    FROM IPMSObjectIdentifiers {joint-iso-itu-t mhs(6) ipms(1) modules(0)
      object-identifiers(0) version-1999(1)};

-- Extended IA5 Text body part
ia5-text-body-part EXTENDED-BODY-PART-TYPE ::= {
  PARAMETERS  {IA5TextParameters
               IDENTIFIED BY  id-ep-ia5-text},
  DATA        {IA5TextData
               IDENTIFIED BY  id-et-ia5-text}
}

-- Extended G3 Facsimile body part
g3-facsimile-body-part EXTENDED-BODY-PART-TYPE ::= {
  PARAMETERS  {G3FacsimileParameters
               IDENTIFIED BY  id-ep-g3-facsimile},
  DATA        {G3FacsimileData
               IDENTIFIED BY  id-et-g3-facsimile}
}

-- Extended G4 Class 1 body part
g4-class1-body-part EXTENDED-BODY-PART-TYPE ::= {
  DATA  {G4Class1BodyPart
         IDENTIFIED BY  id-et-g4-class1}
}

-- Extended Teletex body part
teletex-body-part EXTENDED-BODY-PART-TYPE ::= {
  PARAMETERS  {TeletexParameters
               IDENTIFIED BY  id-ep-teletex},
  DATA        {TeletexData
               IDENTIFIED BY  id-et-teletex}
}

-- Extended Videotex body part
videotex-body-part EXTENDED-BODY-PART-TYPE ::= {
  PARAMETERS  {VideotexParameters
               IDENTIFIED BY  id-ep-videotex},
  DATA        {VideotexData
               IDENTIFIED BY  id-et-videotex}
}

-- Extended Encrypted body part
encrypted-body-part EXTENDED-BODY-PART-TYPE ::= {
  PARAMETERS  {EncryptedParameters
               IDENTIFIED BY  id-ep-encrypted},
  DATA        {EncryptedData
               IDENTIFIED BY  id-et-encrypted}
}

-- Extended Message body part
message-body-part EXTENDED-BODY-PART-TYPE ::= {
  PARAMETERS  {MessageParameters
               IDENTIFIED BY  id-ep-message},
  DATA        {MessageData
               IDENTIFIED BY  id-et-message}
}

-- Extended Mixed-mode body part
mixed-mode-body-part EXTENDED-BODY-PART-TYPE ::= {
  DATA  {MixedModeBodyPart
         IDENTIFIED BY  id-et-mixed-mode}
}

-- Extended Bilaterally Defined body part
bilaterally-defined-body-part EXTENDED-BODY-PART-TYPE ::= {
  DATA  {BilaterallyDefinedBodyPart
         IDENTIFIED BY  id-et-bilaterally-defined}
}

-- Extended Nationally Defined body part
nationally-defined-body-part EXTENDED-BODY-PART-TYPE ::= {
  DATA  {NationallyDefinedBodyPart
         IDENTIFIED BY  id-et-nationally-defined}
}

END -- of IPMSExtendedBodyPartTypes

-- Generated by Asnp, the ASN.1 pretty-printer of France Telecom R&D
