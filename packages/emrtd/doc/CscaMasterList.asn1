CscaMasterList
{joint-iso-itu-t(2) international-organization(23) icao(136) mrtd(1)
security(1) masterlist(2)}
DEFINITIONS IMPLICIT TAGS ::=
BEGIN
IMPORTS

    Certificate
        FROM AuthenticationFramework
        {joint-iso-itu-t ds(5) module(1) authenticationFramework(7) 9}
        WITH SUCCESSORS

    id-icao-mrtd-security
        FROM LDSSecurityObjectV1
        {joint-iso-itu-t(2) international(23) icao(136) mrtd(1) security(1)
        ldsSecurityObject(1)}

    ;

-- CSCA Master List

CscaMasterListVersion ::= INTEGER {v0(0)}

CscaMasterList ::= SEQUENCE {
    version     CscaMasterListVersion,
    certList    SET OF Certificate
}

-- Object Identifiers

id-icao-cscaMasterList              OBJECT IDENTIFIER ::= {id-icao-mrtd-security 2}
id-icao-cscaMasterListSigningKey    OBJECT IDENTIFIER ::= {id-icao-mrtd-security 3}

END
