Safecurves-pkix-18
{ iso(1) identified-organization(3) dod(6) internet(1)
    security(5) mechanisms(5) pkix(7) id-mod(0)
    id-mod-safecurves-pkix(93) }

DEFINITIONS EXPLICIT TAGS ::=
BEGIN

IMPORTS
    SIGNATURE-ALGORITHM, KEY-AGREE, PUBLIC-KEY, KEY-WRAP,
    KeyUsage, AlgorithmIdentifier
    FROM AlgorithmInformation-2009
    {iso(1) identified-organization(3) dod(6) internet(1) security(5)
    mechanisms(5) pkix(7) id-mod(0)
    id-mod-algorithmInformation-02(58)}

    mda-sha512
    FROM PKIX1-PSS-OAEP-Algorithms-2009
    { iso(1) identified-organization(3) dod(6) internet(1)
        security(5) mechanisms(5) pkix(7) id-mod(0)
        id-mod-pkix1-rsa-pkalgs-02(54) }

    kwa-aes128-wrap, kwa-aes256-wrap
    FROM CMSAesRsaesOaep-2009
    { iso(1) member-body(2) us(840) rsadsi(113549) pkcs(1) pkcs-9(9)
        smime(16) modules(0) id-mod-cms-aes-02(38) }
    ;

id-edwards-curve-algs OBJECT IDENTIFIER ::= { 1 3 101 }

id-X25519        OBJECT IDENTIFIER ::= { id-edwards-curve-algs 110 }
id-X448          OBJECT IDENTIFIER ::= { id-edwards-curve-algs 111 }
id-Ed25519       OBJECT IDENTIFIER ::= { id-edwards-curve-algs 112 }
id-Ed448         OBJECT IDENTIFIER ::= { id-edwards-curve-algs 113 }

sa-Ed25519 SIGNATURE-ALGORITHM ::= {
    IDENTIFIER id-Ed25519
    PARAMS ARE absent
    PUBLIC-KEYS {pk-Ed25519}
    SMIME-CAPS { IDENTIFIED BY id-Ed25519 }
}

pk-Ed25519 PUBLIC-KEY ::= {
    IDENTIFIER id-Ed25519
    -- KEY no ASN.1 wrapping --
    PARAMS ARE absent
    CERT-KEY-USAGE {digitalSignature, nonRepudiation,
                    keyCertSign, cRLSign}
    PRIVATE-KEY CurvePrivateKey
}

kaa-X25519 KEY-AGREE ::= {
    IDENTIFIER id-X25519
    PARAMS ARE absent
    PUBLIC-KEYS {pk-X25519}
    UKM -- TYPE no ASN.1 wrapping -- ARE preferredPresent
    SMIME-CAPS {
        TYPE AlgorithmIdentifier{KEY-WRAP, {KeyWrapAlgorithms}}
        IDENTIFIED BY id-X25519 }
}

pk-X25519 PUBLIC-KEY ::= {
    IDENTIFIER id-X25519
    -- KEY no ASN.1 wrapping --
    PARAMS ARE absent
    CERT-KEY-USAGE { keyAgreement }
    PRIVATE-KEY CurvePrivateKey
}

KeyWrapAlgorithms KEY-WRAP ::= {
    kwa-aes128-wrap | kwa-aes256-wrap,
    ...
}

kaa-X448 KEY-AGREE ::= {
    IDENTIFIER id-X448
    PARAMS ARE absent
    PUBLIC-KEYS {pk-X448}
    UKM -- TYPE no ASN.1 wrapping  -- ARE preferredPresent
    SMIME-CAPS {
        TYPE AlgorithmIdentifier{KEY-WRAP, {KeyWrapAlgorithms}}
        IDENTIFIED BY id-X448 }
}

pk-X448 PUBLIC-KEY ::= {
    IDENTIFIER id-X448
    -- KEY no ASN.1 wrapping --
    PARAMS ARE absent
    CERT-KEY-USAGE { keyAgreement }
    PRIVATE-KEY CurvePrivateKey
}

CurvePrivateKey ::= OCTET STRING

END
