Call-Intrusion-Notifications-asn1-97
{iso(1) standard(0) pss1-call-intrusion(14846)
call-intrusion-notifications-asn1-97(3)}
DEFINITIONS EXPLICIT TAGS ::=
BEGIN
IMPORTS

    NOTIFICATION
        FROM Notification-class-asn1-97
        {iso(1) standard(0) pss1-generic-procedures(11582)
        notification-class-asn1-97(21)}
    ;

remoteUserAlerting NOTIFICATION ::= {
    ARGUMENT NULL
    CODE local: 2000
}

intrusionIsImpending NOTIFICATION ::= {
    ARGUMENT NULL
    CODE local: 2003
}

intrusionIsEffective NOTIFICATION ::= {
    ARGUMENT NULL
    CODE local: 2004
}

isolationThroughIntrusion NOTIFICATION ::= {
    ARGUMENT NULL
    CODE local: 2005
}

forcedReleaseAfterIntrusion NOTIFICATION ::= {
    ARGUMENT NULL
    CODE local: 2006
}

endOfIntrusion NOTIFICATION ::= {
    ARGUMENT NULL
    CODE local: 2007
}

Call-Intrusion-Notifications NOTIFICATION ::= {
    remoteUserAlerting
    | intrusionIsImpending
    | intrusionIsEffective
    | isolationThroughIntrusion
    | forcedReleaseAfterIntrusion
    | endOfIntrusion
}

END                      --of Call-Intrusion-Notifications-asn1-97
