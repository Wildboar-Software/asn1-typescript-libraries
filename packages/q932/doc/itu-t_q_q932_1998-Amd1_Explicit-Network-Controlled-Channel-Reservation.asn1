-- Module Explicit-Network-Controlled-Channel-Reservation (Q.932:05/1998)
-- See also ITU-T Q.932 (1998) Amend. 1 (06/2000)
-- See also the index of all ASN.1 assignments needed in this document

Explicit-Network-Controlled-Channel-Reservation {itu-t recommendation
  q 932 explicit-network-controlled-channel-reservation(4)} DEFINITIONS ::=
BEGIN

EXPORTS
  explicitReservationCreationControl, explicitReservationManagement,
    explicitReservationCancel, maximumNumberOfReservationsReached,
    noExplicitReservationExistsOrInvalidReservationIndicator,
    unwantedReservationCreated, implicitReservationUsed, ReservationIndicator;

IMPORTS
  OPERATION, ERROR
    FROM Remote-Operations-Information-Objects {joint-iso-itu-t
      remote-operations(4) informationObjects(5) version1(0)}
  notAvailable, userNotSubscribed
    FROM General-Error-List {itu-t recommendation q 950 general-error-list(1)};

explicitReservationCreationControl OPERATION ::= {
  ARGUMENT
    SEQUENCE {controlOption
                ENUMERATED {noReservationRequired(0),
                            reservationRequiredWithReservationIndicator(1),
                            reservationRequiredWithoutReservationIndicator(2)}
  }
  RESULT    ReservationIndicator -- optional
  ERRORS
    {maximumNumberOfReservationsReached | notAvailable | userNotSubscribed |
      unwantedReservationCreated}
  CODE      local:20
}

explicitReservationManagement OPERATION ::= {
  ARGUMENT  ReservationIndicator -- optional
  -- 		RESULT
  ERRORS
    {noExplicitReservationExistsOrInvalidReservationIndicator | notAvailable |
      userNotSubscribed | implicitReservationUsed}
  CODE      local:21
}

explicitReservationCancel OPERATION ::= {
  ARGUMENT  ReservationIndicator -- optional
  --		RESULT
  ERRORS
    {noExplicitReservationExistsOrInvalidReservationIndicator | notAvailable |
      userNotSubscribed}
  CODE      local:22
}

maximumNumberOfReservationsReached ERROR ::= {CODE  local:33
}

noExplicitReservationExistsOrInvalidReservationIndicator ERROR ::= {
  CODE  local:34
}

unwantedReservationCreated ERROR ::= {CODE  local:35
}

implicitReservationUsed ERROR ::= {CODE  local:36
}

ReservationIndicator ::= INTEGER((-128..127))

END -- of Explicit-Network-Controlled-Channel-Reservation

-- Generated by Asnp, the ASN.1 pretty-printer of France Telecom R&D
