ERS { iso(1) identified-organization(3) dod(6) internet(1) security(5)
    mechanisms(5) ltans(11) id-mod(0) id-mod-ers(1) id-mod-ers-v1(1) }
DEFINITIONS IMPLICIT TAGS ::=
BEGIN

-- EXPORTS ALL --

IMPORTS

    -- Imports from PKCS-7
    ContentInfo
        FROM PKCS7
            {iso(1) member-body(2) us(840) rsadsi(113549) pkcs(1) pkcs-7(7) modules(0)}

        -- Imports from AuthenticationFramework
    AlgorithmIdentifier
        FROM AuthenticationFramework
            {joint-iso-itu-t ds(5) module(1) authenticationFramework(7) 4}


        -- Imports from InformationFramework
    Attribute
        FROM InformationFramework
            {joint-iso-itu-t ds(5) module(1) informationFramework(1) 4}
    ;

ltans OBJECT IDENTIFIER ::= { iso(1) identified-organization(3) dod(6)
    internet(1) security(5) mechanisms(5) ltans(11) }

EvidenceRecord ::= SEQUENCE {
    version                   INTEGER { v1(1) },
    digestAlgorithms          SEQUENCE OF AlgorithmIdentifier,
    cryptoInfos               [0] CryptoInfos OPTIONAL,
    encryptionInfo            [1] EncryptionInfo OPTIONAL,
    archiveTimeStampSequence  ArchiveTimeStampSequence }

CryptoInfos ::= SEQUENCE SIZE (1..MAX) OF Attribute
    (WITH COMPONENTS {
        ...,
        valuesWithContext   ABSENT
    })

ArchiveTimeStamp ::= SEQUENCE {
    digestAlgorithm     [0] AlgorithmIdentifier OPTIONAL,
    attributes          [1] Attributes OPTIONAL,
    reducedHashtree     [2] SEQUENCE OF PartialHashtree OPTIONAL,
    timeStamp           ContentInfo }

PartialHashtree ::= SEQUENCE OF OCTET STRING

Attributes ::= SET SIZE (1..MAX) OF Attribute
    (WITH COMPONENTS {
        ...,
        valuesWithContext   ABSENT
    })

ArchiveTimeStampChain    ::= SEQUENCE OF ArchiveTimeStamp

ArchiveTimeStampSequence ::= SEQUENCE OF ArchiveTimeStampChain

EncryptionInfo       ::=     SEQUENCE {
    encryptionInfoType   ENCINFO-TYPE.&id({SupportedEncryptionAlgorithms}),
    encryptionInfoValue  ENCINFO-TYPE.&Type
                ({SupportedEncryptionAlgorithms}{@encryptionInfoType}) }

ENCINFO-TYPE ::= TYPE-IDENTIFIER

SupportedEncryptionAlgorithms ENCINFO-TYPE ::= {...}

id-aa-er-internal  OBJECT IDENTIFIER ::= { iso(1) member-body(2)
    us(840) rsadsi(113549) pkcs(1) pkcs9(9) smime(16) id-aa(2) 49 }

id-aa-er-external  OBJECT IDENTIFIER ::= { iso(1) member-body(2)
    us(840) rsadsi(113549) pkcs(1) pkcs9(9) smime(16) id-aa(2) 50 }

END
