-- Lightweight Presentation Protocol from IETF RFC 1085
-- See: https://datatracker.ietf.org/doc/html/rfc1085
RFC1085-PS DEFINITIONS ::= BEGIN

PDUs ::= CHOICE {
    connectRequest      ConnectRequest-PDU,
    connectResponse     ConnectResponse-PDU,
    releaseRequest      ReleaseRequest-PDU,
    releaseResponse     ReleaseResponse-PDU,
    abort               Abort-PDU,
    userData            UserData-PDU,
    cL-userData         CL-UserData-PDU
}

-- connect request PDU

ConnectRequest-PDU ::= [0] IMPLICIT SEQUENCE {
    -- version-1 corresponds to to this memo
    version     [0] IMPLICIT INTEGER { version-1(0) },
    reference   SessionConnectionIdentifier,
    calling     PresentationSelector OPTIONAL,
    called      [2] IMPLICIT PresentationSelector OPTIONAL,
    -- the ASN for PCI #1
    asn         [3] IMPLICIT OBJECT IDENTIFIER,
    user-data   UserData-PDU
}

SessionConnectionIdentifier ::= [0] SEQUENCE {
    callingSSUserReference          T61String,
    commonReference                 UTCTime,
    additionalReferenceInformation  [0] IMPLICIT T61String OPTIONAL
}

PresentationSelector ::= [1] IMPLICIT OCTET STRING

-- connect response PDU

ConnectResponse-PDU ::= [1] IMPLICIT SEQUENCE {
    -- present only in the udp-based service
    reference   SessionConnectionIdentifier OPTIONAL,
    responding  PresentationSelector OPTIONAL,
    -- present only if the connection was rejected
    reason      [2] IMPLICIT Rejection-reason OPTIONAL,
    -- present only if reason is absent OR has the value rejected-by-responder
    user-data   UserData-PDU OPTIONAL
}

Rejection-reason ::= INTEGER {
    rejected-by-responder               (0),
    called-presentation-address-unknown (1),
    local-limit-exceeded                (3),
    protocol-version-not-supported      (4)
}

-- release request PDU

ReleaseRequest-PDU ::= [2] IMPLICIT SEQUENCE {
    -- present only in the udp-based service
    reference   SessionConnectionIdentifier OPTIONAL,
    user-data   UserData-PDU
}

-- release response PDU

ReleaseResponse-PDU ::= [3] IMPLICIT SEQUENCE {
    -- present only in the udp-based service
    reference   SessionConnectionIdentifier OPTIONAL,
    user-data   UserData-PDU
}

-- abort PDU

Abort-PDU ::= [4] SEQUENCE {
    -- present only in the udp-based service
    reference   SessionConnectionIdentifier OPTIONAL,
    -- MAY BE present on user-initiated abort
    user-data   UserData-PDU OPTIONAL,
    -- ALWAYS present on provider-initiated abort
    reason      [1] IMPLICIT Abort-reason OPTIONAL
}

Abort-reason ::= INTEGER {
    unspecified                 (0),
    unrecognized-ppdu           (1),
    unexpected-ppdu             (2),
    unrecognized-ppdu-parameter (4),
    invalid-ppdu-parameter      (5),
    reference-mismatch          (9)
}

-- data PDU

UserData-PDU ::= [5] ANY
-- this is the ASN.1 object
-- if it is a top-level PDU, it
-- is in PCI #1, otherwise PCI #3

-- data PDU for the udp-based service

CL-UserData-PDU ::= [6] IMPLICIT SEQUENCE {
    reference   SessionConnectionIdentifier,
    user-data   [0] ANY -- this is the ASN.1 object it is always in PCI #1
}

END
