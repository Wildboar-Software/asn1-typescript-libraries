-- Modified by Jonathan M. Wilbur to fix invalid syntax.
--      Expanded ASN1 Module 'LCSChargingDataTypes'
--SIEMENS ASN.1 Compiler         R6.31  (Production_6.31)
--            Date: 2020-07-10 Time: 16:15:24

LCSChargingDataTypes
{itu-t(0) identified-organization(4) etsi(0) mobileDomain(0) charging(5)
lcsChargingDataTypes(6) asn1Module(0) version2(1)}
DEFINITIONS
::=
BEGIN

RecordType ::= INTEGER {
   moCallRecord              ( 0 ),
   mtCallRecord              ( 1 ),
   roamingRecord             ( 2 ),
   incGatewayRecord          ( 3 ),
   outGatewayRecord          ( 4 ),
   transitCallRecord         ( 5 ),
   moSMSRecord               ( 6 ),
   mtSMSRecord               ( 7 ),
   moSMSIWRecord             ( 8 ),
   mtSMSGWRecord             ( 9 ),
   ssActionRecord            ( 10 ),
   hlrIntRecord              ( 11 ),
   locUpdateHLRRecord        ( 12 ),
   locUpdateVLRRecord        ( 13 ),
   commonEquipRecord         ( 14 ),
   moTraceRecord             ( 15 ),
   mtTraceRecord             ( 16 ),
   termCAMELRecord           ( 17 ),
   sgsnPDPRecord             ( 18 ),
   sgsnMMRecord              ( 20 ),
   sgsnSMORecord             ( 21 ),
   sgsnSMTRecord             ( 22 ),
   mtLCSRecord               ( 23 ),
   moLCSRecord               ( 24 ),
   niLCSRecord               ( 25 ),
   sgsnMTLCSRecord           ( 26 ),
   sgsnMOLCSRecord           ( 27 ),
   sgsnNILCSRecord           ( 28 ),
   mMO1SRecord               ( 30 ),
   mMO4FRqRecord             ( 31 ),
   mMO4FRsRecord             ( 32 ),
   mMO4DRecord               ( 33 ),
   mMO1DRecord               ( 34 ),
   mMO4RRecord               ( 35 ),
   mMO1RRecord               ( 36 ),
   mMOMDRecord               ( 37 ),
   mMR4FRecord               ( 38 ),
   mMR1NRqRecord             ( 39 ),
   mMR1NRsRecord             ( 40 ),
   mMR1RtRecord              ( 41 ),
   mMR1AFRecord              ( 42 ),
   mMR4DRqRecord             ( 43 ),
   mMR4DRsRecord             ( 44 ),
   mMR1RRRecord              ( 45 ),
   mMR4RRqRecord             ( 46 ),
   mMR4RRsRecord             ( 47 ),
   mMRMDRecord               ( 48 ),
   mMFRecord                 ( 49 ),
   mMBx1SRecord              ( 50 ),
   mMBx1VRecord              ( 51 ),
   mMBx1URecord              ( 52 ),
   mMBx1DRecord              ( 53 ),
   mM7SRecord                ( 54 ),
   mM7DRqRecord              ( 55 ),
   mM7DRsRecord              ( 56 ),
   mM7CRecord                ( 57 ),
   mM7RRecord                ( 58 ),
   mM7DRRqRecord             ( 59 ),
   mM7DRRsRecord             ( 60 ),
   mM7RRqRecord              ( 61 ),
   mM7RRsRecord              ( 62 ),
   sCSCFRecord               ( 63 ),
   pCSCFRecord               ( 64 ),
   iCSCFRecord               ( 65 ),
   mRFCRecord                ( 66 ),
   mGCFRecord                ( 67 ),
   bGCFRecord                ( 68 ),
   aSRecord                  ( 69 ),
   eCSCFRecord               ( 70 ),
   iBCFRecord                ( 82 ),
   tRFRecord                 ( 89 ),
   tFRecord                  ( 90 ),
   aTCFRecord                ( 91 ),
   lCSGMORecord              ( 71 ),
   lCSRGMTRecord             ( 72 ),
   lCSHGMTRecord             ( 73 ),
   lCSVGMTRecord             ( 74 ),
   lCSGNIRecord              ( 75 ),
   sgsnMBMSRecord            ( 76 ),
   ggsnMBMSRecord            ( 77 ),
   gwMBMSRecord              ( 86 ),
   sUBBMSCRecord             ( 78 ),
   cONTENTBMSCRecord         ( 79 ),
   pPFRecord                 ( 80 ),
   cPFRecord                 ( 81 ),
   sGWRecord                 ( 84 ),
   pGWRecord                 ( 85 ),
   tDFRecord                 ( 92 ),
   iPERecord                 ( 95 ),
   ePDGRecord                ( 96 ),
   tWAGRecord                ( 97 ),
   mMTelRecord               ( 83 ),
   mSCsRVCCRecord            ( 87 ),
   mMTRFRecord               ( 88 ),
   iCSRegisterRecord         ( 99 ),
   sCSMORecord               ( 93 ),
   sCSMTRecord               ( 94 ),
   pFDDRecord                ( 100 ),
   pFEDRecord                ( 101 ),
   pFDCRecord                ( 102 ),
   mECORecord                ( 103 ),
   mERERecord                ( 104 ),
   cPDTSCERecord             ( 105 ),
   cPDTSNNRecord             ( 106 ),
   sCDVTT4Record             ( 110 ),
   sCSMOT4Record             ( 111 ),
   iSMSMORecord              ( 112 ),
   iSMSMTRecord              ( 113 ),
   eASCERecord               ( 120 ),
   chargingFunctionRecord    ( 200 )}

LCSClientType ::= ENUMERATED {
   emergencyServices          ( 0 ),
   valueAddedServices         ( 1 ),
   plmnOperatorServices       ( 2 ),
   lawfulInterceptServices    ( 3 ),
   ...  }

Pcs-Extensions ::= SEQUENCE {
   ... }

IPBinV6AddressWithPrefixLength ::= SEQUENCE {
   iPBinV6Address           OCTET STRING ( SIZE( 16 ) ),
   pDPAddressPrefixLength   INTEGER ( 1 .. 64 ) DEFAULT 64}

IPTextRepresentedAddress ::= CHOICE {
   iPTextV4Address     [2] IMPLICIT IA5String  ( SIZE( 7 .. 15 ) ),
   iPTextV6Address     [3] IMPLICIT IA5String  ( SIZE( 15 .. 45 ) )}

IPBinV6AddressWithOrWithoutPrefixLength ::= CHOICE {
   iPBinV6Address               [1] IMPLICIT OCTET STRING ( SIZE( 16 ) ),
   iPBinV6AddressWithPrefix     [4] IMPLICIT IPBinV6AddressWithPrefixLength}

IPBinaryAddress ::= CHOICE {
   iPBinV4Address     [0] IMPLICIT OCTET STRING ( SIZE( 4 ) ),
   iPBinV6Address     IPBinV6AddressWithOrWithoutPrefixLength}

IPAddress ::= CHOICE {
   iPBinaryAddress              IPBinaryAddress,
   iPTextRepresentedAddress     IPTextRepresentedAddress}

PrivateExtension ::= SEQUENCE {
   extId      MAP-EXTENSION.&extensionId ({ExtensionSet}) ,
   extType    MAP-EXTENSION.&ExtensionType ({ExtensionSet}{@extId})  OPTIONAL}

ExtensionContainer ::= SEQUENCE {
   privateExtensionList   [0] IMPLICIT SEQUENCE  ( SIZE( 1 .. 10 ) ) OF
      PrivateExtension OPTIONAL,
   pcs-Extensions         [1] IMPLICIT Pcs-Extensions OPTIONAL,
   ... }

LCSClientExternalID ::= SEQUENCE {
   externalAddress      [0] IMPLICIT OCTET STRING ( SIZE( 1 .. 20 ) ) ( SIZE( 1 .. 9 ) ) OPTIONAL,
   extensionContainer   [1] IMPLICIT ExtensionContainer OPTIONAL,
   ... }

ManagementExtension ::= SEQUENCE {
   identifier     DMI-EXTENSION.&id ({ManagementExtensionSet}) ,
   significance   [1] IMPLICIT BOOLEAN DEFAULT FALSE,
   information    [2] DMI-EXTENSION.&Value ({ManagementExtensionSet}{@.identifier}) }

LCSClientIdentity ::= SEQUENCE {
   lcsClientExternalID   [0] IMPLICIT LCSClientExternalID OPTIONAL,
   lcsClientDialedByMS   [1] IMPLICIT OCTET STRING ( SIZE( 1 .. 20 ) ) OPTIONAL,
   lcsClientInternalID   [2] IMPLICIT ENUMERATED {
      broadcastService             ( 0 ),
      o-andM-HPLMN                 ( 1 ),
      o-andM-VPLMN                 ( 2 ),
      anonymousLocation            ( 3 ),
      targetMSsubscribedService    ( 4 ),
      ...  } OPTIONAL}

LocationType ::= SEQUENCE {
   locationEstimateType        [0] IMPLICIT ENUMERATED {
      currentLocation                 ( 0 ),
      currentOrLastKnownLocation      ( 1 ),
      initialLocation                 ( 2 ),
      ... ,
      activateDeferredLocation        ( 3 ),
      cancelDeferredLocation          ( 4 ),
      notificationVerificationOnly    ( 5 ) },
   ... ,
   deferredLocationEventType   [1] IMPLICIT BIT STRING {
      msAvailable  (0 ),
      enteringIntoArea  (1 ),
      leavingFromArea  (2 ),
      beingInsideArea  (3 ),
      periodicLDR  (4 )} ( SIZE( 1 .. 16 ) ) OPTIONAL}

LCSRecord  ::= CHOICE {
   lCSGMORecord      [71] IMPLICIT LCSGMORecord,
   lCSRGMTRecord     [72] IMPLICIT LCSRGMTRecord,
   lCSHGMTRecord     [73] IMPLICIT LCSHGMTRecord,
   lCSVGMTRecord     [74] IMPLICIT LCSVGMTRecord,
   lCSGNIRecord      [75] IMPLICIT LCSGNIRecord}

LCSGMORecord ::= SET {
   recordType            [0] IMPLICIT RecordType,
   recordingEntity       [1] IMPLICIT OCTET STRING ( SIZE( 1 .. 20 ) ),
   lcsClientType         [2] IMPLICIT LCSClientType OPTIONAL,
   lcsClientIdentity     [3] IMPLICIT LCSClientIdentity OPTIONAL,
   servedIMSI            [4] IMPLICIT OCTET STRING ( SIZE( 3 .. 8 ) ),
   servedMSISDN          [5] IMPLICIT OCTET STRING ( SIZE( 1 .. 20 ) ) ( SIZE( 1 .. 9 ) ) OPTIONAL,
   servingEntity         [6] IMPLICIT OCTET STRING ( SIZE( 1 .. 20 ) ) OPTIONAL,
   locationEstimate      [7] IMPLICIT OCTET STRING ( SIZE( 1 .. 20 ) ) OPTIONAL,
   positioningData       [8] IMPLICIT OCTET STRING ( SIZE( 1 .. 33 ) ) OPTIONAL,
   userError             [9] IMPLICIT OCTET STRING ( SIZE( 1 ) ) OPTIONAL,
   providerError         [10] IMPLICIT INTEGER OPTIONAL,
   recordTimeStamp       [11] IMPLICIT OCTET STRING ( SIZE( 9 ) ),
   localSequenceNumber   [12] IMPLICIT INTEGER ( 0 .. 4294967295 ) OPTIONAL,
   recordExtensions      [13] IMPLICIT SET  OF
      ManagementExtension OPTIONAL}

LCSRGMTRecord ::= SET {
   recordType            [0] IMPLICIT RecordType,
   recordingEntity       [1] IMPLICIT OCTET STRING ( SIZE( 1 .. 20 ) ),
   lcsClientType         [2] IMPLICIT LCSClientType OPTIONAL,
   lcsClientIdentity     [3] IMPLICIT LCSClientIdentity OPTIONAL,
   targetIMSI            [4] IMPLICIT OCTET STRING ( SIZE( 3 .. 8 ) ),
   targetMSISDN          [5] IMPLICIT OCTET STRING ( SIZE( 1 .. 20 ) ) ( SIZE( 1 .. 9 ) ) OPTIONAL,
   locationType          [6] IMPLICIT LocationType,
   lCSPriority           [7] IMPLICIT OCTET STRING ( SIZE( 1 ) ) OPTIONAL,
   resultCode            [8] IMPLICIT INTEGER ( 0 .. MAX ) OPTIONAL,
   recordTimeStamp       [9] IMPLICIT OCTET STRING ( SIZE( 9 ) ),
   localSequenceNumber   [10] IMPLICIT INTEGER ( 0 .. 4294967295 ) OPTIONAL,
   recordExtensions      [11] IMPLICIT SET  OF
      ManagementExtension OPTIONAL,
   homeGMLCIdentity      [12] IPAddress OPTIONAL}

LCSHGMTRecord ::= SET {
   recordType               [0] IMPLICIT RecordType,
   recordingEntity          [1] IMPLICIT OCTET STRING ( SIZE( 1 .. 20 ) ),
   lcsClientType            [2] IMPLICIT LCSClientType OPTIONAL,
   lcsClientIdentity        [3] IMPLICIT LCSClientIdentity OPTIONAL,
   targetIMSI               [4] IMPLICIT OCTET STRING ( SIZE( 3 .. 8 ) ),
   targetMSISDN             [5] IMPLICIT OCTET STRING ( SIZE( 1 .. 20 ) ) ( SIZE( 1 .. 9 ) ) OPTIONAL,
   locationType             [6] IMPLICIT LocationType,
   lCSPriority              [7] IMPLICIT OCTET STRING ( SIZE( 1 ) ) OPTIONAL,
   resultCode               [8] IMPLICIT INTEGER ( 0 .. MAX ) OPTIONAL,
   recordTimeStamp          [9] IMPLICIT OCTET STRING ( SIZE( 9 ) ),
   localSequenceNumber      [10] IMPLICIT INTEGER ( 0 .. 4294967295 ) OPTIONAL,
   recordExtensions         [11] IMPLICIT SET  OF
      ManagementExtension OPTIONAL,
   requestingGMLCIdentity   [12] IPAddress OPTIONAL,
   visitedGMLCIdentity      [13] IPAddress OPTIONAL,
   servingNetworkIdentity   [14] IMPLICIT OCTET STRING ( SIZE( 3 ) ) OPTIONAL}

LCSVGMTRecord ::= SET {
   recordType            [0] IMPLICIT RecordType,
   recordingEntity       [1] IMPLICIT OCTET STRING ( SIZE( 1 .. 20 ) ),
   lcsClientType         [2] IMPLICIT LCSClientType OPTIONAL,
   lcsClientIdentity     [3] IMPLICIT LCSClientIdentity OPTIONAL,
   targetIMSI            [4] IMPLICIT OCTET STRING ( SIZE( 3 .. 8 ) ),
   targetMSISDN          [5] IMPLICIT OCTET STRING ( SIZE( 1 .. 20 ) ) ( SIZE( 1 .. 9 ) ) OPTIONAL,
   locationType          [6] IMPLICIT LocationType,
   lCSPriority           [7] IMPLICIT OCTET STRING ( SIZE( 1 ) ) OPTIONAL,
   resultCode            [8] IMPLICIT INTEGER ( 0 .. MAX ) OPTIONAL,
   recordTimeStamp       [9] IMPLICIT OCTET STRING ( SIZE( 9 ) ),
   localSequenceNumber   [10] IMPLICIT INTEGER ( 0 .. 4294967295 ) OPTIONAL,
   recordExtensions      [11] IMPLICIT SET  OF
      ManagementExtension OPTIONAL,
   homeGMLCIdentity      [12] IPAddress OPTIONAL}

LCSGNIRecord ::= SET {
   recordType            [0] IMPLICIT RecordType,
   recordingEntity       [1] IMPLICIT OCTET STRING ( SIZE( 1 .. 20 ) ),
   lcsClientType         [2] IMPLICIT LCSClientType OPTIONAL,
   lcsClientIdentity     [3] IMPLICIT LCSClientIdentity OPTIONAL,
   servedIMSI            [4] IMPLICIT OCTET STRING ( SIZE( 3 .. 8 ) ),
   servedMSISDN          [5] IMPLICIT OCTET STRING ( SIZE( 1 .. 20 ) ) ( SIZE( 1 .. 9 ) ) OPTIONAL,
   servingEntity         [6] IMPLICIT OCTET STRING ( SIZE( 1 .. 20 ) ) OPTIONAL,
   resultCode            [7] IMPLICIT INTEGER ( 0 .. MAX ) OPTIONAL,
   recordTimeStamp       [8] IMPLICIT OCTET STRING ( SIZE( 9 ) ),
   localSequenceNumber   [9] IMPLICIT INTEGER ( 0 .. 4294967295 ) OPTIONAL,
   recordExtensions      [10] IMPLICIT SET  OF
      ManagementExtension OPTIONAL}

ProviderError ::= INTEGER

ResultCodeType ::= INTEGER ( 0 .. MAX )

ServingEntity ::= OCTET STRING ( SIZE( 1 .. 20 ) )

UserError  ::= OCTET STRING ( SIZE( 1 ) )


-- X.721 DMI-EXTENSION. The set is the standard form of the original
-- extensible empty table constraint ({, ...}) and does not change BER.
DMI-EXTENSION ::= CLASS {
    &id     OBJECT IDENTIFIER UNIQUE,
    &Value
}
WITH SYNTAX {
    TYPE &Value
    ID &id
}

ManagementExtensionSet DMI-EXTENSION ::= {...}


-- 3GPP TS 29.002 MAP-EXTENSION. ExtensionSet is the standard form of
-- the original extensible empty table constraint ({, ...}).
MAP-EXTENSION ::= CLASS {
    &ExtensionType OPTIONAL,
    &extensionId OBJECT IDENTIFIER
}

ExtensionSet MAP-EXTENSION ::= {...}

END
