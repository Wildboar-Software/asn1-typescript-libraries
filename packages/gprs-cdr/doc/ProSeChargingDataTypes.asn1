-- Modified by Jonathan M. Wilbur to fix invalid syntax.
--     Expanded ASN1 Module 'ProSeChargingDataTypes'
--SIEMENS ASN.1 Compiler         R6.31  (Production_6.31)
--            Date: 2020-07-10 Time: 16:16:58

ProSeChargingDataTypes
{itu-t(0) identified-organization(4) etsi(0) mobileDomain(0) charging(5)
proseChargingDataType(11) asn1Module(0) version2(1)}
DEFINITIONS
::=
BEGIN

RecordType ::= INTEGER {
   moCallRecord              ( 0 ),
   mtCallRecord              ( 1 ),
   roamingRecord             ( 2 ),
   incGatewayRecord          ( 3 ),
   outGatewayRecord          ( 4 ),
   transitCallRecord         ( 5 ),
   moSMSRecord               ( 6 ),
   mtSMSRecord               ( 7 ),
   moSMSIWRecord             ( 8 ),
   mtSMSGWRecord             ( 9 ),
   ssActionRecord            ( 10 ),
   hlrIntRecord              ( 11 ),
   locUpdateHLRRecord        ( 12 ),
   locUpdateVLRRecord        ( 13 ),
   commonEquipRecord         ( 14 ),
   moTraceRecord             ( 15 ),
   mtTraceRecord             ( 16 ),
   termCAMELRecord           ( 17 ),
   sgsnPDPRecord             ( 18 ),
   sgsnMMRecord              ( 20 ),
   sgsnSMORecord             ( 21 ),
   sgsnSMTRecord             ( 22 ),
   mtLCSRecord               ( 23 ),
   moLCSRecord               ( 24 ),
   niLCSRecord               ( 25 ),
   sgsnMTLCSRecord           ( 26 ),
   sgsnMOLCSRecord           ( 27 ),
   sgsnNILCSRecord           ( 28 ),
   mMO1SRecord               ( 30 ),
   mMO4FRqRecord             ( 31 ),
   mMO4FRsRecord             ( 32 ),
   mMO4DRecord               ( 33 ),
   mMO1DRecord               ( 34 ),
   mMO4RRecord               ( 35 ),
   mMO1RRecord               ( 36 ),
   mMOMDRecord               ( 37 ),
   mMR4FRecord               ( 38 ),
   mMR1NRqRecord             ( 39 ),
   mMR1NRsRecord             ( 40 ),
   mMR1RtRecord              ( 41 ),
   mMR1AFRecord              ( 42 ),
   mMR4DRqRecord             ( 43 ),
   mMR4DRsRecord             ( 44 ),
   mMR1RRRecord              ( 45 ),
   mMR4RRqRecord             ( 46 ),
   mMR4RRsRecord             ( 47 ),
   mMRMDRecord               ( 48 ),
   mMFRecord                 ( 49 ),
   mMBx1SRecord              ( 50 ),
   mMBx1VRecord              ( 51 ),
   mMBx1URecord              ( 52 ),
   mMBx1DRecord              ( 53 ),
   mM7SRecord                ( 54 ),
   mM7DRqRecord              ( 55 ),
   mM7DRsRecord              ( 56 ),
   mM7CRecord                ( 57 ),
   mM7RRecord                ( 58 ),
   mM7DRRqRecord             ( 59 ),
   mM7DRRsRecord             ( 60 ),
   mM7RRqRecord              ( 61 ),
   mM7RRsRecord              ( 62 ),
   sCSCFRecord               ( 63 ),
   pCSCFRecord               ( 64 ),
   iCSCFRecord               ( 65 ),
   mRFCRecord                ( 66 ),
   mGCFRecord                ( 67 ),
   bGCFRecord                ( 68 ),
   aSRecord                  ( 69 ),
   eCSCFRecord               ( 70 ),
   iBCFRecord                ( 82 ),
   tRFRecord                 ( 89 ),
   tFRecord                  ( 90 ),
   aTCFRecord                ( 91 ),
   lCSGMORecord              ( 71 ),
   lCSRGMTRecord             ( 72 ),
   lCSHGMTRecord             ( 73 ),
   lCSVGMTRecord             ( 74 ),
   lCSGNIRecord              ( 75 ),
   sgsnMBMSRecord            ( 76 ),
   ggsnMBMSRecord            ( 77 ),
   gwMBMSRecord              ( 86 ),
   sUBBMSCRecord             ( 78 ),
   cONTENTBMSCRecord         ( 79 ),
   pPFRecord                 ( 80 ),
   cPFRecord                 ( 81 ),
   sGWRecord                 ( 84 ),
   pGWRecord                 ( 85 ),
   tDFRecord                 ( 92 ),
   iPERecord                 ( 95 ),
   ePDGRecord                ( 96 ),
   tWAGRecord                ( 97 ),
   mMTelRecord               ( 83 ),
   mSCsRVCCRecord            ( 87 ),
   mMTRFRecord               ( 88 ),
   iCSRegisterRecord         ( 99 ),
   sCSMORecord               ( 93 ),
   sCSMTRecord               ( 94 ),
   pFDDRecord                ( 100 ),
   pFEDRecord                ( 101 ),
   pFDCRecord                ( 102 ),
   mECORecord                ( 103 ),
   mERERecord                ( 104 ),
   cPDTSCERecord             ( 105 ),
   cPDTSNNRecord             ( 106 ),
   sCDVTT4Record             ( 110 ),
   sCSMOT4Record             ( 111 ),
   iSMSMORecord              ( 112 ),
   iSMSMTRecord              ( 113 ),
   eASCERecord               ( 120 ),
   chargingFunctionRecord    ( 200 )}

ChChSelectionMode ::= ENUMERATED {
   servingNodeSupplied     ( 0 ),
   subscriptionSpecific    ( 1 ),
   aPNSpecific             ( 2 ),
   homeDefault             ( 3 ),
   roamingDefault          ( 4 ),
   visitingDefault         ( 5 ),
   fixedDefault            ( 6 ) }

IPBinV6AddressWithPrefixLength ::= SEQUENCE {
   iPBinV6Address           OCTET STRING ( SIZE( 16 ) ),
   pDPAddressPrefixLength   INTEGER ( 1 .. 64 ) DEFAULT 64}

IPTextRepresentedAddress ::= CHOICE {
   iPTextV4Address     [2] IMPLICIT IA5String  ( SIZE( 7 .. 15 ) ),
   iPTextV6Address     [3] IMPLICIT IA5String  ( SIZE( 15 .. 45 ) )}

IPBinV6AddressWithOrWithoutPrefixLength ::= CHOICE {
   iPBinV6Address               [1] IMPLICIT OCTET STRING ( SIZE( 16 ) ),
   iPBinV6AddressWithPrefix     [4] IMPLICIT IPBinV6AddressWithPrefixLength}

IPBinaryAddress ::= CHOICE {
   iPBinV4Address     [0] IMPLICIT OCTET STRING ( SIZE( 4 ) ),
   iPBinV6Address     IPBinV6AddressWithOrWithoutPrefixLength}

IPAddress ::= CHOICE {
   iPBinaryAddress              IPBinaryAddress,
   iPTextRepresentedAddress     IPTextRepresentedAddress}

ManagementExtension ::= SEQUENCE {
   identifier     DMI-EXTENSION.&id ({ManagementExtensionSet}) ,
   significance   [1] IMPLICIT BOOLEAN DEFAULT FALSE,
   information    [2] DMI-EXTENSION.&Value ({ManagementExtensionSet}{@.identifier}) }

ProSeRecordType ::= CHOICE {
   pFDDRecord     [100] IMPLICIT PFDDRecord,
   pFEDRecord     [101] IMPLICIT PFEDRecord,
   pFDCRecord     [102] IMPLICIT PFDCRecord}

PFDDRecord ::= SET {
   recordType                    [0] IMPLICIT RecordType,
   retransmission                [1] IMPLICIT NULL OPTIONAL,
   serviceContextID              [2] IMPLICIT UTF8String OPTIONAL,
   servedIMSI                    [3] IMPLICIT OCTET STRING ( SIZE( 3 .. 8 ) ) OPTIONAL,
   proSeFunctionIPAddress        [4] IPAddress OPTIONAL,
   chargingCharacteristics       [5] IMPLICIT OCTET STRING ( SIZE( 2 ) ),
   chChSelectionMode             [6] IMPLICIT ChChSelectionMode OPTIONAL,
   recordExtensions              [7] IMPLICIT SET  OF
      ManagementExtension OPTIONAL,
   proSeRequestTimestamp         [8] IMPLICIT OCTET STRING ( SIZE( 9 ) ) OPTIONAL,
   roleofUE                      [9] IMPLICIT ProSeUERole OPTIONAL,
   pCThreeControlProtocolCause   [10] IMPLICIT INTEGER OPTIONAL,
   roleofProSeFunction           [11] IMPLICIT ProSeFunctionRole OPTIONAL,
   proSeApplicationID            [12] IMPLICIT UTF8String OPTIONAL,
   proSeEventType                [13] IMPLICIT ProSeEventType OPTIONAL,
   nodeID                        [14] IMPLICIT IA5String  ( SIZE( 1 .. 20 ) ) OPTIONAL,
   proseFunctionId               [15] IMPLICIT UTF8String OPTIONAL,
   announcingUEHPLMNIdentifier   [16] IMPLICIT OCTET STRING ( SIZE( 3 ) ) OPTIONAL,
   announcingUEVPLMNIdentifier   [17] IMPLICIT OCTET STRING ( SIZE( 3 ) ) OPTIONAL,
   monitoringUEHPLMNIdentifier   [18] IMPLICIT OCTET STRING ( SIZE( 3 ) ) OPTIONAL,
   monitoringUEVPLMNIdentifier   [19] IMPLICIT OCTET STRING ( SIZE( 3 ) ) OPTIONAL,
   monitoredPLMNIdentifier       [20] IMPLICIT OCTET STRING ( SIZE( 3 ) ) OPTIONAL,
   applicationID                 [21] IMPLICIT UTF8String OPTIONAL,
   directDiscoveryModel          [22] IMPLICIT UTF8String OPTIONAL,
   validityPeriod                [23] IMPLICIT INTEGER OPTIONAL,
   monitoringUEIdentifier        [24] IMPLICIT OCTET STRING ( SIZE( 3 .. 8 ) ) OPTIONAL,
   discovererUEHPLMNIdentifier   [25] IMPLICIT OCTET STRING ( SIZE( 3 ) ) OPTIONAL,
   discovererUEVPLMNIdentifier   [26] IMPLICIT OCTET STRING ( SIZE( 3 ) ) OPTIONAL,
   discovereeUEHPLMNIdentifier   [27] IMPLICIT OCTET STRING ( SIZE( 3 ) ) OPTIONAL,
   discovereeUEVPLMNIdentifier   [28] IMPLICIT OCTET STRING ( SIZE( 3 ) ) OPTIONAL,
   announcingPLMNID              [29] IMPLICIT OCTET STRING ( SIZE( 3 ) ) OPTIONAL,
   pc5RadioTechnology            [30] IMPLICIT PC5RadioTechnology OPTIONAL}

PFEDRecord ::= SET {
   recordType                             [0] IMPLICIT RecordType,
   retransmission                         [1] IMPLICIT NULL OPTIONAL,
   serviceContextID                       [2] IMPLICIT UTF8String OPTIONAL,
   servedIMSI                             [3] IMPLICIT OCTET STRING ( SIZE( 3 .. 8 ) ) OPTIONAL,
   proSeFunctionIPAddress                 [4] IPAddress OPTIONAL,
   chargingCharacteristics                [5] IMPLICIT OCTET STRING ( SIZE( 2 ) ),
   chChSelectionMode                      [6] IMPLICIT ChChSelectionMode OPTIONAL,
   recordExtensions                       [7] IMPLICIT SET  OF
      ManagementExtension OPTIONAL,
   proSeRequestTimestamp                  [8] IMPLICIT OCTET STRING ( SIZE( 9 ) ) OPTIONAL,
   roleofUE                               [9] IMPLICIT ProSeUERole OPTIONAL,
   pCThreeEPCControlProtocolCause         [10] IMPLICIT INTEGER OPTIONAL,
   proseFunctionPLMNIdentifier            [11] IMPLICIT OCTET STRING ( SIZE( 3 ) ) OPTIONAL,
   proseFunctionId                        [12] IMPLICIT UTF8String OPTIONAL,
   recordOpeningTime                      [13] IMPLICIT OCTET STRING ( SIZE( 9 ) ) OPTIONAL,
   recordClosureTime                      [14] IMPLICIT OCTET STRING ( SIZE( 9 ) ) OPTIONAL,
   applicationID                          [15] IMPLICIT UTF8String OPTIONAL,
   requestorApplicationLayerUserID        [16] IMPLICIT UTF8String OPTIONAL,
   wLANLinkLayerID                        [17] IMPLICIT UTF8String OPTIONAL,
   requestorEPCProSeUserID                [18] IMPLICIT UTF8String OPTIONAL,
   requestedApplicationLayerUserID        [19] IMPLICIT UTF8String OPTIONAL,
   requestedPLMNIdentifier                [20] IMPLICIT OCTET STRING ( SIZE( 3 ) ) OPTIONAL,
   timeWindow                             [21] IMPLICIT INTEGER OPTIONAL,
   rangeClass                             [22] IMPLICIT RangeClass OPTIONAL,
   uELocation                             [23] IMPLICIT OCTET STRING OPTIONAL,
   proximityAlertIndication               [24] IMPLICIT ProximityAlertIndication OPTIONAL,
   proximityAlertTimestamp                [25] IMPLICIT OCTET STRING ( SIZE( 9 ) ) OPTIONAL,
   proximityCancellationTimestamp         [26] IMPLICIT OCTET STRING ( SIZE( 9 ) ) OPTIONAL,
   reasonforCancellation                  [27] IMPLICIT ReasonforCancellation OPTIONAL,
   causeForRecClosing                     [28] IMPLICIT ProSeCauseForRecClosing,
   proximityRequestRenewalInfoBlockList   [29] IMPLICIT SEQUENCE  OF
      ProximityRequestRenewalInfoBlock OPTIONAL}

PFDCRecord ::= SET {
   recordType                     [0] IMPLICIT RecordType,
   retransmission                 [1] IMPLICIT NULL OPTIONAL,
   serviceContextID               [2] IMPLICIT UTF8String OPTIONAL,
   servedIMSI                     [3] IMPLICIT OCTET STRING ( SIZE( 3 .. 8 ) ) OPTIONAL,
   proSeFunctionIPAddress         [4] IPAddress OPTIONAL,
   chargingCharacteristics        [5] IMPLICIT OCTET STRING ( SIZE( 2 ) ),
   chChSelectionMode              [6] IMPLICIT ChChSelectionMode OPTIONAL,
   recordExtensions               [7] IMPLICIT SET  OF
      ManagementExtension OPTIONAL,
   nodeID                         [8] IMPLICIT IA5String  ( SIZE( 1 .. 20 ) ) OPTIONAL,
   proseFunctionPLMNIdentifier    [9] IMPLICIT OCTET STRING ( SIZE( 3 ) ) OPTIONAL,
   proseFunctionId                [10] IMPLICIT UTF8String OPTIONAL,
   recordOpeningTime              [11] IMPLICIT OCTET STRING ( SIZE( 9 ) ) OPTIONAL,
   recordClosureTime              [12] IMPLICIT OCTET STRING ( SIZE( 9 ) ) OPTIONAL,
   listOfCoverageInfo             [13] IMPLICIT SEQUENCE  OF
      CoverageInfo OPTIONAL,
   listOfRadioParameterSet        [14] IMPLICIT SEQUENCE  OF
      RadioParameterSetInfo OPTIONAL,
   proSeUEID                      [15] IMPLICIT OCTET STRING OPTIONAL,
   sourceIPaddress                [16] IPAddress OPTIONAL,
   layerTwoGroupID                [17] IMPLICIT OCTET STRING OPTIONAL,
   proSeGroupIPmulticastaddress   [18] IPAddress OPTIONAL,
   timeOfFirstTransmission        [19] IMPLICIT OCTET STRING ( SIZE( 9 ) ) OPTIONAL,
   timeOfFirstReception           [20] IMPLICIT OCTET STRING ( SIZE( 9 ) ) OPTIONAL,
   listOfTransmitters             [21] IMPLICIT SEQUENCE  OF
      TransmitterInfo OPTIONAL,
   listOfTransmissionData         [22] IMPLICIT SEQUENCE  OF
      ChangeOfProSeCondition OPTIONAL,
   listOfReceptionData            [23] IMPLICIT SEQUENCE  OF
      ChangeOfProSeCondition OPTIONAL,
   causeForRecClosing             [24] IMPLICIT ProSeCauseForRecClosing,
   listOfAppSpecificData          [25] IMPLICIT SEQUENCE  OF
      OCTET STRING,
   targetIPaddress                [26] IPAddress OPTIONAL,
   relayIPaddress                 [27] IPAddress OPTIONAL,
   proSeUEtoNetworkRelayUEID      [28] IMPLICIT OCTET STRING OPTIONAL,
   proSeTargetLayerTwoID          [29] IMPLICIT OCTET STRING OPTIONAL}

ChangeOfProSeCondition ::= SEQUENCE {
   changeConditionTimestamp               [0] IMPLICIT OCTET STRING ( SIZE( 9 ) ) OPTIONAL,
   coverageStatus                         [1] IMPLICIT CoverageStatus OPTIONAL,
   uELocation                             [2] IMPLICIT OCTET STRING OPTIONAL,
   dataVolume                             [3] IMPLICIT INTEGER OPTIONAL,
   serviceChangeCondition                 [4] IMPLICIT BIT STRING {
      pLMNchange  (0 ),
      coverageStatusChange  (1 ),
      locationChange  (2 )} OPTIONAL,
   localSequenceNumber                    [5] IMPLICIT INTEGER ( 0 .. 4294967295 ) OPTIONAL,
   usageInformationReportSequenceNumber   [6] IMPLICIT INTEGER OPTIONAL,
   radioResourcesInd                      [7] IMPLICIT INTEGER {
      operatorProvided    ( 1 ),
      configured          ( 2 )} OPTIONAL,
   radiofrequency                         [8] IMPLICIT OCTET STRING OPTIONAL,
   vPLMNIdentifier                        [9] IMPLICIT OCTET STRING ( SIZE( 3 ) ) OPTIONAL}

AppSpecificData ::= OCTET STRING

CoverageInfo ::= SEQUENCE {
   coverageStatus   [0] IMPLICIT CoverageStatus,
   timeStamp        [1] IMPLICIT OCTET STRING ( SIZE( 9 ) ) OPTIONAL,
   listOfLocation   [2] IMPLICIT SEQUENCE  OF
      LocationInfo OPTIONAL}

CoverageStatus ::= ENUMERATED {
   outOfCoverage    ( 0 ),
   inCoverage       ( 1 ) }

LocationInfo ::= SEQUENCE {
   uELocation   [0] IMPLICIT OCTET STRING OPTIONAL,
   timeStamp    [1] IMPLICIT OCTET STRING ( SIZE( 9 ) ) OPTIONAL}

RadioFrequency ::= OCTET STRING

RadioParameterSetInfo ::= SEQUENCE {
   timeStamp   [0] IMPLICIT OCTET STRING ( SIZE( 9 ) ) OPTIONAL,
   params      [1] IMPLICIT OCTET STRING}

RadioResourcesIndicator ::= INTEGER {
   operatorProvided    ( 1 ),
   configured          ( 2 )}

ServiceChangeCondition ::= BIT STRING {
   pLMNchange  (0 ),
   coverageStatusChange  (1 ),
   locationChange  (2 )}

PC5RadioTechnology ::= ENUMERATED {
   eUTRA               ( 0 ),
   wLAN                ( 1 ),
   bothEUTRAAndWLAN    ( 2 ) }

ProSeCauseForRecClosing ::= ENUMERATED {
   proximityAlerted             ( 0 ),
   timeExpiredWithNoRrenewal    ( 1 ),
   requestorCancellation        ( 2 ),
   timeLimited                  ( 3 ),
   maxNumberOfReports           ( 4 ),
   abnormalRelease              ( 5 ) }

ProSeEventType ::= ENUMERATED {
   openAnnouncing                  ( 0 ),
   openMonitoring                  ( 1 ),
   openMatchReport                 ( 2 ),
   restrictedAnnouncing            ( 3 ),
   restrictedMonitoring            ( 4 ),
   restrictedMatchReport           ( 5 ),
   restrictedDiscoveryRequest      ( 6 ),
   restrictedDiscoveryReporting    ( 7 ) }

ProSeFunctionRole ::= ENUMERATED {
   hPLMN        ( 0 ),
   vPLMN        ( 1 ),
   localPLMN    ( 2 ) }

ProSeUERole ::= ENUMERATED {
   annoucingUE     ( 0 ),
   monitoringUE    ( 1 ),
   requestorUE     ( 2 ),
   requestedUE     ( 3 ),
   discovererUE    ( 4 ),
   discovereeUE    ( 5 ) }

ProximityAlertIndication ::= ENUMERATED {
   alerted     ( 0 ),
   noAlert     ( 1 ) }

ProximityRequestRenewalInfoBlock ::= SEQUENCE {
   proSeRequestTimestamp   [0] IMPLICIT OCTET STRING ( SIZE( 9 ) ) OPTIONAL,
   timeWindow              [1] IMPLICIT INTEGER OPTIONAL,
   rangeClass              [2] IMPLICIT RangeClass OPTIONAL,
   uELocation              [3] IMPLICIT OCTET STRING OPTIONAL}

RangeClass ::= ENUMERATED {
   reserved            ( 0 ),
   fiftyMeter          ( 1 ),
   onehundredMeter     ( 2 ),
   twohundredMeter     ( 3 ),
   fivehundredMeter    ( 4 ),
   onethousandMeter    ( 5 ) }

ReasonforCancellation ::= ENUMERATED {
   proximityAlerted             ( 0 ),
   timeExpiredWithNoRrenewal    ( 1 ),
   requestorCancellation        ( 2 ) }

TransmitterInfo ::= SEQUENCE {
   sourceIPaddress   [0] IPAddress,
   proSeUEID         [1] IMPLICIT OCTET STRING}


-- X.721 DMI-EXTENSION. The set is the standard form of the original
-- extensible empty table constraint ({, ...}) and does not change BER.
DMI-EXTENSION ::= CLASS {
    &id     OBJECT IDENTIFIER UNIQUE,
    &Value
}
WITH SYNTAX {
    TYPE &Value
    ID &id
}

ManagementExtensionSet DMI-EXTENSION ::= {...}

END
