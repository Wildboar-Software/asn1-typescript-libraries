-- Modified by Jonathan M. Wilbur to fix invalid syntax.
--      Expanded ASN1 Module 'MMSChargingDataTypes'
--SIEMENS ASN.1 Compiler         R6.31  (Production_6.31)
--            Date: 2020-07-10 Time: 16:15:54

MMSChargingDataTypes
{itu-t(0) identified-organization(4) etsi(0) mobileDomain(0) charging(5)
mmsChargingDataTypes(5) asn1Module(0) version2(1)}
DEFINITIONS
::=
BEGIN

RecordType ::= INTEGER {
   moCallRecord              ( 0 ),
   mtCallRecord              ( 1 ),
   roamingRecord             ( 2 ),
   incGatewayRecord          ( 3 ),
   outGatewayRecord          ( 4 ),
   transitCallRecord         ( 5 ),
   moSMSRecord               ( 6 ),
   mtSMSRecord               ( 7 ),
   moSMSIWRecord             ( 8 ),
   mtSMSGWRecord             ( 9 ),
   ssActionRecord            ( 10 ),
   hlrIntRecord              ( 11 ),
   locUpdateHLRRecord        ( 12 ),
   locUpdateVLRRecord        ( 13 ),
   commonEquipRecord         ( 14 ),
   moTraceRecord             ( 15 ),
   mtTraceRecord             ( 16 ),
   termCAMELRecord           ( 17 ),
   sgsnPDPRecord             ( 18 ),
   sgsnMMRecord              ( 20 ),
   sgsnSMORecord             ( 21 ),
   sgsnSMTRecord             ( 22 ),
   mtLCSRecord               ( 23 ),
   moLCSRecord               ( 24 ),
   niLCSRecord               ( 25 ),
   sgsnMTLCSRecord           ( 26 ),
   sgsnMOLCSRecord           ( 27 ),
   sgsnNILCSRecord           ( 28 ),
   mMO1SRecord               ( 30 ),
   mMO4FRqRecord             ( 31 ),
   mMO4FRsRecord             ( 32 ),
   mMO4DRecord               ( 33 ),
   mMO1DRecord               ( 34 ),
   mMO4RRecord               ( 35 ),
   mMO1RRecord               ( 36 ),
   mMOMDRecord               ( 37 ),
   mMR4FRecord               ( 38 ),
   mMR1NRqRecord             ( 39 ),
   mMR1NRsRecord             ( 40 ),
   mMR1RtRecord              ( 41 ),
   mMR1AFRecord              ( 42 ),
   mMR4DRqRecord             ( 43 ),
   mMR4DRsRecord             ( 44 ),
   mMR1RRRecord              ( 45 ),
   mMR4RRqRecord             ( 46 ),
   mMR4RRsRecord             ( 47 ),
   mMRMDRecord               ( 48 ),
   mMFRecord                 ( 49 ),
   mMBx1SRecord              ( 50 ),
   mMBx1VRecord              ( 51 ),
   mMBx1URecord              ( 52 ),
   mMBx1DRecord              ( 53 ),
   mM7SRecord                ( 54 ),
   mM7DRqRecord              ( 55 ),
   mM7DRsRecord              ( 56 ),
   mM7CRecord                ( 57 ),
   mM7RRecord                ( 58 ),
   mM7DRRqRecord             ( 59 ),
   mM7DRRsRecord             ( 60 ),
   mM7RRqRecord              ( 61 ),
   mM7RRsRecord              ( 62 ),
   sCSCFRecord               ( 63 ),
   pCSCFRecord               ( 64 ),
   iCSCFRecord               ( 65 ),
   mRFCRecord                ( 66 ),
   mGCFRecord                ( 67 ),
   bGCFRecord                ( 68 ),
   aSRecord                  ( 69 ),
   eCSCFRecord               ( 70 ),
   iBCFRecord                ( 82 ),
   tRFRecord                 ( 89 ),
   tFRecord                  ( 90 ),
   aTCFRecord                ( 91 ),
   lCSGMORecord              ( 71 ),
   lCSRGMTRecord             ( 72 ),
   lCSHGMTRecord             ( 73 ),
   lCSVGMTRecord             ( 74 ),
   lCSGNIRecord              ( 75 ),
   sgsnMBMSRecord            ( 76 ),
   ggsnMBMSRecord            ( 77 ),
   gwMBMSRecord              ( 86 ),
   sUBBMSCRecord             ( 78 ),
   cONTENTBMSCRecord         ( 79 ),
   pPFRecord                 ( 80 ),
   cPFRecord                 ( 81 ),
   sGWRecord                 ( 84 ),
   pGWRecord                 ( 85 ),
   tDFRecord                 ( 92 ),
   iPERecord                 ( 95 ),
   ePDGRecord                ( 96 ),
   tWAGRecord                ( 97 ),
   mMTelRecord               ( 83 ),
   mSCsRVCCRecord            ( 87 ),
   mMTRFRecord               ( 88 ),
   iCSRegisterRecord         ( 99 ),
   sCSMORecord               ( 93 ),
   sCSMTRecord               ( 94 ),
   pFDDRecord                ( 100 ),
   pFEDRecord                ( 101 ),
   pFDCRecord                ( 102 ),
   mECORecord                ( 103 ),
   mERERecord                ( 104 ),
   cPDTSCERecord             ( 105 ),
   cPDTSNNRecord             ( 106 ),
   sCDVTT4Record             ( 110 ),
   sCSMOT4Record             ( 111 ),
   iSMSMORecord              ( 112 ),
   iSMSMTRecord              ( 113 ),
   eASCERecord               ( 120 ),
   chargingFunctionRecord    ( 200 )}

PriorityType ::= ENUMERATED {
   low         ( 0 ),
   normal      ( 1 ),
   high        ( 2 ) }

MessageClass ::= ENUMERATED {
   personal               ( 0 ),
   advertisement          ( 1 ),
   information-service    ( 2 ),
   auto                   ( 3 ) }

IPBinV6AddressWithPrefixLength ::= SEQUENCE {
   iPBinV6Address           OCTET STRING ( SIZE( 16 ) ),
   pDPAddressPrefixLength   INTEGER ( 1 .. 64 ) DEFAULT 64}

IPTextRepresentedAddress ::= CHOICE {
   iPTextV4Address     [2] IMPLICIT IA5String  ( SIZE( 7 .. 15 ) ),
   iPTextV6Address     [3] IMPLICIT IA5String  ( SIZE( 15 .. 45 ) )}

IPBinV6AddressWithOrWithoutPrefixLength ::= CHOICE {
   iPBinV6Address               [1] IMPLICIT OCTET STRING ( SIZE( 16 ) ),
   iPBinV6AddressWithPrefix     [4] IMPLICIT IPBinV6AddressWithPrefixLength}

IPBinaryAddress ::= CHOICE {
   iPBinV4Address     [0] IMPLICIT OCTET STRING ( SIZE( 4 ) ),
   iPBinV6Address     IPBinV6AddressWithOrWithoutPrefixLength}

IPAddress ::= CHOICE {
   iPBinaryAddress              IPBinaryAddress,
   iPTextRepresentedAddress     IPTextRepresentedAddress}

ManagementExtension ::= SEQUENCE {
   identifier     DMI-EXTENSION.&id ({ManagementExtensionSet}) ,
   significance   [1] IMPLICIT BOOLEAN DEFAULT FALSE,
   information    [2] DMI-EXTENSION.&Value ({ManagementExtensionSet}{@.identifier}) }

MMSRecordType ::= CHOICE {
   mMO1SRecord        [30] IMPLICIT MMO1SRecord,
   mMO4FRqRecord      [31] IMPLICIT MMO4FRqRecord,
   mMO4FRsRecord      [32] IMPLICIT MMO4FRsRecord,
   mMO4DRecord        [33] IMPLICIT MMO4DRecord,
   mMO1DRecord        [34] IMPLICIT MMO1DRecord,
   mMO4RRecord        [35] IMPLICIT MMO4RRecord,
   mMO1RRecord        [36] IMPLICIT MMO1RRecord,
   mMOMDRecord        [37] IMPLICIT MMOMDRecord,
   mMR4FRecord        [38] IMPLICIT MMR4FRecord,
   mMR1NRqRecord      [39] IMPLICIT MMR1NRqRecord,
   mMR1NRsRecord      [40] IMPLICIT MMR1NRsRecord,
   mMR1RtRqRecord     [41] IMPLICIT MMR1RtRecord,
   mMR1ARecord        [42] IMPLICIT MMR1ARecord,
   mMR4DRqRecord      [43] IMPLICIT MMR4DRqRecord,
   mMR4DRsRecord      [44] IMPLICIT MMR4DRsRecord,
   mMR1RRRecord       [45] IMPLICIT MMR1RRRecord,
   mMR4RRqRecord      [46] IMPLICIT MMR4RRqRecord,
   mMR4RRsRecord      [47] IMPLICIT MMR4RRsRecord,
   mMRMDRecord        [48] IMPLICIT MMRMDRecord,
   mMFRecord          [49] IMPLICIT MMFRecord,
   mMBx1SRecord       [50] IMPLICIT MMBx1SRecord,
   mMBx1VRecord       [51] IMPLICIT MMBx1VRecord,
   mMBx1URecord       [52] IMPLICIT MMBx1URecord,
   mMBx1DRecord       [53] IMPLICIT MMBx1DRecord,
   mM7SRecord         [54] IMPLICIT MM7SRecord,
   mM7DRqRecord       [55] IMPLICIT MM7DRqRecord,
   mM7DRsRecord       [56] IMPLICIT MM7DRsRecord,
   mM7CRecord         [57] IMPLICIT MM7CRecord,
   mM7RRecord         [58] IMPLICIT MM7RRecord,
   mM7DRRqRecord      [59] IMPLICIT MM7DRRqRecord,
   mM7DRRsRecord      [60] IMPLICIT MM7DRRsRecord,
   mM7RRqRecord       [61] IMPLICIT MM7RRqRecord,
   mM7RRsRecord       [62] IMPLICIT MM7RRsRecord}

MMO1SRecord ::= SET {
   recordType                [0] IMPLICIT RecordType,
   originatorMmsRSAddress    [1] IMPLICIT MMSRSAddress,
   messageID                 [2] IMPLICIT OCTET STRING,
   replyChargingID           [3] IMPLICIT OCTET STRING OPTIONAL,
   originatorAddress         [4] IMPLICIT MMSAgentAddress,
   recipientAddresses        [5] IMPLICIT SET  OF
      MMSAgentAddress,
   accessCorrelation         [6] AccessCorrelation OPTIONAL,
   contentType               [7] IMPLICIT OCTET STRING,
   mmComponentType           [8] IMPLICIT MMComponentType OPTIONAL,
   messageSize               [9] IMPLICIT INTEGER,
   messageClass              [10] IMPLICIT MessageClass OPTIONAL,
   chargeInformation         [11] IMPLICIT ChargeInformation OPTIONAL,
   submissionTime            [12] IMPLICIT OCTET STRING ( SIZE( 9 ) ) OPTIONAL,
   timeOfExpiry              [13] WaitTime OPTIONAL,
   earliestTimeOfDelivery    [14] WaitTime OPTIONAL,
   durationOfTransmission    [15] IMPLICIT INTEGER OPTIONAL,
   requestStatusCode         [16] IMPLICIT RequestStatusCodeType OPTIONAL,
   deliveryReportRequested   [17] IMPLICIT BOOLEAN OPTIONAL,
   replyCharging             [18] IMPLICIT BOOLEAN OPTIONAL,
   replyDeadline             [19] WaitTime OPTIONAL,
   replyChargingSize         [20] IMPLICIT INTEGER OPTIONAL,
   priority                  [21] IMPLICIT PriorityType OPTIONAL,
   senderVisibility          [22] IMPLICIT BOOLEAN OPTIONAL,
   readReplyRequested        [23] IMPLICIT BOOLEAN OPTIONAL,
   statusText                [24] IMPLICIT OCTET STRING,
   recordTimeStamp           [25] IMPLICIT OCTET STRING ( SIZE( 9 ) ),
   localSequenceNumber       [26] IMPLICIT INTEGER ( 0 .. 4294967295 ) OPTIONAL,
   recordExtensions          [27] IMPLICIT SET  OF
      ManagementExtension OPTIONAL,
   mMBoxstorageInformation   [28] IMPLICIT MMBoxStorageInformation OPTIONAL,
   mscfInformation           [29] IMPLICIT MSCFInformation OPTIONAL,
   sGSNPLMNIdentifier        [30] IMPLICIT OCTET STRING ( SIZE( 3 ) ) OPTIONAL,
   rATType                   [31] IMPLICIT INTEGER ( 0 .. 255 ) OPTIONAL,
   mSTimeZone                [32] IMPLICIT OCTET STRING ( SIZE( 2 ) ) OPTIONAL}

MMO4FRqRecord ::= SET {
   recordType                [0] IMPLICIT RecordType,
   originatorMmsRSAddress    [1] IMPLICIT MMSRSAddress,
   recipientMmsRSAddress     [2] IMPLICIT MMSRSAddress,
   messageID                 [3] IMPLICIT OCTET STRING,
   mms3GPPVersion            [4] IMPLICIT OCTET STRING OPTIONAL,
   originatorAddress         [5] IMPLICIT MMSAgentAddress,
   recipientAddresses        [6] IMPLICIT SET  OF
      MMSAgentAddress,
   contentType               [7] IMPLICIT OCTET STRING,
   mmComponentType           [8] IMPLICIT MMComponentType OPTIONAL,
   messageSize               [9] IMPLICIT INTEGER,
   messageClass              [10] IMPLICIT MessageClass OPTIONAL,
   submissionTime            [11] IMPLICIT OCTET STRING ( SIZE( 9 ) ),
   timeOfExpiry              [12] WaitTime OPTIONAL,
   deliveryReportRequested   [13] IMPLICIT BOOLEAN,
   priority                  [14] IMPLICIT PriorityType OPTIONAL,
   senderVisibility          [15] IMPLICIT BOOLEAN,
   readReplyRequested        [16] IMPLICIT BOOLEAN,
   acknowledgementRequest    [17] IMPLICIT BOOLEAN,
   forwardCounter            [18] IMPLICIT INTEGER OPTIONAL,
   forwardingAddress         [19] IMPLICIT SET  OF
      MMSAgentAddress OPTIONAL,
   recordTimeStamp           [20] IMPLICIT OCTET STRING ( SIZE( 9 ) ),
   localSequenceNumber       [21] IMPLICIT INTEGER ( 0 .. 4294967295 ) OPTIONAL,
   recordExtensions          [22] IMPLICIT SET  OF
      ManagementExtension OPTIONAL}

MMO4FRsRecord ::= SET {
   recordType               [0] IMPLICIT RecordType,
   originatorMmsRSAddress   [1] IMPLICIT MMSRSAddress OPTIONAL,
   recipientMmsRSAddress    [2] IMPLICIT MMSRSAddress,
   messageID                [3] IMPLICIT OCTET STRING,
   mms3GPPVersion           [4] IMPLICIT OCTET STRING OPTIONAL,
   requestStatusCode        [5] IMPLICIT RequestStatusCodeType OPTIONAL,
   statusText               [6] IMPLICIT OCTET STRING OPTIONAL,
   recordTimeStamp          [7] IMPLICIT OCTET STRING ( SIZE( 9 ) ) OPTIONAL,
   localSequenceNumber      [8] IMPLICIT INTEGER ( 0 .. 4294967295 ) OPTIONAL,
   recordExtensions         [9] IMPLICIT SET  OF
      ManagementExtension OPTIONAL}

MMO4DRecord ::= SET {
   recordType               [0] IMPLICIT RecordType,
   recipientMmsRSAddress    [1] IMPLICIT MMSRSAddress OPTIONAL,
   originatorMmsRSAddress   [2] IMPLICIT MMSRSAddress OPTIONAL,
   messageID                [3] IMPLICIT OCTET STRING,
   mms3GPPVersion           [4] IMPLICIT OCTET STRING OPTIONAL,
   originatorAddress        [5] IMPLICIT MMSAgentAddress OPTIONAL,
   recipientAddress         [6] IMPLICIT MMSAgentAddress,
   mmDateAndTime            [7] IMPLICIT OCTET STRING ( SIZE( 9 ) ),
   acknowledgementRequest   [8] IMPLICIT BOOLEAN,
   mmStatusCode             [9] IMPLICIT MMStatusCodeType,
   statusText               [10] IMPLICIT OCTET STRING OPTIONAL,
   recordTimeStamp          [11] IMPLICIT OCTET STRING ( SIZE( 9 ) ) OPTIONAL,
   localSequenceNumber      [12] IMPLICIT INTEGER ( 0 .. 4294967295 ) OPTIONAL,
   recordExtensions         [13] IMPLICIT SET  OF
      ManagementExtension OPTIONAL}

MMO1DRecord ::= SET {
   recordType               [0] IMPLICIT RecordType,
   recipientMmsRSAddress    [1] IMPLICIT MMSRSAddress OPTIONAL,
   originatorMmsRSAddress   [2] IMPLICIT MMSRSAddress OPTIONAL,
   accessCorrelation        [3] AccessCorrelation OPTIONAL,
   messageID                [4] IMPLICIT OCTET STRING,
   mms3GPPVersion           [5] IMPLICIT OCTET STRING OPTIONAL,
   originatorAddress        [6] IMPLICIT MMSAgentAddress OPTIONAL,
   recipientAddress         [7] IMPLICIT MMSAgentAddress,
   mmStatusCode             [8] IMPLICIT MMStatusCodeType OPTIONAL,
   recordTimeStamp          [9] IMPLICIT OCTET STRING ( SIZE( 9 ) ) OPTIONAL,
   localSequenceNumber      [10] IMPLICIT INTEGER ( 0 .. 4294967295 ) OPTIONAL,
   recordExtensions         [11] IMPLICIT SET  OF
      ManagementExtension OPTIONAL,
   sGSNPLMNIdentifier       [12] IMPLICIT OCTET STRING ( SIZE( 3 ) ) OPTIONAL,
   rATType                  [13] IMPLICIT INTEGER ( 0 .. 255 ) OPTIONAL,
   mSTimeZone               [14] IMPLICIT OCTET STRING ( SIZE( 2 ) ) OPTIONAL}

MMO4RRecord ::= SET {
   recordType               [0] IMPLICIT RecordType,
   recipientMmsRSAddress    [1] IMPLICIT MMSRSAddress OPTIONAL,
   originatorMmsRSAddress   [2] IMPLICIT MMSRSAddress OPTIONAL,
   messageID                [3] IMPLICIT OCTET STRING,
   mms3GPPVersion           [4] IMPLICIT OCTET STRING OPTIONAL,
   originatorAddress        [5] IMPLICIT MMSAgentAddress OPTIONAL,
   recipientAddresses       [6] IMPLICIT SET  OF
      MMSAgentAddress OPTIONAL,
   mmDateAndTime            [7] IMPLICIT OCTET STRING ( SIZE( 9 ) ) OPTIONAL,
   acknowledgementRequest   [8] IMPLICIT BOOLEAN,
   readStatus               [9] IMPLICIT MMStatusCodeType OPTIONAL,
   statusText               [10] IMPLICIT OCTET STRING OPTIONAL,
   recordTimeStamp          [11] IMPLICIT OCTET STRING ( SIZE( 9 ) ) OPTIONAL,
   localSequenceNumber      [12] IMPLICIT INTEGER ( 0 .. 4294967295 ) OPTIONAL,
   recordExtensions         [13] IMPLICIT SET  OF
      ManagementExtension OPTIONAL}

MMO1RRecord ::= SET {
   recordType               [0] IMPLICIT RecordType,
   recipientMmsRSAddress    [1] IMPLICIT MMSRSAddress OPTIONAL,
   originatorMmsRSAddress   [2] IMPLICIT MMSRSAddress OPTIONAL,
   accessCorrelation        [3] AccessCorrelation OPTIONAL,
   messageID                [4] IMPLICIT OCTET STRING,
   mms3GPPVersion           [5] IMPLICIT OCTET STRING OPTIONAL,
   originatorAddress        [6] IMPLICIT MMSAgentAddress OPTIONAL,
   recipientAddress         [7] IMPLICIT MMSAgentAddress OPTIONAL,
   readStatus               [8] IMPLICIT MMStatusCodeType OPTIONAL,
   recordTimeStamp          [9] IMPLICIT OCTET STRING ( SIZE( 9 ) ) OPTIONAL,
   localSequenceNumber      [10] IMPLICIT INTEGER ( 0 .. 4294967295 ) OPTIONAL,
   recordExtensions         [11] IMPLICIT SET  OF
      ManagementExtension OPTIONAL,
   sGSNPLMNIdentifier       [12] IMPLICIT OCTET STRING ( SIZE( 3 ) ) OPTIONAL,
   rATType                  [13] IMPLICIT INTEGER ( 0 .. 255 ) OPTIONAL,
   mSTimeZone               [14] IMPLICIT OCTET STRING ( SIZE( 2 ) ) OPTIONAL}

MMOMDRecord ::= SET {
   recordType               [0] IMPLICIT RecordType,
   originatorMmsRSAddress   [1] IMPLICIT MMSRSAddress OPTIONAL,
   recipientMmsRSAddress    [2] IMPLICIT MMSRSAddress OPTIONAL,
   messageID                [3] IMPLICIT OCTET STRING,
   messageSize              [4] IMPLICIT INTEGER OPTIONAL,
   mmStatusCode             [5] IMPLICIT MMStatusCodeType OPTIONAL,
   statusText               [6] IMPLICIT OCTET STRING OPTIONAL,
   recordTimeStamp          [7] IMPLICIT OCTET STRING ( SIZE( 9 ) ) OPTIONAL,
   localSequenceNumber      [8] IMPLICIT INTEGER ( 0 .. 4294967295 ) OPTIONAL,
   recordExtensions         [9] IMPLICIT SET  OF
      ManagementExtension OPTIONAL}

MMR4FRecord ::= SET {
   recordType                [0] IMPLICIT RecordType,
   recipientMmsRSAddress     [1] IMPLICIT MMSRSAddress,
   originatorMmsRSAddress    [2] IMPLICIT MMSRSAddress,
   messageID                 [3] IMPLICIT OCTET STRING,
   mms3GPPVersion            [4] IMPLICIT OCTET STRING OPTIONAL,
   originatorAddress         [5] IMPLICIT MMSAgentAddress,
   recipientAddresses        [6] IMPLICIT SET  OF
      MMSAgentAddress,
   contentType               [7] IMPLICIT OCTET STRING,
   mmComponentType           [8] IMPLICIT MMComponentType OPTIONAL,
   messageSize               [9] IMPLICIT INTEGER,
   messageClass              [10] IMPLICIT MessageClass OPTIONAL,
   submissionTime            [11] IMPLICIT OCTET STRING ( SIZE( 9 ) ),
   timeOfExpiry              [12] WaitTime OPTIONAL,
   deliveryReportRequested   [13] IMPLICIT BOOLEAN,
   priority                  [14] IMPLICIT PriorityType OPTIONAL,
   senderVisibility          [15] IMPLICIT BOOLEAN,
   readReplyRequested        [16] IMPLICIT BOOLEAN,
   requestStatusCode         [17] IMPLICIT RequestStatusCodeType,
   statusText                [18] IMPLICIT OCTET STRING,
   acknowledgementRequest    [19] IMPLICIT BOOLEAN,
   forwardCounter            [20] IMPLICIT INTEGER OPTIONAL,
   forwardingAddress         [21] IMPLICIT SET  OF
      MMSAgentAddress OPTIONAL,
   recordTimeStamp           [22] IMPLICIT OCTET STRING ( SIZE( 9 ) ),
   localSequenceNumber       [23] IMPLICIT INTEGER ( 0 .. 4294967295 ) OPTIONAL,
   recordExtensions          [24] IMPLICIT SET  OF
      ManagementExtension OPTIONAL}

MMR1NRqRecord ::= SET {
   recordType                [0] IMPLICIT RecordType,
   recipientMmsRSAddress     [1] IMPLICIT MMSRSAddress,
   messageID                 [2] IMPLICIT OCTET STRING,
   replyChargingID           [3] IMPLICIT OCTET STRING OPTIONAL,
   senderAddress             [4] IMPLICIT MMSAgentAddress,
   recipientAddress          [5] IMPLICIT MMSAgentAddress,
   accessCorrelation         [6] AccessCorrelation OPTIONAL,
   messageClass              [7] IMPLICIT MessageClass OPTIONAL,
   mmComponentType           [8] IMPLICIT MMComponentType OPTIONAL,
   messageSize               [9] IMPLICIT INTEGER,
   timeOfExpiry              [10] WaitTime OPTIONAL,
   messageReference          [11] IMPLICIT OCTET STRING,
   deliveryReportRequested   [12] IMPLICIT BOOLEAN OPTIONAL,
   replyCharging             [13] IMPLICIT BOOLEAN OPTIONAL,
   replyDeadline             [14] WaitTime OPTIONAL,
   replyChargingSize         [15] IMPLICIT INTEGER OPTIONAL,
   mmStatusCode              [16] IMPLICIT MMStatusCodeType OPTIONAL,
   statusText                [17] IMPLICIT OCTET STRING OPTIONAL,
   recordTimeStamp           [18] IMPLICIT OCTET STRING ( SIZE( 9 ) ) OPTIONAL,
   localSequenceNumber       [19] IMPLICIT INTEGER ( 0 .. 4294967295 ) OPTIONAL,
   recordExtensions          [20] IMPLICIT SET  OF
      ManagementExtension OPTIONAL,
   mscfInformation           [21] IMPLICIT MSCFInformation OPTIONAL,
   vaspID                    [22] IMPLICIT OCTET STRING OPTIONAL,
   vasID                     [23] IMPLICIT OCTET STRING OPTIONAL,
   sGSNPLMNIdentifier        [24] IMPLICIT OCTET STRING ( SIZE( 3 ) ) OPTIONAL,
   rATType                   [25] IMPLICIT INTEGER ( 0 .. 255 ) OPTIONAL,
   mSTimeZone                [26] IMPLICIT OCTET STRING ( SIZE( 2 ) ) OPTIONAL}

MMR1NRsRecord ::= SET {
   recordType              [0] IMPLICIT RecordType,
   recipientMmsRSAddress   [1] IMPLICIT MMSRSAddress,
   messageID               [2] IMPLICIT OCTET STRING,
   recipientAddress        [3] IMPLICIT MMSAgentAddress,
   accessCorrelation       [4] AccessCorrelation OPTIONAL,
   reportAllowed           [5] IMPLICIT BOOLEAN OPTIONAL,
   mmStatusCode            [6] IMPLICIT MMStatusCodeType OPTIONAL,
   statusText              [7] IMPLICIT OCTET STRING OPTIONAL,
   recordTimeStamp         [8] IMPLICIT OCTET STRING ( SIZE( 9 ) ) OPTIONAL,
   localSequenceNumber     [9] IMPLICIT INTEGER ( 0 .. 4294967295 ) OPTIONAL,
   recordExtensions        [10] IMPLICIT SET  OF
      ManagementExtension OPTIONAL,
   sGSNPLMNIdentifier      [11] IMPLICIT OCTET STRING ( SIZE( 3 ) ) OPTIONAL,
   rATType                 [12] IMPLICIT INTEGER ( 0 .. 255 ) OPTIONAL,
   mSTimeZone              [13] IMPLICIT OCTET STRING ( SIZE( 2 ) ) OPTIONAL}

MMR1RtRecord ::= SET {
   recordType                [0] IMPLICIT RecordType,
   recipientMmsRSAddress     [1] IMPLICIT MMSRSAddress,
   messageID                 [2] IMPLICIT OCTET STRING,
   replyChargingID           [3] IMPLICIT OCTET STRING OPTIONAL,
   senderAddress             [4] IMPLICIT MMSAgentAddress OPTIONAL,
   recipientAddress          [5] IMPLICIT MMSAgentAddress,
   accessCorrelation         [6] AccessCorrelation OPTIONAL,
   contentType               [7] IMPLICIT OCTET STRING,
   mmComponentType           [8] IMPLICIT MMComponentType OPTIONAL,
   messageClass              [9] IMPLICIT MessageClass OPTIONAL,
   submissionTime            [10] IMPLICIT OCTET STRING ( SIZE( 9 ) ),
   messageSize               [11] IMPLICIT INTEGER OPTIONAL,
   deliveryReportRequested   [12] IMPLICIT BOOLEAN OPTIONAL,
   priority                  [13] IMPLICIT PriorityType OPTIONAL,
   readReplyRequested        [14] IMPLICIT BOOLEAN OPTIONAL,
   mmStatusCode              [15] IMPLICIT MMStatusCodeType OPTIONAL,
   statusText                [16] IMPLICIT OCTET STRING OPTIONAL,
   replyDeadline             [17] WaitTime OPTIONAL,
   replyChargingSize         [18] IMPLICIT INTEGER OPTIONAL,
   durationOfTransmission    [19] IMPLICIT INTEGER OPTIONAL,
   timeOfExpiry              [20] WaitTime OPTIONAL,
   recordTimeStamp           [21] IMPLICIT OCTET STRING ( SIZE( 9 ) ) OPTIONAL,
   localSequenceNumber       [22] IMPLICIT INTEGER ( 0 .. 4294967295 ) OPTIONAL,
   recordExtensions          [23] IMPLICIT SET  OF
      ManagementExtension OPTIONAL,
   messageReference          [24] IMPLICIT OCTET STRING,
   vaspID                    [25] IMPLICIT OCTET STRING OPTIONAL,
   vasID                     [26] IMPLICIT OCTET STRING OPTIONAL,
   sGSNPLMNIdentifier        [27] IMPLICIT OCTET STRING ( SIZE( 3 ) ) OPTIONAL,
   rATType                   [28] IMPLICIT INTEGER ( 0 .. 255 ) OPTIONAL,
   mSTimeZone                [29] IMPLICIT OCTET STRING ( SIZE( 2 ) ) OPTIONAL}

MMR1ARecord ::= SET {
   recordType              [0] IMPLICIT RecordType,
   recipientMmsRSAddress   [1] IMPLICIT MMSRSAddress,
   messageID               [2] IMPLICIT OCTET STRING,
   recipientAddress        [3] IMPLICIT MMSAgentAddress,
   accessCorrelation       [4] AccessCorrelation OPTIONAL,
   reportAllowed           [5] IMPLICIT BOOLEAN OPTIONAL,
   mmStatusCode            [6] IMPLICIT MMStatusCodeType OPTIONAL,
   statusText              [7] IMPLICIT OCTET STRING OPTIONAL,
   recordTimeStamp         [8] IMPLICIT OCTET STRING ( SIZE( 9 ) ) OPTIONAL,
   localSequenceNumber     [9] IMPLICIT INTEGER ( 0 .. 4294967295 ) OPTIONAL,
   recordExtensions        [10] IMPLICIT SET  OF
      ManagementExtension OPTIONAL,
   sGSNPLMNIdentifier      [11] IMPLICIT OCTET STRING ( SIZE( 3 ) ) OPTIONAL,
   rATType                 [12] IMPLICIT INTEGER ( 0 .. 255 ) OPTIONAL,
   mSTimeZone              [13] IMPLICIT OCTET STRING ( SIZE( 2 ) ) OPTIONAL}

MMR4DRqRecord ::= SET {
   recordType               [0] IMPLICIT RecordType,
   recipientMmsRSAddress    [1] IMPLICIT MMSRSAddress,
   originatorMmsRSAddress   [2] IMPLICIT MMSRSAddress,
   messageID                [3] IMPLICIT OCTET STRING,
   mms3GPPVersion           [4] IMPLICIT OCTET STRING OPTIONAL,
   originatorAddress        [5] IMPLICIT MMSAgentAddress,
   recipientAddress         [6] IMPLICIT MMSAgentAddress,
   mmDateAndTime            [7] IMPLICIT OCTET STRING ( SIZE( 9 ) ) OPTIONAL,
   acknowledgementRequest   [8] IMPLICIT BOOLEAN,
   mmStatusCode             [9] IMPLICIT MMStatusCodeType OPTIONAL,
   statusText               [10] IMPLICIT OCTET STRING OPTIONAL,
   recordTimeStamp          [11] IMPLICIT OCTET STRING ( SIZE( 9 ) ) OPTIONAL,
   localSequenceNumber      [12] IMPLICIT INTEGER ( 0 .. 4294967295 ) OPTIONAL,
   recordExtensions         [13] IMPLICIT SET  OF
      ManagementExtension OPTIONAL}

MMR4DRsRecord ::= SET {
   recordType               [0] IMPLICIT RecordType,
   recipientMmsRSAddress    [1] IMPLICIT MMSRSAddress,
   originatorMmsRSAddress   [2] IMPLICIT MMSRSAddress,
   messageID                [3] IMPLICIT OCTET STRING,
   mms3GPPVersion           [4] IMPLICIT OCTET STRING OPTIONAL,
   requestStatusCode        [5] IMPLICIT RequestStatusCodeType OPTIONAL,
   statusText               [6] IMPLICIT OCTET STRING OPTIONAL,
   recordTimeStamp          [7] IMPLICIT OCTET STRING ( SIZE( 9 ) ) OPTIONAL,
   localSequenceNumber      [8] IMPLICIT INTEGER ( 0 .. 4294967295 ) OPTIONAL,
   recordExtensions         [9] IMPLICIT SET  OF
      ManagementExtension OPTIONAL}

MMR1RRRecord ::= SET {
   recordType              [0] IMPLICIT RecordType,
   recipientMmsRSAddress   [1] IMPLICIT MMSRSAddress,
   messageID               [2] IMPLICIT OCTET STRING,
   recipientAddress        [3] IMPLICIT MMSAgentAddress,
   originatorAddress       [4] IMPLICIT MMSAgentAddress,
   accessCorrelation       [5] AccessCorrelation OPTIONAL,
   mmStatusCode            [6] IMPLICIT MMStatusCodeType OPTIONAL,
   statusText              [7] IMPLICIT OCTET STRING OPTIONAL,
   recordTimeStamp         [8] IMPLICIT OCTET STRING ( SIZE( 9 ) ) OPTIONAL,
   localSequenceNumber     [9] IMPLICIT INTEGER ( 0 .. 4294967295 ) OPTIONAL,
   recordExtensions        [10] IMPLICIT SET  OF
      ManagementExtension OPTIONAL,
   sGSNPLMNIdentifier      [11] IMPLICIT OCTET STRING ( SIZE( 3 ) ) OPTIONAL,
   rATType                 [12] IMPLICIT INTEGER ( 0 .. 255 ) OPTIONAL,
   mSTimeZone              [13] IMPLICIT OCTET STRING ( SIZE( 2 ) ) OPTIONAL}

MMR4RRqRecord ::= SET {
   recordType               [0] IMPLICIT RecordType,
   recipientMmsRSAddress    [1] IMPLICIT MMSRSAddress,
   originatorMmsRSAddress   [2] IMPLICIT MMSRSAddress,
   messageID                [3] IMPLICIT OCTET STRING,
   mms3GPPVersion           [4] IMPLICIT OCTET STRING OPTIONAL,
   originatorAddress        [5] IMPLICIT MMSAgentAddress,
   recipientAddress         [6] IMPLICIT MMSAgentAddress,
   mmDateAndTime            [7] IMPLICIT OCTET STRING ( SIZE( 9 ) ) OPTIONAL,
   acknowledgementRequest   [8] IMPLICIT BOOLEAN,
   mmStatusCode             [9] IMPLICIT MMStatusCodeType OPTIONAL,
   statusText               [10] IMPLICIT OCTET STRING OPTIONAL,
   recordTimeStamp          [11] IMPLICIT OCTET STRING ( SIZE( 9 ) ) OPTIONAL,
   localSequenceNumber      [12] IMPLICIT INTEGER ( 0 .. 4294967295 ) OPTIONAL,
   recordExtensions         [13] IMPLICIT SET  OF
      ManagementExtension OPTIONAL}

MMR4RRsRecord ::= SET {
   recordType               [0] IMPLICIT RecordType,
   recipientMmsRSAddress    [1] IMPLICIT MMSRSAddress,
   originatorMmsRSAddress   [2] IMPLICIT MMSRSAddress,
   messageID                [3] IMPLICIT OCTET STRING,
   mms3GPPVersion           [4] IMPLICIT OCTET STRING OPTIONAL,
   requestStatusCode        [5] IMPLICIT RequestStatusCodeType OPTIONAL,
   statusText               [6] IMPLICIT OCTET STRING OPTIONAL,
   recordTimeStamp          [7] IMPLICIT OCTET STRING ( SIZE( 9 ) ) OPTIONAL,
   localSequenceNumber      [8] IMPLICIT INTEGER ( 0 .. 4294967295 ) OPTIONAL,
   recordExtensions         [9] IMPLICIT SET  OF
      ManagementExtension OPTIONAL}

MMRMDRecord ::= SET {
   recordType               [0] IMPLICIT RecordType,
   originatorMmsRSAddress   [1] IMPLICIT MMSRSAddress,
   recipientMmsRSAddress    [2] IMPLICIT MMSRSAddress OPTIONAL,
   messageID                [3] IMPLICIT OCTET STRING,
   messageSize              [4] IMPLICIT INTEGER,
   mmStatusCode             [5] IMPLICIT MMStatusCodeType OPTIONAL,
   statusText               [6] IMPLICIT OCTET STRING OPTIONAL,
   recordTimeStamp          [7] IMPLICIT OCTET STRING ( SIZE( 9 ) ) OPTIONAL,
   localSequenceNumber      [8] IMPLICIT INTEGER ( 0 .. 4294967295 ) OPTIONAL,
   recordExtensions         [9] IMPLICIT SET  OF
      ManagementExtension OPTIONAL}

MMFRecord  ::= SET {
   recordType                [0] IMPLICIT RecordType,
   forwardingMmsRSAddress    [1] IMPLICIT MMSRSAddress,
   messageID                 [2] IMPLICIT OCTET STRING,
   forwardingAddress         [3] IMPLICIT MMSAgentAddress,
   recipientAddresses        [4] IMPLICIT SET  OF
      MMSAgentAddress,
   chargeInformation         [5] IMPLICIT ChargeInformation OPTIONAL,
   timeOfExpiry              [6] WaitTime OPTIONAL,
   earliestTimeOfDelivery    [7] WaitTime OPTIONAL,
   deliveryReportRequested   [8] IMPLICIT BOOLEAN OPTIONAL,
   readReplyRequested        [9] IMPLICIT BOOLEAN OPTIONAL,
   messageReference          [10] IMPLICIT OCTET STRING,
   mmStatusCode              [11] IMPLICIT MMStatusCodeType OPTIONAL,
   statusText                [12] IMPLICIT OCTET STRING OPTIONAL,
   recordTimeStamp           [13] IMPLICIT OCTET STRING ( SIZE( 9 ) ) OPTIONAL,
   localSequenceNumber       [14] IMPLICIT INTEGER ( 0 .. 4294967295 ) OPTIONAL,
   recordExtensions          [15] IMPLICIT SET  OF
      ManagementExtension OPTIONAL,
   mMBoxstorageInformation   [16] IMPLICIT MMBoxStorageInformation OPTIONAL}

MMBx1SRecord ::= SET {
   recordType           [0] IMPLICIT RecordType,
   mmsRelayAddress      [1] IPAddress,
   managingAddress      [2] IMPLICIT MMSAgentAddress,
   accessCorrelation    [3] AccessCorrelation OPTIONAL,
   contentType          [4] IMPLICIT OCTET STRING OPTIONAL,
   messageSize          [5] IMPLICIT INTEGER OPTIONAL,
   messageReference     [6] IMPLICIT OCTET STRING OPTIONAL,
   mmState              [7] IMPLICIT OCTET STRING OPTIONAL,
   mmFlags              [8] IMPLICIT OCTET STRING OPTIONAL,
   storeStatus          [9] IMPLICIT StoreStatus OPTIONAL,
   storeStatusText      [10] IMPLICIT OCTET STRING OPTIONAL,
   sequenceNumber       [11] IMPLICIT INTEGER OPTIONAL,
   timeStamp            [12] IMPLICIT OCTET STRING ( SIZE( 9 ) ) OPTIONAL,
   recordExtensions     [13] IMPLICIT SET  OF
      ManagementExtension OPTIONAL,
   sGSNPLMNIdentifier   [14] IMPLICIT OCTET STRING ( SIZE( 3 ) ) OPTIONAL,
   rATType              [15] IMPLICIT INTEGER ( 0 .. 255 ) OPTIONAL,
   mSTimeZone           [16] IMPLICIT OCTET STRING ( SIZE( 2 ) ) OPTIONAL}

MMBx1VRecord ::= SET {
   recordType           [0] IMPLICIT RecordType,
   mmsRelayAddress      [1] IPAddress,
   managingAddress      [2] IMPLICIT MMSAgentAddress,
   accessCorrelation    [3] AccessCorrelation OPTIONAL,
   attributesList       [4] IMPLICIT AttributesList OPTIONAL,
   messageSelection     [5] IMPLICIT INTEGER OPTIONAL,
   start                [6] IMPLICIT INTEGER OPTIONAL,
   limit                [7] IMPLICIT INTEGER OPTIONAL,
   totalsRequested      [8] IMPLICIT BOOLEAN OPTIONAL,
   quotasRequested      [9] IMPLICIT BOOLEAN OPTIONAL,
   mmListing            [10] IMPLICIT AttributesList OPTIONAL,
   requestStatusCode    [11] IMPLICIT RequestStatusCodeType OPTIONAL,
   statusText           [12] IMPLICIT OCTET STRING OPTIONAL,
   totals               [13] IMPLICIT Totals OPTIONAL,
   quotas               [14] IMPLICIT Quotas OPTIONAL,
   sequenceNumber       [15] IMPLICIT INTEGER OPTIONAL,
   timeStamp            [16] IMPLICIT OCTET STRING ( SIZE( 9 ) ) OPTIONAL,
   recordExtensions     [17] IMPLICIT SET  OF
      ManagementExtension OPTIONAL,
   sGSNPLMNIdentifier   [18] IMPLICIT OCTET STRING ( SIZE( 3 ) ) OPTIONAL,
   rATType              [19] IMPLICIT INTEGER ( 0 .. 255 ) OPTIONAL,
   mSTimeZone           [20] IMPLICIT OCTET STRING ( SIZE( 2 ) ) OPTIONAL}

MMBx1URecord ::= SET {
   recordType               [0] IMPLICIT RecordType,
   mmsRelayAddress          [1] IPAddress,
   managingAddress          [2] IMPLICIT MMSAgentAddress,
   accessCorrelation        [3] AccessCorrelation OPTIONAL,
   recipientsAddressList    [4] IMPLICIT SET  OF
      MMSAgentAddress,
   messageClass             [5] IMPLICIT MessageClass OPTIONAL,
   uploadTime               [6] IMPLICIT OCTET STRING ( SIZE( 9 ) ) OPTIONAL,
   timeOfExpiry             [7] WaitTime OPTIONAL,
   earliestTimeOfDelivery   [8] WaitTime OPTIONAL,
   priority                 [9] IMPLICIT PriorityType OPTIONAL,
   mmState                  [10] IMPLICIT OCTET STRING OPTIONAL,
   mmFlags                  [11] IMPLICIT OCTET STRING OPTIONAL,
   contentType              [12] IMPLICIT OCTET STRING OPTIONAL,
   messageSize              [13] IMPLICIT INTEGER OPTIONAL,
   messageReference         [14] IMPLICIT OCTET STRING OPTIONAL,
   requestStatusCode        [15] IMPLICIT RequestStatusCodeType OPTIONAL,
   statusText               [16] IMPLICIT OCTET STRING OPTIONAL,
   sequenceNumber           [17] IMPLICIT INTEGER OPTIONAL,
   timeStamp                [18] IMPLICIT OCTET STRING ( SIZE( 9 ) ) OPTIONAL,
   recordExtensions         [19] IMPLICIT SET  OF
      ManagementExtension OPTIONAL,
   sGSNPLMNIdentifier       [20] IMPLICIT OCTET STRING ( SIZE( 3 ) ) OPTIONAL,
   rATType                  [21] IMPLICIT INTEGER ( 0 .. 255 ) OPTIONAL,
   mSTimeZone               [22] IMPLICIT OCTET STRING ( SIZE( 2 ) ) OPTIONAL}

MMBx1DRecord ::= SET {
   recordType           [0] IMPLICIT RecordType,
   mmsRelayAddress      [1] IPAddress,
   managingAddress      [2] IMPLICIT MMSAgentAddress,
   accessCorrelation    [3] AccessCorrelation OPTIONAL,
   messageReference     [4] IMPLICIT OCTET STRING OPTIONAL,
   requestStatusCode    [5] IMPLICIT RequestStatusCodeType OPTIONAL,
   statusText           [6] IMPLICIT OCTET STRING OPTIONAL,
   sequenceNumber       [7] IMPLICIT INTEGER OPTIONAL,
   timeStamp            [8] IMPLICIT OCTET STRING ( SIZE( 9 ) ) OPTIONAL,
   recordExtensions     [9] IMPLICIT SET  OF
      ManagementExtension OPTIONAL,
   sGSNPLMNIdentifier   [20] IMPLICIT OCTET STRING ( SIZE( 3 ) ) OPTIONAL,
   rATType              [21] IMPLICIT INTEGER ( 0 .. 255 ) OPTIONAL,
   mSTimeZone           [22] IMPLICIT OCTET STRING ( SIZE( 2 ) ) OPTIONAL}

MM7SRecord ::= SET {
   recordType                     [0] IMPLICIT RecordType,
   originatorMmsRSAddress         [1] IMPLICIT MMSRSAddress,
   linkedID                       [2] IMPLICIT OCTET STRING OPTIONAL,
   vaspID                         [3] IMPLICIT OCTET STRING,
   vasID                          [4] IMPLICIT OCTET STRING,
   messageID                      [5] IMPLICIT OCTET STRING,
   originatorAddress              [6] IMPLICIT MMSAgentAddress,
   recipientAddresses             [7] IMPLICIT SET  OF
      MMSAgentAddress,
   serviceCode                    [8] IMPLICIT OCTET STRING OPTIONAL,
   contentType                    [9] IMPLICIT OCTET STRING,
   mmComponentType                [10] IMPLICIT MMComponentType OPTIONAL,
   messageSize                    [11] IMPLICIT INTEGER,
   messageClass                   [12] IMPLICIT MessageClass OPTIONAL,
   chargeInformation              [13] IMPLICIT ChargeInformation OPTIONAL,
   submissionTime                 [14] IMPLICIT OCTET STRING ( SIZE( 9 ) ) OPTIONAL,
   timeOfExpiry                   [15] WaitTime OPTIONAL,
   earliestTimeOfDelivery         [16] WaitTime OPTIONAL,
   deliveryReportRequested        [17] IMPLICIT BOOLEAN OPTIONAL,
   readReplyRequested             [18] IMPLICIT BOOLEAN OPTIONAL,
   replyCharging                  [19] IMPLICIT BOOLEAN OPTIONAL,
   replyDeadline                  [20] WaitTime OPTIONAL,
   replyChargingSize              [21] IMPLICIT INTEGER OPTIONAL,
   priority                       [22] IMPLICIT PriorityType OPTIONAL,
   messageDistributionIndicator   [23] IMPLICIT BOOLEAN OPTIONAL,
   requestStatusCode              [24] IMPLICIT RequestStatusCodeType OPTIONAL,
   statusText                     [25] IMPLICIT OCTET STRING OPTIONAL,
   recordTimeStamp                [26] IMPLICIT OCTET STRING ( SIZE( 9 ) ),
   localSequenceNumber            [27] IMPLICIT INTEGER ( 0 .. 4294967295 ) OPTIONAL,
   recordExtensions               [28] IMPLICIT SET  OF
      ManagementExtension OPTIONAL,
   mscfInformation                [29] IMPLICIT MSCFInformation OPTIONAL}

MM7DRqRecord ::= SET {
   recordType              [0] IMPLICIT RecordType,
   recipientMmsRSAddress   [1] IMPLICIT MMSRSAddress,
   linkedID                [2] IMPLICIT OCTET STRING OPTIONAL,
   replyChargingID         [3] IMPLICIT OCTET STRING OPTIONAL,
   originatorAddress       [4] IMPLICIT MMSAgentAddress,
   recipientAddress        [5] IMPLICIT MMSAgentAddress,
   mmComponentType         [6] IMPLICIT MMComponentType OPTIONAL,
   messageSize             [7] IMPLICIT INTEGER,
   contentType             [8] IMPLICIT OCTET STRING,
   priority                [9] IMPLICIT PriorityType OPTIONAL,
   recordTimeStamp         [10] IMPLICIT OCTET STRING ( SIZE( 9 ) ) OPTIONAL,
   localSequenceNumber     [11] IMPLICIT INTEGER ( 0 .. 4294967295 ) OPTIONAL,
   recordExtensions        [12] IMPLICIT SET  OF
      ManagementExtension OPTIONAL}

MM7DRsRecord ::= SET {
   recordType              [0] IMPLICIT RecordType,
   recipientMmsRSAddress   [1] IMPLICIT MMSRSAddress,
   messageID               [2] IMPLICIT OCTET STRING,
   recipientAddress        [3] IMPLICIT MMSAgentAddress,
   serviceCode             [4] IMPLICIT OCTET STRING OPTIONAL,
   requestStatusCode       [5] IMPLICIT RequestStatusCodeType OPTIONAL,
   statusText              [6] IMPLICIT OCTET STRING OPTIONAL,
   recordTimeStamp         [7] IMPLICIT OCTET STRING ( SIZE( 9 ) ) OPTIONAL,
   localSequenceNumber     [8] IMPLICIT INTEGER ( 0 .. 4294967295 ) OPTIONAL,
   recordExtensions        [9] IMPLICIT SET  OF
      ManagementExtension OPTIONAL}

MM7CRecord ::= SET {
   recordType               [0] IMPLICIT RecordType,
   originatorMmsRSAddress   [1] IMPLICIT MMSRSAddress,
   vaspID                   [2] IMPLICIT OCTET STRING,
   vasID                    [3] IMPLICIT OCTET STRING,
   messageID                [4] IMPLICIT OCTET STRING,
   originatorAddress        [5] IMPLICIT MMSAgentAddress,
   serviceCode              [6] IMPLICIT OCTET STRING OPTIONAL,
   requestStatusCode        [7] IMPLICIT RequestStatusCodeType OPTIONAL,
   statusText               [8] IMPLICIT OCTET STRING OPTIONAL,
   recordTimeStamp          [9] IMPLICIT OCTET STRING ( SIZE( 9 ) ) OPTIONAL,
   localSequenceNumber      [10] IMPLICIT INTEGER ( 0 .. 4294967295 ) OPTIONAL,
   recordExtensions         [11] IMPLICIT SET  OF
      ManagementExtension OPTIONAL}

MM7RRecord ::= SET {
   recordType               [0] IMPLICIT RecordType,
   originatorMmsRSAddress   [1] IMPLICIT MMSRSAddress,
   vaspID                   [2] IMPLICIT OCTET STRING,
   vasID                    [3] IMPLICIT OCTET STRING,
   messageID                [4] IMPLICIT OCTET STRING,
   originatorAddress        [5] IMPLICIT MMSAgentAddress,
   serviceCode              [6] IMPLICIT OCTET STRING OPTIONAL,
   contentType              [7] IMPLICIT OCTET STRING,
   submissionTime           [8] IMPLICIT OCTET STRING ( SIZE( 9 ) ) OPTIONAL,
   timeOfExpiry             [9] WaitTime OPTIONAL,
   earliestTimeOfDelivery   [10] WaitTime OPTIONAL,
   requestStatusCode        [11] IMPLICIT RequestStatusCodeType OPTIONAL,
   statusText               [12] IMPLICIT OCTET STRING OPTIONAL,
   recordTimeStamp          [13] IMPLICIT OCTET STRING ( SIZE( 9 ) ) OPTIONAL,
   localSequenceNumber      [14] IMPLICIT INTEGER ( 0 .. 4294967295 ) OPTIONAL,
   recordExtensions         [15] IMPLICIT SET  OF
      ManagementExtension OPTIONAL}

MM7DRRqRecord ::= SET {
   recordType              [0] IMPLICIT RecordType,
   recipientMmsRSAddress   [1] IMPLICIT MMSRSAddress OPTIONAL,
   messageID               [2] IMPLICIT OCTET STRING,
   originatorAddress       [3] IMPLICIT MMSAgentAddress OPTIONAL,
   recipientAddress        [4] IMPLICIT MMSAgentAddress,
   mmDateAndTime           [5] IMPLICIT OCTET STRING ( SIZE( 9 ) ) OPTIONAL,
   mmStatusCode            [6] IMPLICIT MMStatusCodeType,
   mmStatusText            [7] IMPLICIT OCTET STRING OPTIONAL,
   recordTimeStamp         [8] IMPLICIT OCTET STRING ( SIZE( 9 ) ) OPTIONAL,
   localSequenceNumber     [9] IMPLICIT INTEGER ( 0 .. 4294967295 ) OPTIONAL,
   recordExtensions        [10] IMPLICIT SET  OF
      ManagementExtension OPTIONAL}

MM7DRRsRecord ::= SET {
   recordType              [0] IMPLICIT RecordType,
   recipientMmsRSAddress   [1] IMPLICIT MMSRSAddress OPTIONAL,
   messageID               [2] IMPLICIT OCTET STRING,
   originatorAddress       [3] IMPLICIT MMSAgentAddress OPTIONAL,
   recipientAddress        [4] IMPLICIT MMSAgentAddress,
   requestStatusCode       [5] IMPLICIT RequestStatusCodeType OPTIONAL,
   statusText              [6] IMPLICIT OCTET STRING OPTIONAL,
   recordTimeStamp         [7] IMPLICIT OCTET STRING ( SIZE( 9 ) ) OPTIONAL,
   localSequenceNumber     [8] IMPLICIT INTEGER ( 0 .. 4294967295 ) OPTIONAL,
   recordExtensions        [9] IMPLICIT SET  OF
      ManagementExtension OPTIONAL}

MM7RRqRecord ::= SET {
   recordType              [0] IMPLICIT RecordType,
   recipientMmsRSAddress   [1] IMPLICIT MMSRSAddress OPTIONAL,
   messageID               [2] IMPLICIT OCTET STRING,
   originatorAddress       [3] IMPLICIT MMSAgentAddress OPTIONAL,
   recipientAddress        [4] IMPLICIT MMSAgentAddress,
   mmDateAndTime           [5] IMPLICIT OCTET STRING ( SIZE( 9 ) ) OPTIONAL,
   readStatus              [6] IMPLICIT MMStatusCodeType,
   mmStatusText            [7] IMPLICIT OCTET STRING OPTIONAL,
   recordTimeStamp         [8] IMPLICIT OCTET STRING ( SIZE( 9 ) ) OPTIONAL,
   localSequenceNumber     [9] IMPLICIT INTEGER ( 0 .. 4294967295 ) OPTIONAL,
   recordExtensions        [10] IMPLICIT SET  OF
      ManagementExtension OPTIONAL}

MM7RRsRecord ::= SET {
   recordType              [0] IMPLICIT RecordType,
   recipientMmsRSAddress   [1] IMPLICIT MMSRSAddress OPTIONAL,
   messageID               [2] IMPLICIT OCTET STRING,
   originatorAddress       [3] IMPLICIT MMSAgentAddress OPTIONAL,
   recipientAddress        [4] IMPLICIT MMSAgentAddress,
   requestStatusCode       [5] IMPLICIT RequestStatusCodeType OPTIONAL,
   statusText              [6] IMPLICIT OCTET STRING OPTIONAL,
   recordTimeStamp         [7] IMPLICIT OCTET STRING ( SIZE( 9 ) ) OPTIONAL,
   localSequenceNumber     [8] IMPLICIT INTEGER ( 0 .. 4294967295 ) OPTIONAL,
   recordExtensions        [9] IMPLICIT SET  OF
      ManagementExtension OPTIONAL}

AccessCorrelation ::= CHOICE {
   circuitSwitched     [0] IMPLICIT CircuitSwitchedAccess,
   packetSwitched      [1] IMPLICIT PacketSwitchedAccess}

AttributesList ::= SEQUENCE {
   messageID       [0] IMPLICIT OCTET STRING,
   dateAndTime     [1] IMPLICIT OCTET STRING ( SIZE( 9 ) ),
   senderAddress   [2] IMPLICIT MMSRSAddress,
   subject         [3] IMPLICIT OCTET STRING,
   messageSize     [4] IMPLICIT INTEGER,
   mmFlags         [5] IMPLICIT OCTET STRING,
   mmState         [6] IMPLICIT MMState}

ChargeInformation ::= SEQUENCE {
   chargedparty   [0] IMPLICIT ChargedParty OPTIONAL,
   chargetype     [1] IMPLICIT ChargeType OPTIONAL}

ChargedParty ::= ENUMERATED {
   sender                ( 0 ),
   recipient             ( 1 ),
   both                  ( 2 ),
   neither               ( 3 ),
   notspecifiedbyVASP    ( 99 ) }

ChargeType ::= ENUMERATED {
   postpaid    ( 0 ),
   pre-paid    ( 1 ) }

CircuitSwitchedAccess ::= SEQUENCE {
   mSCIdentifier         [0] IMPLICIT OCTET STRING ( SIZE( 1 .. 20 ) ) ( SIZE( 1 .. 9 ) ),
   callReferenceNumber   [1] IMPLICIT OCTET STRING ( SIZE( 1 .. 8 ) )}

ContentType ::= OCTET STRING

DataVolume ::= INTEGER

DeltaSeconds ::= OCTET STRING ( SIZE( 8 ) )

MediaComponent ::= SEQUENCE {
   mediaType   [0] IMPLICIT OCTET STRING,
   mediaSize   [1] IMPLICIT INTEGER}

MediaComponents ::= SET  OF
   MediaComponent

MessageSelection ::= INTEGER

MMBoxStorageInformation ::= SET {
   mmState                  [0] IMPLICIT MMState,
   mmFlag                   [1] IMPLICIT OCTET STRING,
   storeStatus              [2] IMPLICIT StoreStatus,
   storeStatusText          [3] IMPLICIT OCTET STRING,
   storedMessageReference   [4] IMPLICIT OCTET STRING}

MMComponentType ::= SEQUENCE {
   subject    [0] IMPLICIT SubjectComponent,
   media      [1] IMPLICIT SET  OF
      MediaComponent}

MMSAgentAddress ::= SEQUENCE {
   mMSAgentAddressData   [0] MMSAgentAddressData,
   mMSRecipientType      [1] IMPLICIT SEQUENCE  OF
      MMSRecipientType OPTIONAL}

MMSAgentAddresses ::= SET  OF
   MMSAgentAddress

MMSAgentAddressData ::= CHOICE {
   eMail-address     [0] IMPLICIT OCTET STRING,
   mSISDN            [1] IMPLICIT OCTET STRING ( SIZE( 1 .. 20 ) ) ( SIZE( 1 .. 9 ) ),
   shortCode         [2] IMPLICIT OCTET STRING}

MMSRecipientType ::= ENUMERATED {
   tO          ( 0 ),
   cC          ( 1 ),
   bCC         ( 2 ) }

MMSRSAddress ::= SEQUENCE {
   domainName   [0] IMPLICIT OCTET STRING OPTIONAL,
   iPAddress    [2] IPAddress OPTIONAL}

MMState    ::= ENUMERATED {
   draft        ( 0 ),
   sent         ( 1 ),
   new          ( 2 ),
   retrieved    ( 3 ),
   forwarded    ( 4 ) }

MMStatusCodeType ::= ENUMERATED {
   retrieved                  ( 0 ),
   forwarded                  ( 1 ),
   expired                    ( 2 ),
   rejected                   ( 3 ),
   deferred                   ( 4 ),
   unrecognised               ( 5 ),
   read                       ( 6 ),
   deletedWithoutBeingRead    ( 7 ) }

MSCFInformation ::= SET {
   billingInformation    [0] IMPLICIT OCTET STRING OPTIONAL,
   routeingAddressList   [1] IMPLICIT SET  OF
      MMSAgentAddress OPTIONAL}

PacketSwitchedAccess ::= SEQUENCE {
   gSNAddress   [0] IPAddress,
   chargingID   [1] IMPLICIT INTEGER ( 0 .. 4294967295 )}

Quotas     ::= SEQUENCE {
   numberOfMessages   [0] IMPLICIT INTEGER OPTIONAL,
   numberOfOctets     [1] IMPLICIT INTEGER OPTIONAL}

RequestStatusCodeType ::= INTEGER {
   normalRelease               ( 0 ),
   abnormalRelease             ( 4 ),
   serviceDenied               ( 30 ),
   messageFormatCorrupt        ( 31 ),
   sendingAddressUnresolved    ( 32 ),
   messageNotFound             ( 33 ),
   networkProblem              ( 34 ),
   contentNotAccepted          ( 35 ),
   unsupportedMessage          ( 36 )}

RouteingAddress ::= SEQUENCE {
   eMail-address   [0] IMPLICIT OCTET STRING,
   mSISDN          [1] IMPLICIT OCTET STRING ( SIZE( 1 .. 20 ) ) ( SIZE( 1 .. 9 ) ) OPTIONAL,
   shortCode       [2] IMPLICIT OCTET STRING OPTIONAL}

RouteingAddressList ::= SET  OF
   MMSAgentAddress

StatusTextType ::= OCTET STRING

StoreStatus ::= INTEGER {
   stored                            ( 0 ),
   errorTransientFailure             ( 1 ),
   errorTransientMailboxFull         ( 2 ),
   errorTransientNetworkProblems     ( 3 ),
   errorPermanentFailure             ( 4 ),
   errorPermanentPermissionDenied    ( 5 ),
   errorPermanentMessageFormat       ( 6 ),
   errorPermanentMessageNotFound     ( 7 )}

SubjectComponent ::= SEQUENCE {
   subjectType   [0] IMPLICIT OCTET STRING,
   subjectSize   [1] IMPLICIT INTEGER}

Totals     ::= SEQUENCE {
   numberOfMessages   [0] IMPLICIT INTEGER OPTIONAL,
   numberOfOctets     [1] IMPLICIT INTEGER OPTIONAL}

WaitTime   ::= CHOICE {
   http-date         [0] IMPLICIT OCTET STRING ( SIZE( 9 ) ),
   delta-seconds     [1] IMPLICIT OCTET STRING ( SIZE( 8 ) )}


-- X.721 DMI-EXTENSION. The set is the standard form of the original
-- extensible empty table constraint ({, ...}) and does not change BER.
DMI-EXTENSION ::= CLASS {
    &id     OBJECT IDENTIFIER UNIQUE,
    &Value
}
WITH SYNTAX {
    TYPE &Value
    ID &id
}

ManagementExtensionSet DMI-EXTENSION ::= {...}

END
