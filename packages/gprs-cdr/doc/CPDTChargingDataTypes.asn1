-- Modified by Jonathan M. Wilbur to fix invalid syntax.
--     Expanded ASN1 Module 'CPDTChargingDataTypes'      
--SIEMENS ASN.1 Compiler         R6.31  (Production_6.31)    
--            Date: 2020-07-10 Time: 16:14:52            

CPDTChargingDataTypes
{itu-t(0) identified-organization(4) etsi(0) mobileDomain(0) charging(5)
cpdtChargingDataTypes(13) asn1Module(0) version2(1)}
DEFINITIONS
::=
BEGIN

RecordType ::= INTEGER {
   moCallRecord              ( 0 ), 
   mtCallRecord              ( 1 ), 
   roamingRecord             ( 2 ), 
   incGatewayRecord          ( 3 ), 
   outGatewayRecord          ( 4 ), 
   transitCallRecord         ( 5 ), 
   moSMSRecord               ( 6 ), 
   mtSMSRecord               ( 7 ), 
   moSMSIWRecord             ( 8 ), 
   mtSMSGWRecord             ( 9 ), 
   ssActionRecord            ( 10 ), 
   hlrIntRecord              ( 11 ), 
   locUpdateHLRRecord        ( 12 ), 
   locUpdateVLRRecord        ( 13 ), 
   commonEquipRecord         ( 14 ), 
   moTraceRecord             ( 15 ), 
   mtTraceRecord             ( 16 ), 
   termCAMELRecord           ( 17 ), 
   sgsnPDPRecord             ( 18 ), 
   sgsnMMRecord              ( 20 ), 
   sgsnSMORecord             ( 21 ), 
   sgsnSMTRecord             ( 22 ), 
   mtLCSRecord               ( 23 ), 
   moLCSRecord               ( 24 ), 
   niLCSRecord               ( 25 ), 
   sgsnMTLCSRecord           ( 26 ), 
   sgsnMOLCSRecord           ( 27 ), 
   sgsnNILCSRecord           ( 28 ), 
   mMO1SRecord               ( 30 ), 
   mMO4FRqRecord             ( 31 ), 
   mMO4FRsRecord             ( 32 ), 
   mMO4DRecord               ( 33 ), 
   mMO1DRecord               ( 34 ), 
   mMO4RRecord               ( 35 ), 
   mMO1RRecord               ( 36 ), 
   mMOMDRecord               ( 37 ), 
   mMR4FRecord               ( 38 ), 
   mMR1NRqRecord             ( 39 ), 
   mMR1NRsRecord             ( 40 ), 
   mMR1RtRecord              ( 41 ), 
   mMR1AFRecord              ( 42 ), 
   mMR4DRqRecord             ( 43 ), 
   mMR4DRsRecord             ( 44 ), 
   mMR1RRRecord              ( 45 ), 
   mMR4RRqRecord             ( 46 ), 
   mMR4RRsRecord             ( 47 ), 
   mMRMDRecord               ( 48 ), 
   mMFRecord                 ( 49 ), 
   mMBx1SRecord              ( 50 ), 
   mMBx1VRecord              ( 51 ), 
   mMBx1URecord              ( 52 ), 
   mMBx1DRecord              ( 53 ), 
   mM7SRecord                ( 54 ), 
   mM7DRqRecord              ( 55 ), 
   mM7DRsRecord              ( 56 ), 
   mM7CRecord                ( 57 ), 
   mM7RRecord                ( 58 ), 
   mM7DRRqRecord             ( 59 ), 
   mM7DRRsRecord             ( 60 ), 
   mM7RRqRecord              ( 61 ), 
   mM7RRsRecord              ( 62 ), 
   sCSCFRecord               ( 63 ), 
   pCSCFRecord               ( 64 ), 
   iCSCFRecord               ( 65 ), 
   mRFCRecord                ( 66 ), 
   mGCFRecord                ( 67 ), 
   bGCFRecord                ( 68 ), 
   aSRecord                  ( 69 ), 
   eCSCFRecord               ( 70 ), 
   iBCFRecord                ( 82 ), 
   tRFRecord                 ( 89 ), 
   tFRecord                  ( 90 ), 
   aTCFRecord                ( 91 ), 
   lCSGMORecord              ( 71 ), 
   lCSRGMTRecord             ( 72 ), 
   lCSHGMTRecord             ( 73 ), 
   lCSVGMTRecord             ( 74 ), 
   lCSGNIRecord              ( 75 ), 
   sgsnMBMSRecord            ( 76 ), 
   ggsnMBMSRecord            ( 77 ), 
   gwMBMSRecord              ( 86 ), 
   sUBBMSCRecord             ( 78 ), 
   cONTENTBMSCRecord         ( 79 ), 
   pPFRecord                 ( 80 ), 
   cPFRecord                 ( 81 ), 
   sGWRecord                 ( 84 ), 
   pGWRecord                 ( 85 ), 
   tDFRecord                 ( 92 ), 
   iPERecord                 ( 95 ), 
   ePDGRecord                ( 96 ), 
   tWAGRecord                ( 97 ), 
   mMTelRecord               ( 83 ), 
   mSCsRVCCRecord            ( 87 ), 
   mMTRFRecord               ( 88 ), 
   iCSRegisterRecord         ( 99 ), 
   sCSMORecord               ( 93 ), 
   sCSMTRecord               ( 94 ), 
   pFDDRecord                ( 100 ), 
   pFEDRecord                ( 101 ), 
   pFDCRecord                ( 102 ), 
   mECORecord                ( 103 ), 
   mERERecord                ( 104 ), 
   cPDTSCERecord             ( 105 ), 
   cPDTSNNRecord             ( 106 ), 
   sCDVTT4Record             ( 110 ), 
   sCSMOT4Record             ( 111 ), 
   iSMSMORecord              ( 112 ), 
   iSMSMTRecord              ( 113 ), 
   eASCERecord               ( 120 ), 
   chargingFunctionRecord    ( 200 )}

ChChSelectionMode ::= ENUMERATED {
   servingNodeSupplied     ( 0 ), 
   subscriptionSpecific    ( 1 ), 
   aPNSpecific             ( 2 ), 
   homeDefault             ( 3 ), 
   roamingDefault          ( 4 ), 
   visitingDefault         ( 5 ), 
   fixedDefault            ( 6 ) }

PositionMethodFailure-Diagnostic ::= ENUMERATED {
   congestion                                  ( 0 ), 
   insufficientResources                       ( 1 ), 
   insufficientMeasurementData                 ( 2 ), 
   inconsistentMeasurementData                 ( 3 ), 
   locationProcedureNotCompleted               ( 4 ), 
   locationProcedureNotSupportedByTargetMS     ( 5 ), 
   qoSNotAttainable                            ( 6 ), 
   positionMethodNotAvailableInNetwork         ( 7 ), 
   positionMethodNotAvailableInLocationArea    ( 8 ), 
   ...  }

UnauthorizedLCSClient-Diagnostic ::= ENUMERATED {
   noAdditionalInformation                           ( 0 ), 
   clientNotInMSPrivacyExceptionList                 ( 1 ), 
   callToClientNotSetup                              ( 2 ), 
   privacyOverrideNotApplicable                      ( 3 ), 
   disallowedByLocalRegulatoryRequirements           ( 4 ), 
   ... , 
   unauthorizedPrivacyClass                          ( 5 ), 
   unauthorizedCallSessionUnrelatedExternalClient    ( 6 ), 
   unauthorizedCallSessionRelatedExternalClient      ( 7 ) }

ServingPLMNRateControl ::= SEQUENCE {
   sPLMNDLRateControlValue   [0] IMPLICIT INTEGER, 
   sPLMNULRateControlValue   [1] IMPLICIT INTEGER}

SubscriptionID ::= SET {
   subscriptionIDType   [0] IMPLICIT ENUMERATED {
      eND-USER-E164       ( 0 ), 
      eND-USER-IMSI       ( 1 ), 
      eND-USER-SIP-URI    ( 2 ), 
      eND-USER-NAI        ( 3 ), 
      eND-USER-PRIVATE    ( 4 ) }, 
   subscriptionIDData   [1] IMPLICIT UTF8String}

ManagementExtension ::= SEQUENCE {
   identifier     DMI-EXTENSION.&id ({ManagementExtensionSet}) , 
   significance   [1] IMPLICIT BOOLEAN DEFAULT FALSE, 
   information    [2] DMI-EXTENSION.&Value ({ManagementExtensionSet}{@.identifier}) }

APNRateControlParameters ::= SEQUENCE {
   additionalExceptionReports   [0] IMPLICIT ENUMERATED {
      notAllowed    ( 0 ), 
      allowed       ( 1 ) } OPTIONAL, 
   rateControlTimeUnit          [1] IMPLICIT INTEGER {
      unrestricted    ( 0 ), 
      minute          ( 1 ), 
      hour            ( 2 ), 
      day             ( 3 ), 
      week            ( 4 )} OPTIONAL, 
   rateControlMaxRate           [2] IMPLICIT INTEGER OPTIONAL, 
   rateControlMaxMessageSize    [3] IMPLICIT INTEGER OPTIONAL}

APNRateControl ::= SEQUENCE {
   aPNRateControlUplink     [0] IMPLICIT APNRateControlParameters OPTIONAL, 
   aPNRateControlDownlink   [1] IMPLICIT APNRateControlParameters OPTIONAL}

Diagnostics ::= CHOICE {
   gsm0408Cause                                [0] IMPLICIT INTEGER, 
   gsm0902MapErrorValue                        [1] IMPLICIT INTEGER, 
   itu-tQ767Cause                              [2] IMPLICIT INTEGER, 
   networkSpecificCause                        [3] IMPLICIT ManagementExtension, 
   manufacturerSpecificCause                   [4] IMPLICIT ManagementExtension, 
   positionMethodFailureCause                  [5] IMPLICIT PositionMethodFailure-Diagnostic, 
   unauthorizedLCSClientCause                  [6] IMPLICIT UnauthorizedLCSClient-Diagnostic, 
   diameterResultCodeAndExperimentalResult     [7] IMPLICIT INTEGER}

CPDTRecord ::= CHOICE {
   cPDTSCERecord     [105] IMPLICIT CPDTSCERecord, 
   cPDTSNNRecord     [106] IMPLICIT CPDTSNNRecord}

CPDTSCERecord ::= SET {
   recordType                  [0] IMPLICIT RecordType, 
   retransmission              [1] IMPLICIT NULL OPTIONAL, 
   servedIMSI                  [2] IMPLICIT OCTET STRING ( SIZE( 3 .. 8 ) ) OPTIONAL, 
   servedMSISDN                [3] IMPLICIT OCTET STRING ( SIZE( 1 .. 20 ) ) ( SIZE( 1 .. 9 ) ) OPTIONAL, 
   chargingID                  [4] IMPLICIT INTEGER ( 0 .. 4294967295 ), 
   serviceContextID            [5] IMPLICIT UTF8String OPTIONAL, 
   nodeID                      [6] IMPLICIT IA5String  ( SIZE( 1 .. 20 ) ) OPTIONAL, 
   recordOpeningTime           [7] IMPLICIT OCTET STRING ( SIZE( 9 ) ), 
   duration                    [8] IMPLICIT INTEGER, 
   accessPointNameNI           [9] IMPLICIT IA5String  ( SIZE( 1 .. 63 ) ) OPTIONAL, 
   sCEFID                      [10] IMPLICIT OCTET STRING OPTIONAL, 
   chargingCharacteristics     [11] IMPLICIT OCTET STRING ( SIZE( 2 ) ), 
   chChSelectionMode           [12] IMPLICIT ChChSelectionMode OPTIONAL, 
   servingNodeIdentity         [13] IMPLICIT OCTET STRING OPTIONAL, 
   servingPLMNRateControl      [14] IMPLICIT ServingPLMNRateControl OPTIONAL, 
   listOfNIDDsubmission        [15] IMPLICIT SEQUENCE  OF
      NIDDsubmission OPTIONAL, 
   causeForRecClosing          [16] IMPLICIT CPCauseForRecClosing, 
   diagnostics                 [17] Diagnostics OPTIONAL, 
   localSequenceNumber         [18] IMPLICIT INTEGER ( 0 .. 4294967295 ) OPTIONAL, 
   recordSequenceNumber        [19] IMPLICIT INTEGER OPTIONAL, 
   recordExtensions            [20] IMPLICIT SET  OF
      ManagementExtension OPTIONAL, 
   externalIdentifier          [21] IMPLICIT SubscriptionID OPTIONAL, 
   aPNRateControl              [22] IMPLICIT APNRateControl OPTIONAL, 
   rATType                     [23] IMPLICIT INTEGER ( 0 .. 255 ) OPTIONAL, 
   servingNodePLMNIdentifier   [24] IMPLICIT OCTET STRING ( SIZE( 3 ) ) OPTIONAL, 
   servedIMEI                  [25] IMPLICIT OCTET STRING ( SIZE( 8 ) ) OPTIONAL}

CPDTSNNRecord ::= SET {
   recordType                  [0] IMPLICIT RecordType, 
   retransmission              [1] IMPLICIT NULL OPTIONAL, 
   servedIMSI                  [2] IMPLICIT OCTET STRING ( SIZE( 3 .. 8 ) ) OPTIONAL, 
   servedMSISDN                [3] IMPLICIT OCTET STRING ( SIZE( 1 .. 20 ) ) ( SIZE( 1 .. 9 ) ) OPTIONAL, 
   chargingID                  [4] IMPLICIT INTEGER ( 0 .. 4294967295 ), 
   serviceContextID            [5] IMPLICIT UTF8String OPTIONAL, 
   nodeID                      [6] IMPLICIT IA5String  ( SIZE( 1 .. 20 ) ) OPTIONAL, 
   recordOpeningTime           [7] IMPLICIT OCTET STRING ( SIZE( 9 ) ), 
   duration                    [8] IMPLICIT INTEGER, 
   accessPointNameNI           [9] IMPLICIT IA5String  ( SIZE( 1 .. 63 ) ) OPTIONAL, 
   sCEFID                      [10] IMPLICIT OCTET STRING OPTIONAL, 
   chargingCharacteristics     [11] IMPLICIT OCTET STRING ( SIZE( 2 ) ), 
   chChSelectionMode           [12] IMPLICIT ChChSelectionMode OPTIONAL, 
   servingNodeIdentity         [13] IMPLICIT OCTET STRING OPTIONAL, 
   servingPLMNRateControl      [14] IMPLICIT ServingPLMNRateControl OPTIONAL, 
   listOfNIDDsubmission        [15] IMPLICIT SEQUENCE  OF
      NIDDsubmission OPTIONAL, 
   causeForRecClosing          [16] IMPLICIT CPCauseForRecClosing, 
   diagnostics                 [17] Diagnostics OPTIONAL, 
   localSequenceNumber         [18] IMPLICIT INTEGER ( 0 .. 4294967295 ) OPTIONAL, 
   recordSequenceNumber        [19] IMPLICIT INTEGER OPTIONAL, 
   recordExtensions            [20] IMPLICIT SET  OF
      ManagementExtension OPTIONAL, 
   externalIdentifier          [21] IMPLICIT SubscriptionID OPTIONAL, 
   aPNRateControl              [22] IMPLICIT APNRateControl OPTIONAL, 
   rATType                     [23] IMPLICIT INTEGER ( 0 .. 255 ) OPTIONAL, 
   servingNodePLMNIdentifier   [24] IMPLICIT OCTET STRING ( SIZE( 3 ) ) OPTIONAL, 
   servedIMEI                  [25] IMPLICIT OCTET STRING ( SIZE( 8 ) ) OPTIONAL}

CPCauseForRecClosing ::= INTEGER {
   normalRelease                   ( 0 ), 
   abnormalRelease                 ( 1 ), 
   volumeLimit                     ( 2 ), 
   timeLimit                       ( 3 ), 
   maxNIDDsubmissions              ( 4 ), 
   servingNodeChange               ( 5 ), 
   pLMNChange                      ( 6 ), 
   servingPLMNRateControlChange    ( 7 ), 
   aPNRateControlChange            ( 8 ), 
   rATTypeChange                   ( 9 ), 
   managementIntervention          ( 10 )}

NIDDsubmission ::= SEQUENCE {
   submissionTimestamp      [0] IMPLICIT OCTET STRING ( SIZE( 9 ) ) OPTIONAL, 
   eventTimestamp           [1] IMPLICIT OCTET STRING ( SIZE( 9 ) ) OPTIONAL, 
   dataVolumeGPRSUplink     [2] IMPLICIT INTEGER OPTIONAL, 
   dataVolumeGPRSDownlink   [3] IMPLICIT INTEGER OPTIONAL, 
   submissionResultCode     [4] IMPLICIT INTEGER OPTIONAL, 
   serviceChangeCondition   [5] IMPLICIT BIT STRING {
      nIDDsubmissionResponseReceipt  (0 ), 
      nIDDsubmissionResponseSending  (1 ), 
      nIDDdeliveryToUE  (2 ), 
      nIDDdeliveryFromUEerror  (3 ), 
      nIDDsubmissionTimeout  (4 )} OPTIONAL}

ServiceChangeCondition ::= BIT STRING {
   nIDDsubmissionResponseReceipt  (0 ), 
   nIDDsubmissionResponseSending  (1 ), 
   nIDDdeliveryToUE  (2 ), 
   nIDDdeliveryFromUEerror  (3 ), 
   nIDDsubmissionTimeout  (4 )}

SubmissionResultCode ::= INTEGER


-- X.721 DMI-EXTENSION. The set is the standard form of the original
-- extensible empty table constraint ({, ...}) and does not change BER.
DMI-EXTENSION ::= CLASS {
    &id     OBJECT IDENTIFIER UNIQUE,
    &Value
}
WITH SYNTAX {
    TYPE &Value
    ID &id
}

ManagementExtensionSet DMI-EXTENSION ::= {...}

END
