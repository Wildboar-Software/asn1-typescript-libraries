-- Modified by Jonathan M. Wilbur to fix invalid syntax.
--Expanded ASN1 Module 'ExposureFunctionAPIChargingDataTypes'
--SIEMENS ASN.1 Compiler         R6.31  (Production_6.31)
--            Date: 2020-07-10 Time: 16:15:04

ExposureFunctionAPIChargingDataTypes
{itu-t(0) identified-organization(4) etsi(0) mobileDomain(0) charging(5)
exposureFunctionAPIChargingDataTypes(14) asn1Module(0) version2(1)}
DEFINITIONS
::=
BEGIN

RecordType ::= INTEGER {
   moCallRecord              ( 0 ),
   mtCallRecord              ( 1 ),
   roamingRecord             ( 2 ),
   incGatewayRecord          ( 3 ),
   outGatewayRecord          ( 4 ),
   transitCallRecord         ( 5 ),
   moSMSRecord               ( 6 ),
   mtSMSRecord               ( 7 ),
   moSMSIWRecord             ( 8 ),
   mtSMSGWRecord             ( 9 ),
   ssActionRecord            ( 10 ),
   hlrIntRecord              ( 11 ),
   locUpdateHLRRecord        ( 12 ),
   locUpdateVLRRecord        ( 13 ),
   commonEquipRecord         ( 14 ),
   moTraceRecord             ( 15 ),
   mtTraceRecord             ( 16 ),
   termCAMELRecord           ( 17 ),
   sgsnPDPRecord             ( 18 ),
   sgsnMMRecord              ( 20 ),
   sgsnSMORecord             ( 21 ),
   sgsnSMTRecord             ( 22 ),
   mtLCSRecord               ( 23 ),
   moLCSRecord               ( 24 ),
   niLCSRecord               ( 25 ),
   sgsnMTLCSRecord           ( 26 ),
   sgsnMOLCSRecord           ( 27 ),
   sgsnNILCSRecord           ( 28 ),
   mMO1SRecord               ( 30 ),
   mMO4FRqRecord             ( 31 ),
   mMO4FRsRecord             ( 32 ),
   mMO4DRecord               ( 33 ),
   mMO1DRecord               ( 34 ),
   mMO4RRecord               ( 35 ),
   mMO1RRecord               ( 36 ),
   mMOMDRecord               ( 37 ),
   mMR4FRecord               ( 38 ),
   mMR1NRqRecord             ( 39 ),
   mMR1NRsRecord             ( 40 ),
   mMR1RtRecord              ( 41 ),
   mMR1AFRecord              ( 42 ),
   mMR4DRqRecord             ( 43 ),
   mMR4DRsRecord             ( 44 ),
   mMR1RRRecord              ( 45 ),
   mMR4RRqRecord             ( 46 ),
   mMR4RRsRecord             ( 47 ),
   mMRMDRecord               ( 48 ),
   mMFRecord                 ( 49 ),
   mMBx1SRecord              ( 50 ),
   mMBx1VRecord              ( 51 ),
   mMBx1URecord              ( 52 ),
   mMBx1DRecord              ( 53 ),
   mM7SRecord                ( 54 ),
   mM7DRqRecord              ( 55 ),
   mM7DRsRecord              ( 56 ),
   mM7CRecord                ( 57 ),
   mM7RRecord                ( 58 ),
   mM7DRRqRecord             ( 59 ),
   mM7DRRsRecord             ( 60 ),
   mM7RRqRecord              ( 61 ),
   mM7RRsRecord              ( 62 ),
   sCSCFRecord               ( 63 ),
   pCSCFRecord               ( 64 ),
   iCSCFRecord               ( 65 ),
   mRFCRecord                ( 66 ),
   mGCFRecord                ( 67 ),
   bGCFRecord                ( 68 ),
   aSRecord                  ( 69 ),
   eCSCFRecord               ( 70 ),
   iBCFRecord                ( 82 ),
   tRFRecord                 ( 89 ),
   tFRecord                  ( 90 ),
   aTCFRecord                ( 91 ),
   lCSGMORecord              ( 71 ),
   lCSRGMTRecord             ( 72 ),
   lCSHGMTRecord             ( 73 ),
   lCSVGMTRecord             ( 74 ),
   lCSGNIRecord              ( 75 ),
   sgsnMBMSRecord            ( 76 ),
   ggsnMBMSRecord            ( 77 ),
   gwMBMSRecord              ( 86 ),
   sUBBMSCRecord             ( 78 ),
   cONTENTBMSCRecord         ( 79 ),
   pPFRecord                 ( 80 ),
   cPFRecord                 ( 81 ),
   sGWRecord                 ( 84 ),
   pGWRecord                 ( 85 ),
   tDFRecord                 ( 92 ),
   iPERecord                 ( 95 ),
   ePDGRecord                ( 96 ),
   tWAGRecord                ( 97 ),
   mMTelRecord               ( 83 ),
   mSCsRVCCRecord            ( 87 ),
   mMTRFRecord               ( 88 ),
   iCSRegisterRecord         ( 99 ),
   sCSMORecord               ( 93 ),
   sCSMTRecord               ( 94 ),
   pFDDRecord                ( 100 ),
   pFEDRecord                ( 101 ),
   pFDCRecord                ( 102 ),
   mECORecord                ( 103 ),
   mERERecord                ( 104 ),
   cPDTSCERecord             ( 105 ),
   cPDTSNNRecord             ( 106 ),
   sCDVTT4Record             ( 110 ),
   sCSMOT4Record             ( 111 ),
   iSMSMORecord              ( 112 ),
   iSMSMTRecord              ( 113 ),
   eASCERecord               ( 120 ),
   chargingFunctionRecord    ( 200 )}

IPBinV6AddressWithPrefixLength ::= SEQUENCE {
   iPBinV6Address           OCTET STRING ( SIZE( 16 ) ),
   pDPAddressPrefixLength   INTEGER ( 1 .. 64 ) DEFAULT 64}

IPTextRepresentedAddress ::= CHOICE {
   iPTextV4Address     [2] IMPLICIT IA5String  ( SIZE( 7 .. 15 ) ),
   iPTextV6Address     [3] IMPLICIT IA5String  ( SIZE( 15 .. 45 ) )}

IPBinV6AddressWithOrWithoutPrefixLength ::= CHOICE {
   iPBinV6Address               [1] IMPLICIT OCTET STRING ( SIZE( 16 ) ),
   iPBinV6AddressWithPrefix     [4] IMPLICIT IPBinV6AddressWithPrefixLength}

IPBinaryAddress ::= CHOICE {
   iPBinV4Address     [0] IMPLICIT OCTET STRING ( SIZE( 4 ) ),
   iPBinV6Address     IPBinV6AddressWithOrWithoutPrefixLength}

IPAddress ::= CHOICE {
   iPBinaryAddress              IPBinaryAddress,
   iPTextRepresentedAddress     IPTextRepresentedAddress}

SCSASAddress ::= SET {
   sCSAddress   [1] IPAddress,
   sCSRealm     [2] IMPLICIT OCTET STRING}

SubscriptionID ::= SET {
   subscriptionIDType   [0] IMPLICIT ENUMERATED {
      eND-USER-E164       ( 0 ),
      eND-USER-IMSI       ( 1 ),
      eND-USER-SIP-URI    ( 2 ),
      eND-USER-NAI        ( 3 ),
      eND-USER-PRIVATE    ( 4 ) },
   subscriptionIDData   [1] IMPLICIT UTF8String}

ManagementExtension ::= SEQUENCE {
   identifier     DMI-EXTENSION.&id ({ManagementExtensionSet}) ,
   significance   [1] IMPLICIT BOOLEAN DEFAULT FALSE,
   information    [2] DMI-EXTENSION.&Value ({ManagementExtensionSet}{@.identifier}) }

ExposureFunctionAPIRecordType ::= CHOICE {
   eASCERecord     [120] IMPLICIT EASCERecord}

EASCERecord ::= SET {
   recordType                  [0] IMPLICIT RecordType,
   retransmission              [1] IMPLICIT NULL OPTIONAL,
   serviceContextID            [2] IMPLICIT UTF8String OPTIONAL,
   nodeId                      [3] IMPLICIT IA5String  ( SIZE( 1 .. 20 ) ) OPTIONAL,
   sCEFID                      [4] IMPLICIT OCTET STRING OPTIONAL,
   sCEFAddress                 [5] IPAddress OPTIONAL,
   aPIIdentifier               [6] IMPLICIT OCTET STRING OPTIONAL,
   tLTRI                       [7] IMPLICIT INTEGER OPTIONAL,
   sCSASAddress                [9] IMPLICIT SCSASAddress OPTIONAL,
   eventTimestamp              [10] IMPLICIT OCTET STRING ( SIZE( 9 ) ) OPTIONAL,
   aPIInvocationTimestamp      [11] IMPLICIT OCTET STRING ( SIZE( 9 ) ) OPTIONAL,
   aPIDirection                [12] IMPLICIT APIDirection OPTIONAL,
   aPINetworkServiceNode       [13] IMPLICIT APINetworkServiceNode OPTIONAL,
   aPIContent                  [14] IMPLICIT UTF8String OPTIONAL,
   aPISize                     [15] IMPLICIT INTEGER OPTIONAL,
   aPIresultCode               [16] IMPLICIT INTEGER OPTIONAL,
   externalIdentifier          [17] IMPLICIT SubscriptionID OPTIONAL,
   localRecordSequenceNumber   [18] IMPLICIT INTEGER ( 0 .. 4294967295 ) OPTIONAL,
   recordExtensions            [19] IMPLICIT SET  OF
      ManagementExtension OPTIONAL,
   startTime                   [20] IMPLICIT OCTET STRING ( SIZE( 9 ) ) OPTIONAL,
   stopTime                    [21] IMPLICIT OCTET STRING ( SIZE( 9 ) ) OPTIONAL}

APIDirection ::= ENUMERATED {
   invocation      ( 0 ),
   notification    ( 1 ) }

APINetworkServiceNode ::= ENUMERATED {
   mME         ( 0 ),
   sGSN        ( 1 ),
   hSS         ( 2 ),
   pCRF        ( 3 ),
   pFDF        ( 4 ),
   bMSC        ( 5 ),
   cCSCF       ( 6 ),
   rCAF        ( 7 ) }


-- X.721 DMI-EXTENSION. The set is the standard form of the original
-- extensible empty table constraint ({, ...}) and does not change BER.
DMI-EXTENSION ::= CLASS {
    &id     OBJECT IDENTIFIER UNIQUE,
    &Value
}
WITH SYNTAX {
    TYPE &Value
    ID &id
}

ManagementExtensionSet DMI-EXTENSION ::= {...}

END
