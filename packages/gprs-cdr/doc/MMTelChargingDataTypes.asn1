-- Modified by Jonathan M. Wilbur to fix invalid syntax.
--     Expanded ASN1 Module 'MMTelChargingDataTypes'
--SIEMENS ASN.1 Compiler         R6.31  (Production_6.31)
--            Date: 2020-07-10 Time: 16:16:10

MMTelChargingDataTypes
{itu-t(0) identified-organization(4) etsi(0) mobileDomain(0) charging(5)
mMTelChargingDataTypes(9) asn1Module(0) version2(1)}
DEFINITIONS
::=
BEGIN

RecordType ::= INTEGER {
   moCallRecord              ( 0 ),
   mtCallRecord              ( 1 ),
   roamingRecord             ( 2 ),
   incGatewayRecord          ( 3 ),
   outGatewayRecord          ( 4 ),
   transitCallRecord         ( 5 ),
   moSMSRecord               ( 6 ),
   mtSMSRecord               ( 7 ),
   moSMSIWRecord             ( 8 ),
   mtSMSGWRecord             ( 9 ),
   ssActionRecord            ( 10 ),
   hlrIntRecord              ( 11 ),
   locUpdateHLRRecord        ( 12 ),
   locUpdateVLRRecord        ( 13 ),
   commonEquipRecord         ( 14 ),
   moTraceRecord             ( 15 ),
   mtTraceRecord             ( 16 ),
   termCAMELRecord           ( 17 ),
   sgsnPDPRecord             ( 18 ),
   sgsnMMRecord              ( 20 ),
   sgsnSMORecord             ( 21 ),
   sgsnSMTRecord             ( 22 ),
   mtLCSRecord               ( 23 ),
   moLCSRecord               ( 24 ),
   niLCSRecord               ( 25 ),
   sgsnMTLCSRecord           ( 26 ),
   sgsnMOLCSRecord           ( 27 ),
   sgsnNILCSRecord           ( 28 ),
   mMO1SRecord               ( 30 ),
   mMO4FRqRecord             ( 31 ),
   mMO4FRsRecord             ( 32 ),
   mMO4DRecord               ( 33 ),
   mMO1DRecord               ( 34 ),
   mMO4RRecord               ( 35 ),
   mMO1RRecord               ( 36 ),
   mMOMDRecord               ( 37 ),
   mMR4FRecord               ( 38 ),
   mMR1NRqRecord             ( 39 ),
   mMR1NRsRecord             ( 40 ),
   mMR1RtRecord              ( 41 ),
   mMR1AFRecord              ( 42 ),
   mMR4DRqRecord             ( 43 ),
   mMR4DRsRecord             ( 44 ),
   mMR1RRRecord              ( 45 ),
   mMR4RRqRecord             ( 46 ),
   mMR4RRsRecord             ( 47 ),
   mMRMDRecord               ( 48 ),
   mMFRecord                 ( 49 ),
   mMBx1SRecord              ( 50 ),
   mMBx1VRecord              ( 51 ),
   mMBx1URecord              ( 52 ),
   mMBx1DRecord              ( 53 ),
   mM7SRecord                ( 54 ),
   mM7DRqRecord              ( 55 ),
   mM7DRsRecord              ( 56 ),
   mM7CRecord                ( 57 ),
   mM7RRecord                ( 58 ),
   mM7DRRqRecord             ( 59 ),
   mM7DRRsRecord             ( 60 ),
   mM7RRqRecord              ( 61 ),
   mM7RRsRecord              ( 62 ),
   sCSCFRecord               ( 63 ),
   pCSCFRecord               ( 64 ),
   iCSCFRecord               ( 65 ),
   mRFCRecord                ( 66 ),
   mGCFRecord                ( 67 ),
   bGCFRecord                ( 68 ),
   aSRecord                  ( 69 ),
   eCSCFRecord               ( 70 ),
   iBCFRecord                ( 82 ),
   tRFRecord                 ( 89 ),
   tFRecord                  ( 90 ),
   aTCFRecord                ( 91 ),
   lCSGMORecord              ( 71 ),
   lCSRGMTRecord             ( 72 ),
   lCSHGMTRecord             ( 73 ),
   lCSVGMTRecord             ( 74 ),
   lCSGNIRecord              ( 75 ),
   sgsnMBMSRecord            ( 76 ),
   ggsnMBMSRecord            ( 77 ),
   gwMBMSRecord              ( 86 ),
   sUBBMSCRecord             ( 78 ),
   cONTENTBMSCRecord         ( 79 ),
   pPFRecord                 ( 80 ),
   cPFRecord                 ( 81 ),
   sGWRecord                 ( 84 ),
   pGWRecord                 ( 85 ),
   tDFRecord                 ( 92 ),
   iPERecord                 ( 95 ),
   ePDGRecord                ( 96 ),
   tWAGRecord                ( 97 ),
   mMTelRecord               ( 83 ),
   mSCsRVCCRecord            ( 87 ),
   mMTRFRecord               ( 88 ),
   iCSRegisterRecord         ( 99 ),
   sCSMORecord               ( 93 ),
   sCSMTRecord               ( 94 ),
   pFDDRecord                ( 100 ),
   pFEDRecord                ( 101 ),
   pFDCRecord                ( 102 ),
   mECORecord                ( 103 ),
   mERERecord                ( 104 ),
   cPDTSCERecord             ( 105 ),
   cPDTSNNRecord             ( 106 ),
   sCDVTT4Record             ( 110 ),
   sCSMOT4Record             ( 111 ),
   iSMSMORecord              ( 112 ),
   iSMSMTRecord              ( 113 ),
   eASCERecord               ( 120 ),
   chargingFunctionRecord    ( 200 )}

SDP-Type ::= ENUMERATED {
   sDP-offer     ( 0 ),
   sDP-answer    ( 1 ) }

IPBinV6AddressWithPrefixLength ::= SEQUENCE {
   iPBinV6Address           OCTET STRING ( SIZE( 16 ) ),
   pDPAddressPrefixLength   INTEGER ( 1 .. 64 ) DEFAULT 64}

InterOperatorIdentifiers ::= SEQUENCE {
   originatingIOI   [0] IMPLICIT GraphicString OPTIONAL,
   terminatingIOI   [1] IMPLICIT GraphicString OPTIONAL}

AoCCostInformation ::= SEQUENCE {
   accumulatedCost   [0] IMPLICIT REAL,
   incrementalCost   [1] IMPLICIT REAL,
   currencyCode      [2] IMPLICIT INTEGER}

AccessCorrelationID ::= CHOICE {
   gPRS-Charging-Id                    [2] IMPLICIT INTEGER ( 0 .. 4294967295 ),
   accessNetworkChargingIdentifier     [4] IMPLICIT GraphicString}

IPTextRepresentedAddress ::= CHOICE {
   iPTextV4Address     [2] IMPLICIT IA5String  ( SIZE( 7 .. 15 ) ),
   iPTextV6Address     [3] IMPLICIT IA5String  ( SIZE( 15 .. 45 ) )}

IPBinV6AddressWithOrWithoutPrefixLength ::= CHOICE {
   iPBinV6Address               [1] IMPLICIT OCTET STRING ( SIZE( 16 ) ),
   iPBinV6AddressWithPrefix     [4] IMPLICIT IPBinV6AddressWithPrefixLength}

IPBinaryAddress ::= CHOICE {
   iPBinV4Address     [0] IMPLICIT OCTET STRING ( SIZE( 4 ) ),
   iPBinV6Address     IPBinV6AddressWithOrWithoutPrefixLength}

IPAddress ::= CHOICE {
   iPBinaryAddress              IPBinaryAddress,
   iPTextRepresentedAddress     IPTextRepresentedAddress}

NodeAddress ::= CHOICE {
   iPAddress      [0] IPAddress,
   domainName     [1] IMPLICIT GraphicString}

RateElements ::= SEQUENCE {
   unitType             [0] IMPLICIT INTEGER,
   unitValue            [1] IMPLICIT REAL,
   unitCost             [2] IMPLICIT REAL,
   unitQuotaThreshold   [3] IMPLICIT REAL}

TariffInformation ::= SEQUENCE {
   currencyCode   [0] IMPLICIT INTEGER,
   scaleFactor    [1] IMPLICIT REAL,
   rateElements   [2] IMPLICIT SEQUENCE  OF
      RateElements OPTIONAL}

RealTimeTariffInformation ::= CHOICE {
   tariffInformation     [0] IMPLICIT TariffInformation,
   tariffXml             [1] IMPLICIT UTF8String}

AoCInformation ::= SET {
   tariffInformation    [0] IMPLICIT TariffInformation OPTIONAL,
   aoCCostInformation   [1] IMPLICIT AoCCostInformation OPTIONAL}

InvolvedParty ::= CHOICE {
   sIP-URI       [0] IMPLICIT GraphicString,
   tEL-URI       [1] IMPLICIT GraphicString,
   uRN           [2] IMPLICIT GraphicString,
   iSDN-E164     [3] IMPLICIT GraphicString}

Incomplete-CDR-Indication ::= SET {
   aCRStartLost     [0] IMPLICIT BOOLEAN,
   aCRInterimLost   [1] IMPLICIT ENUMERATED {
      no          ( 0 ),
      yes         ( 1 ),
      unknown     ( 2 ) },
   aCRStopLost      [2] IMPLICIT BOOLEAN}

SubscriberEquipmentNumber ::= SET {
   subscriberEquipmentNumberType   [0] IMPLICIT ENUMERATED {
      iMEISV           ( 0 ),
      mAC              ( 1 ),
      eUI64            ( 2 ),
      modifiedEUI64    ( 3 ) },
   subscriberEquipmentNumberData   [1] IMPLICIT OCTET STRING}

List-Of-Message-Bodies ::= SEQUENCE {
   content-Type          [0] IMPLICIT GraphicString,
   content-Disposition   [1] IMPLICIT GraphicString OPTIONAL,
   content-Length        [2] IMPLICIT INTEGER,
   originator            [3] InvolvedParty OPTIONAL}

SubscriptionID ::= SET {
   subscriptionIDType   [0] IMPLICIT ENUMERATED {
      eND-USER-E164       ( 0 ),
      eND-USER-IMSI       ( 1 ),
      eND-USER-SIP-URI    ( 2 ),
      eND-USER-NAI        ( 3 ),
      eND-USER-PRIVATE    ( 4 ) },
   subscriptionIDData   [1] IMPLICIT UTF8String}

ManagementExtension ::= SEQUENCE {
   identifier     DMI-EXTENSION.&id ({ManagementExtensionSet}) ,
   significance   [1] IMPLICIT BOOLEAN DEFAULT FALSE,
   information    [2] DMI-EXTENSION.&Value ({ManagementExtensionSet}{@.identifier}) }

SDP-Media-Components ::= SEQUENCE {
   sDP-Media-Name                 [0] IMPLICIT GraphicString OPTIONAL,
   sDP-Media-Descriptions         [1] IMPLICIT SEQUENCE  OF
      GraphicString OPTIONAL,
   accessCorrelationID            AccessCorrelationID OPTIONAL,
   localGWInsertedIndication      [5] IMPLICIT BOOLEAN OPTIONAL,
   iPRealmDefaultIndication       [6] IMPLICIT BOOLEAN OPTIONAL,
   transcoderInsertedIndication   [7] IMPLICIT BOOLEAN OPTIONAL}

List-Of-Early-SDP-Media-Components ::= SEQUENCE {
   sDP-Offer-Timestamp       [0] IMPLICIT OCTET STRING ( SIZE( 9 ) ) OPTIONAL,
   sDP-Answer-Timestamp      [1] IMPLICIT OCTET STRING ( SIZE( 9 ) ) OPTIONAL,
   sDP-Media-Components      [2] IMPLICIT SEQUENCE  OF
      SDP-Media-Components OPTIONAL,
   mediaInitiatorFlag        [3] IMPLICIT NULL OPTIONAL,
   sDP-Session-Description   [4] IMPLICIT SEQUENCE  OF
      GraphicString OPTIONAL,
   sDP-Type                  [5] IMPLICIT SDP-Type OPTIONAL}

List-Of-SDP-Media-Components ::= SEQUENCE {
   sIP-Request-Timestamp             [0] IMPLICIT OCTET STRING ( SIZE( 9 ) ) OPTIONAL,
   sIP-Response-Timestamp            [1] IMPLICIT OCTET STRING ( SIZE( 9 ) ) OPTIONAL,
   sDP-Media-Components              [2] IMPLICIT SEQUENCE  OF
      SDP-Media-Components OPTIONAL,
   mediaInitiatorFlag                [3] IMPLICIT NULL OPTIONAL,
   sDP-Session-Description           [4] IMPLICIT SEQUENCE  OF
      GraphicString OPTIONAL,
   mediaInitiatorParty               [5] InvolvedParty OPTIONAL,
   sIP-Request-Timestamp-Fraction    [6] IMPLICIT INTEGER ( 0 .. 999 ) OPTIONAL,
   sIP-Response-Timestamp-Fraction   [7] IMPLICIT INTEGER ( 0 .. 999 ) OPTIONAL,
   sDP-Type                          [8] IMPLICIT SDP-Type OPTIONAL}

MMTelServiceRecord ::= CHOICE {
   mMTelRecord     [83] IMPLICIT MMTelRecord}

MMTelRecord ::= SET {
   recordType                              [0] IMPLICIT RecordType,
   retransmission                          [1] IMPLICIT NULL OPTIONAL,
   sIP-Method                              [2] IMPLICIT GraphicString OPTIONAL,
   role-of-Node                            [3] IMPLICIT ENUMERATED {
      originating    ( 0 ),
      terminating    ( 1 ) } OPTIONAL,
   nodeAddress                             [4] NodeAddress OPTIONAL,
   session-Id                              [5] IMPLICIT GraphicString OPTIONAL,
   list-Of-Calling-Party-Address           [6] IMPLICIT SEQUENCE  OF
      InvolvedParty OPTIONAL,
   called-Party-Address                    [7] InvolvedParty OPTIONAL,
   serviceRequestTimeStamp                 [9] IMPLICIT OCTET STRING ( SIZE( 9 ) ) OPTIONAL,
   serviceDeliveryStartTimeStamp           [10] IMPLICIT OCTET STRING ( SIZE( 9 ) ) OPTIONAL,
   serviceDeliveryEndTimeStamp             [11] IMPLICIT OCTET STRING ( SIZE( 9 ) ) OPTIONAL,
   recordOpeningTime                       [12] IMPLICIT OCTET STRING ( SIZE( 9 ) ) OPTIONAL,
   recordClosureTime                       [13] IMPLICIT OCTET STRING ( SIZE( 9 ) ) OPTIONAL,
   interOperatorIdentifiers                [14] IMPLICIT SEQUENCE  OF
      InterOperatorIdentifiers OPTIONAL,
   localRecordSequenceNumber               [15] IMPLICIT INTEGER ( 0 .. 4294967295 ) OPTIONAL,
   recordSequenceNumber                    [16] IMPLICIT INTEGER OPTIONAL,
   causeForRecordClosing                   [17] IMPLICIT ENUMERATED {
      serviceDeliveryEndSuccessfully    ( 0 ),
      unSuccessfulServiceDelivery       ( 1 ),
      timeLimit                         ( 3 ),
      serviceChange                     ( 4 ),
      managementIntervention            ( 5 ) } OPTIONAL,
   incomplete-CDR-Indication               [18] IMPLICIT Incomplete-CDR-Indication OPTIONAL,
   iMS-Charging-Identifier                 [19] IMPLICIT OCTET STRING OPTIONAL,
   list-Of-SDP-Media-Components            [21] IMPLICIT SEQUENCE  OF
      List-Of-SDP-Media-Components OPTIONAL,
   gGSNaddress                             [22] NodeAddress OPTIONAL,
   serviceReasonReturnCode                 [23] IMPLICIT UTF8String OPTIONAL,
   list-Of-Message-Bodies                  [24] IMPLICIT SEQUENCE  OF
      List-Of-Message-Bodies OPTIONAL,
   recordExtensions                        [25] IMPLICIT SET  OF
      ManagementExtension OPTIONAL,
   expiresInformation                      [26] IMPLICIT INTEGER OPTIONAL,
   event                                   [28] IMPLICIT UTF8String OPTIONAL,
   accessNetworkInformation                [29] IMPLICIT OCTET STRING OPTIONAL,
   serviceContextID                        [30] IMPLICIT UTF8String OPTIONAL,
   list-of-subscription-ID                 [31] IMPLICIT SEQUENCE  OF
      SubscriptionID OPTIONAL,
   list-Of-Early-SDP-Media-Components      [32] IMPLICIT SEQUENCE  OF
      List-Of-Early-SDP-Media-Components OPTIONAL,
   iMSCommunicationServiceIdentifier       [33] IMPLICIT OCTET STRING OPTIONAL,
   numberPortabilityRouting                [34] IMPLICIT GraphicString OPTIONAL,
   carrierSelectRouting                    [35] IMPLICIT GraphicString OPTIONAL,
   sessionPriority                         [36] IMPLICIT ENUMERATED {
      pRIORITY-0    ( 0 ),
      pRIORITY-1    ( 1 ),
      pRIORITY-2    ( 2 ),
      pRIORITY-3    ( 3 ),
      pRIORITY-4    ( 4 ) } OPTIONAL,
   serviceRequestTimeStampFraction         [37] IMPLICIT INTEGER ( 0 .. 999 ) OPTIONAL,
   serviceDeliveryStartTimeStampFraction   [38] IMPLICIT INTEGER ( 0 .. 999 ) OPTIONAL,
   serviceDeliveryEndTimeStampFraction     [39] IMPLICIT INTEGER ( 0 .. 999 ) OPTIONAL,
   online-charging-flag                    [43] IMPLICIT NULL OPTIONAL,
   realTimeTariffInformation               [44] IMPLICIT SEQUENCE  OF
      RealTimeTariffInformation OPTIONAL,
   transit-IOI-Lists                       [53] IMPLICIT SEQUENCE  OF
      GraphicString OPTIONAL,
   iMSVisitedNetworkIdentifier             [54] IMPLICIT OCTET STRING OPTIONAL,
   listOfReasonHeader                      [55] IMPLICIT SEQUENCE  OF
      GraphicString OPTIONAL,
   additionalAccessNetworkInformation      [56] IMPLICIT OCTET STRING OPTIONAL,
   instanceId                              [57] IMPLICIT OCTET STRING OPTIONAL,
   subscriberEquipmentNumber               [58] IMPLICIT SubscriberEquipmentNumber OPTIONAL,
   cellularNetworkInformation              [64] IMPLICIT OCTET STRING OPTIONAL,
   requested-Party-Address                 [101] InvolvedParty OPTIONAL,
   list-Of-Called-Asserted-Identity        [102] IMPLICIT SEQUENCE  OF
      InvolvedParty OPTIONAL,
   outgoingSessionId                       [104] IMPLICIT GraphicString OPTIONAL,
   mMTelInformation                        [110] IMPLICIT MMTelInformation OPTIONAL,
   threeGPPPSDataOffStatus                 [112] IMPLICIT ENUMERATED {
      active      ( 0 ),
      inactive    ( 1 ) } OPTIONAL,
   fEIdentifierList                        [113] IMPLICIT SEQUENCE  OF
      GraphicString OPTIONAL}

MMTelInformation ::= SET {
   listOfSupplServices   [0] IMPLICIT SEQUENCE  OF
      SupplService OPTIONAL}

ParticipantActionType ::= ENUMERATED {
   cREATE-CONF          ( 0 ),
   jOIN-CONF            ( 1 ),
   iNVITED-INTO-CONF    ( 2 ),
   qUIT-CONF            ( 3 ) }

SupplService ::= SET {
   serviceType                [0] IMPLICIT ServiceType,
   serviceMode                [1] IMPLICIT ServiceMode OPTIONAL,
   numberOfDiversions         [2] IMPLICIT INTEGER OPTIONAL,
   associated-Party-Address   [3] InvolvedParty OPTIONAL,
   serviceId                  [4] IMPLICIT GraphicString OPTIONAL,
   changeTime                 [5] IMPLICIT OCTET STRING ( SIZE( 9 ) ),
   numberOfParticipants       [6] IMPLICIT INTEGER OPTIONAL,
   participantActionType      [7] IMPLICIT ParticipantActionType OPTIONAL,
   cUGInformation             [8] IMPLICIT OCTET STRING OPTIONAL,
   aoCInformation             [9] IMPLICIT SEQUENCE  OF
      AoCInformation OPTIONAL}

ServiceType ::= INTEGER {
   oIPresentation      ( 0 ),
   oIRestriction       ( 1 ),
   tIPresentation      ( 2 ),
   tIRestriction       ( 3 ),
   hOLD                ( 4 ),
   cBarring            ( 5 ),
   cDIVersion          ( 6 ),
   cWaiting            ( 8 ),
   mWaitingIndic       ( 9 ),
   cONF                ( 10 ),
   fLexibleAlerting    ( 11 ),
   cCBS                ( 12 ),
   cCNR                ( 13 ),
   mCID                ( 14 ),
   cAT                 ( 15 ),
   cUG                 ( 16 ),
   pNM                 ( 17 ),
   cRS                 ( 18 ),
   aoC                 ( 19 ),
   eCT                 ( 20 )}

ServiceMode ::= INTEGER {
   cFunCond           ( 0 ),
   cFbusy             ( 1 ),
   cFnoReply          ( 2 ),
   cFnotLogged        ( 3 ),
   deflection         ( 4 ),
   notReach           ( 5 ),
   iCBarring          ( 6 ),
   oCBarring          ( 7 ),
   aCRejection        ( 8 ),
   eCTBlind           ( 9 ),
   eCTConsultative    ( 10 ),
   threePTY           ( 11 ),
   aoC-S              ( 12 ),
   aoC-D              ( 13 ),
   aoC-E              ( 14 )}


-- X.721 DMI-EXTENSION. The set is the standard form of the original
-- extensible empty table constraint ({, ...}) and does not change BER.
DMI-EXTENSION ::= CLASS {
    &id     OBJECT IDENTIFIER UNIQUE,
    &Value
}
WITH SYNTAX {
    TYPE &Value
    ID &id
}

ManagementExtensionSet DMI-EXTENSION ::= {...}

END
