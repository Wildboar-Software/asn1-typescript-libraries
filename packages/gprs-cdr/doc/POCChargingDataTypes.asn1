-- Modified by Jonathan M. Wilbur to fix invalid syntax.
--      Expanded ASN1 Module 'POCChargingDataTypes'
--SIEMENS ASN.1 Compiler         R6.31  (Production_6.31)
--            Date: 2020-07-10 Time: 16:16:42

POCChargingDataTypes
{itu-t(0) identified-organization(4) etsi(0) mobileDomain(0) charging(5)
pocChargingDataTypes(7) asn1Module(0) version2(1)}
DEFINITIONS
::=
BEGIN

RecordType ::= INTEGER {
   moCallRecord              ( 0 ),
   mtCallRecord              ( 1 ),
   roamingRecord             ( 2 ),
   incGatewayRecord          ( 3 ),
   outGatewayRecord          ( 4 ),
   transitCallRecord         ( 5 ),
   moSMSRecord               ( 6 ),
   mtSMSRecord               ( 7 ),
   moSMSIWRecord             ( 8 ),
   mtSMSGWRecord             ( 9 ),
   ssActionRecord            ( 10 ),
   hlrIntRecord              ( 11 ),
   locUpdateHLRRecord        ( 12 ),
   locUpdateVLRRecord        ( 13 ),
   commonEquipRecord         ( 14 ),
   moTraceRecord             ( 15 ),
   mtTraceRecord             ( 16 ),
   termCAMELRecord           ( 17 ),
   sgsnPDPRecord             ( 18 ),
   sgsnMMRecord              ( 20 ),
   sgsnSMORecord             ( 21 ),
   sgsnSMTRecord             ( 22 ),
   mtLCSRecord               ( 23 ),
   moLCSRecord               ( 24 ),
   niLCSRecord               ( 25 ),
   sgsnMTLCSRecord           ( 26 ),
   sgsnMOLCSRecord           ( 27 ),
   sgsnNILCSRecord           ( 28 ),
   mMO1SRecord               ( 30 ),
   mMO4FRqRecord             ( 31 ),
   mMO4FRsRecord             ( 32 ),
   mMO4DRecord               ( 33 ),
   mMO1DRecord               ( 34 ),
   mMO4RRecord               ( 35 ),
   mMO1RRecord               ( 36 ),
   mMOMDRecord               ( 37 ),
   mMR4FRecord               ( 38 ),
   mMR1NRqRecord             ( 39 ),
   mMR1NRsRecord             ( 40 ),
   mMR1RtRecord              ( 41 ),
   mMR1AFRecord              ( 42 ),
   mMR4DRqRecord             ( 43 ),
   mMR4DRsRecord             ( 44 ),
   mMR1RRRecord              ( 45 ),
   mMR4RRqRecord             ( 46 ),
   mMR4RRsRecord             ( 47 ),
   mMRMDRecord               ( 48 ),
   mMFRecord                 ( 49 ),
   mMBx1SRecord              ( 50 ),
   mMBx1VRecord              ( 51 ),
   mMBx1URecord              ( 52 ),
   mMBx1DRecord              ( 53 ),
   mM7SRecord                ( 54 ),
   mM7DRqRecord              ( 55 ),
   mM7DRsRecord              ( 56 ),
   mM7CRecord                ( 57 ),
   mM7RRecord                ( 58 ),
   mM7DRRqRecord             ( 59 ),
   mM7DRRsRecord             ( 60 ),
   mM7RRqRecord              ( 61 ),
   mM7RRsRecord              ( 62 ),
   sCSCFRecord               ( 63 ),
   pCSCFRecord               ( 64 ),
   iCSCFRecord               ( 65 ),
   mRFCRecord                ( 66 ),
   mGCFRecord                ( 67 ),
   bGCFRecord                ( 68 ),
   aSRecord                  ( 69 ),
   eCSCFRecord               ( 70 ),
   iBCFRecord                ( 82 ),
   tRFRecord                 ( 89 ),
   tFRecord                  ( 90 ),
   aTCFRecord                ( 91 ),
   lCSGMORecord              ( 71 ),
   lCSRGMTRecord             ( 72 ),
   lCSHGMTRecord             ( 73 ),
   lCSVGMTRecord             ( 74 ),
   lCSGNIRecord              ( 75 ),
   sgsnMBMSRecord            ( 76 ),
   ggsnMBMSRecord            ( 77 ),
   gwMBMSRecord              ( 86 ),
   sUBBMSCRecord             ( 78 ),
   cONTENTBMSCRecord         ( 79 ),
   pPFRecord                 ( 80 ),
   cPFRecord                 ( 81 ),
   sGWRecord                 ( 84 ),
   pGWRecord                 ( 85 ),
   tDFRecord                 ( 92 ),
   iPERecord                 ( 95 ),
   ePDGRecord                ( 96 ),
   tWAGRecord                ( 97 ),
   mMTelRecord               ( 83 ),
   mSCsRVCCRecord            ( 87 ),
   mMTRFRecord               ( 88 ),
   iCSRegisterRecord         ( 99 ),
   sCSMORecord               ( 93 ),
   sCSMTRecord               ( 94 ),
   pFDDRecord                ( 100 ),
   pFEDRecord                ( 101 ),
   pFDCRecord                ( 102 ),
   mECORecord                ( 103 ),
   mERERecord                ( 104 ),
   cPDTSCERecord             ( 105 ),
   cPDTSNNRecord             ( 106 ),
   sCDVTT4Record             ( 110 ),
   sCSMOT4Record             ( 111 ),
   iSMSMORecord              ( 112 ),
   iSMSMTRecord              ( 113 ),
   eASCERecord               ( 120 ),
   chargingFunctionRecord    ( 200 )}

IPBinV6AddressWithPrefixLength ::= SEQUENCE {
   iPBinV6Address           OCTET STRING ( SIZE( 16 ) ),
   pDPAddressPrefixLength   INTEGER ( 1 .. 64 ) DEFAULT 64}

InterOperatorIdentifiers ::= SEQUENCE {
   originatingIOI   [0] IMPLICIT GraphicString OPTIONAL,
   terminatingIOI   [1] IMPLICIT GraphicString OPTIONAL}

AccessCorrelationID ::= CHOICE {
   gPRS-Charging-Id                    [2] IMPLICIT INTEGER ( 0 .. 4294967295 ),
   accessNetworkChargingIdentifier     [4] IMPLICIT GraphicString}

IPTextRepresentedAddress ::= CHOICE {
   iPTextV4Address     [2] IMPLICIT IA5String  ( SIZE( 7 .. 15 ) ),
   iPTextV6Address     [3] IMPLICIT IA5String  ( SIZE( 15 .. 45 ) )}

IPBinV6AddressWithOrWithoutPrefixLength ::= CHOICE {
   iPBinV6Address               [1] IMPLICIT OCTET STRING ( SIZE( 16 ) ),
   iPBinV6AddressWithPrefix     [4] IMPLICIT IPBinV6AddressWithPrefixLength}

IPBinaryAddress ::= CHOICE {
   iPBinV4Address     [0] IMPLICIT OCTET STRING ( SIZE( 4 ) ),
   iPBinV6Address     IPBinV6AddressWithOrWithoutPrefixLength}

IPAddress ::= CHOICE {
   iPBinaryAddress              IPBinaryAddress,
   iPTextRepresentedAddress     IPTextRepresentedAddress}

NodeAddress ::= CHOICE {
   iPAddress      [0] IPAddress,
   domainName     [1] IMPLICIT GraphicString}

InvolvedParty ::= CHOICE {
   sIP-URI       [0] IMPLICIT GraphicString,
   tEL-URI       [1] IMPLICIT GraphicString,
   uRN           [2] IMPLICIT GraphicString,
   iSDN-E164     [3] IMPLICIT GraphicString}

Incomplete-CDR-Indication ::= SET {
   aCRStartLost     [0] IMPLICIT BOOLEAN,
   aCRInterimLost   [1] IMPLICIT ENUMERATED {
      no          ( 0 ),
      yes         ( 1 ),
      unknown     ( 2 ) },
   aCRStopLost      [2] IMPLICIT BOOLEAN}

List-Of-Message-Bodies ::= SEQUENCE {
   content-Type          [0] IMPLICIT GraphicString,
   content-Disposition   [1] IMPLICIT GraphicString OPTIONAL,
   content-Length        [2] IMPLICIT INTEGER,
   originator            [3] InvolvedParty OPTIONAL}

ManagementExtension ::= SEQUENCE {
   identifier     DMI-EXTENSION.&id ({ManagementExtensionSet}) ,
   significance   [1] IMPLICIT BOOLEAN DEFAULT FALSE,
   information    [2] DMI-EXTENSION.&Value ({ManagementExtensionSet}{@.identifier}) }

SDP-Media-Components ::= SEQUENCE {
   sDP-Media-Name                 [0] IMPLICIT GraphicString OPTIONAL,
   sDP-Media-Descriptions         [1] IMPLICIT SEQUENCE  OF
      GraphicString OPTIONAL,
   accessCorrelationID            AccessCorrelationID OPTIONAL,
   localGWInsertedIndication      [5] IMPLICIT BOOLEAN OPTIONAL,
   iPRealmDefaultIndication       [6] IMPLICIT BOOLEAN OPTIONAL,
   transcoderInsertedIndication   [7] IMPLICIT BOOLEAN OPTIONAL}

List-Of-SDP-Media-Components ::= SEQUENCE {
   sIP-Request-Timestamp             [0] IMPLICIT OCTET STRING ( SIZE( 9 ) ) OPTIONAL,
   sIP-Response-Timestamp            [1] IMPLICIT OCTET STRING ( SIZE( 9 ) ) OPTIONAL,
   sDP-Media-Components              [2] IMPLICIT SEQUENCE  OF
      SDP-Media-Components OPTIONAL,
   mediaInitiatorFlag                [3] IMPLICIT NULL OPTIONAL,
   sDP-Session-Description           [4] IMPLICIT SEQUENCE  OF
      GraphicString OPTIONAL,
   mediaInitiatorParty               [5] InvolvedParty OPTIONAL,
   sIP-Request-Timestamp-Fraction    [6] IMPLICIT INTEGER ( 0 .. 999 ) OPTIONAL,
   sIP-Response-Timestamp-Fraction   [7] IMPLICIT INTEGER ( 0 .. 999 ) OPTIONAL,
   sDP-Type                          [8] IMPLICIT ENUMERATED {
      sDP-offer     ( 0 ),
      sDP-answer    ( 1 ) } OPTIONAL}

POCRecord  ::= CHOICE {
   pPFRecord     [80] IMPLICIT PPFRecord,
   cPFRecord     [81] IMPLICIT CPFRecord}

PPFRecord  ::= SET {
   recordType                      [0] IMPLICIT RecordType,
   retransmission                  [1] IMPLICIT NULL OPTIONAL,
   sIP-Method                      [2] IMPLICIT GraphicString OPTIONAL,
   nodeAddress                     [3] NodeAddress OPTIONAL,
   session-Id                      [4] IMPLICIT GraphicString OPTIONAL,
   calling-Party-Address           [5] InvolvedParty OPTIONAL,
   called-Party-Address            [6] InvolvedParty OPTIONAL,
   servedParty                     [7] IMPLICIT GraphicString OPTIONAL,
   serviceRequestTimeStamp         [8] IMPLICIT OCTET STRING ( SIZE( 9 ) ) OPTIONAL,
   serviceDeliveryStartTimeStamp   [9] IMPLICIT OCTET STRING ( SIZE( 9 ) ) OPTIONAL,
   serviceDeliveryEndTimeStamp     [10] IMPLICIT OCTET STRING ( SIZE( 9 ) ) OPTIONAL,
   recordOpeningTime               [11] IMPLICIT OCTET STRING ( SIZE( 9 ) ) OPTIONAL,
   recordClosureTime               [12] IMPLICIT OCTET STRING ( SIZE( 9 ) ) OPTIONAL,
   interOperatorIdentifiers        [13] IMPLICIT InterOperatorIdentifiers OPTIONAL,
   localRecordSequenceNumber       [14] IMPLICIT INTEGER ( 0 .. 4294967295 ) OPTIONAL,
   recordSequenceNumber            [15] IMPLICIT INTEGER OPTIONAL,
   causeForRecordClosing           [16] IMPLICIT CauseForRecordClosing OPTIONAL,
   incomplete-CDR-Indication       [17] IMPLICIT Incomplete-CDR-Indication OPTIONAL,
   iMS-Charging-Identifier         [18] IMPLICIT OCTET STRING OPTIONAL,
   list-Of-SDP-Media-Components    [19] IMPLICIT SEQUENCE  OF
      List-Of-SDP-Media-Components OPTIONAL,
   gGSNaddress                     [20] NodeAddress OPTIONAL,
   serviceReasonReturnCode         [21] IMPLICIT UTF8String OPTIONAL,
   list-Of-Message-Bodies          [22] IMPLICIT SEQUENCE  OF
      List-Of-Message-Bodies OPTIONAL,
   userLocationInfo                [23] IMPLICIT OCTET STRING OPTIONAL,
   poCInformation                  [24] IMPLICIT POCInformation OPTIONAL,
   recordExtensions                [25] IMPLICIT SET  OF
      ManagementExtension OPTIONAL,
   serviceContextID                [26] IMPLICIT UTF8String OPTIONAL}

CPFRecord  ::= SET {
   recordType                      [0] IMPLICIT RecordType,
   retransmission                  [1] IMPLICIT NULL OPTIONAL,
   sIP-Method                      [2] IMPLICIT GraphicString OPTIONAL,
   nodeAddress                     [3] NodeAddress OPTIONAL,
   session-Id                      [4] IMPLICIT GraphicString OPTIONAL,
   calling-Party-Address           [5] InvolvedParty OPTIONAL,
   called-Party-Address            [6] InvolvedParty OPTIONAL,
   servedParty                     [7] IMPLICIT GraphicString OPTIONAL,
   serviceRequestTimeStamp         [8] IMPLICIT OCTET STRING ( SIZE( 9 ) ) OPTIONAL,
   serviceDeliveryStartTimeStamp   [9] IMPLICIT OCTET STRING ( SIZE( 9 ) ) OPTIONAL,
   serviceDeliveryEndTimeStamp     [10] IMPLICIT OCTET STRING ( SIZE( 9 ) ) OPTIONAL,
   recordOpeningTime               [11] IMPLICIT OCTET STRING ( SIZE( 9 ) ) OPTIONAL,
   recordClosureTime               [12] IMPLICIT OCTET STRING ( SIZE( 9 ) ) OPTIONAL,
   interOperatorIdentifiers        [13] IMPLICIT InterOperatorIdentifiers OPTIONAL,
   localRecordSequenceNumber       [14] IMPLICIT INTEGER ( 0 .. 4294967295 ) OPTIONAL,
   recordSequenceNumber            [15] IMPLICIT INTEGER OPTIONAL,
   causeForRecordClosing           [16] IMPLICIT CauseForRecordClosing OPTIONAL,
   incomplete-CDR-Indication       [17] IMPLICIT Incomplete-CDR-Indication OPTIONAL,
   iMS-Charging-Identifier         [18] IMPLICIT OCTET STRING OPTIONAL,
   list-Of-SDP-Media-Components    [19] IMPLICIT SEQUENCE  OF
      List-Of-SDP-Media-Components OPTIONAL,
   gGSNaddress                     [20] NodeAddress OPTIONAL,
   serviceReasonReturnCode         [21] IMPLICIT UTF8String OPTIONAL,
   list-Of-Message-Bodies          [22] IMPLICIT SEQUENCE  OF
      List-Of-Message-Bodies OPTIONAL,
   userLocationInfo                [23] IMPLICIT OCTET STRING OPTIONAL,
   poCInformation                  [24] IMPLICIT POCInformation OPTIONAL,
   recordExtensions                [25] IMPLICIT SET  OF
      ManagementExtension OPTIONAL,
   serviceContextID                [26] IMPLICIT UTF8String OPTIONAL}

AccessPriority ::= ENUMERATED {
   pre-emptive    ( 0 ),
   high           ( 1 ),
   normal         ( 2 ),
   low            ( 3 ) }

CauseForRecordClosing ::= ENUMERATED {
   normalRelease             ( 0 ),
   abnormalRelease           ( 1 ),
   serviceChange             ( 2 ),
   volumeLimit               ( 3 ),
   timeLimit                 ( 4 ),
   numberofTalkBurstLimit    ( 5 ),
   maxChangeCond             ( 6 ),
   sessionTypeChange         ( 7 ),
   managementIntervention    ( 8 ) }

ChangeCondition ::= ENUMERATED {
   serviceChange                 ( 0 ),
   volumeLimit                   ( 1 ),
   timeLimit                     ( 2 ),
   numberofTalkBurstLimit        ( 3 ),
   numberofActiveParticipants    ( 4 ),
   tariffTime                    ( 5 ) }

ListofTalkBurstExchange ::= SET {
   number-Of-Talk-Bursts            [1] IMPLICIT INTEGER OPTIONAL,
   talk-Burst-Volume                [2] IMPLICIT INTEGER OPTIONAL,
   talk-Bursts-Time                 [3] IMPLICIT INTEGER OPTIONAL,
   number-Of-Received-Talk-Bursts   [4] IMPLICIT INTEGER OPTIONAL,
   received-Talk-Burst-Volume       [5] IMPLICIT INTEGER OPTIONAL,
   received-Talk-Burst-Time         [6] IMPLICIT INTEGER OPTIONAL,
   changeCondition                  [7] IMPLICIT ChangeCondition OPTIONAL,
   changeTime                       [8] IMPLICIT OCTET STRING ( SIZE( 9 ) ),
   numberofParticipants             [9] IMPLICIT INTEGER OPTIONAL}

ParticipatingType ::= ENUMERATED {
   normal        ( 0 ),
   nW-PoC-Box    ( 1 ),
   uE-PoC-Box    ( 2 ) }

POCEventType ::= ENUMERATED {
   normal                   ( 0 ),
   instantPersonalAlert     ( 1 ),
   pOCGroupAdvertisement    ( 2 ),
   earlySessionSettingup    ( 3 ),
   pOCTalkBurst             ( 4 ) }

POCInformation ::= SET {
   pOCSessionType             [1] IMPLICIT POCSessionType OPTIONAL,
   numberofParticipants       [2] IMPLICIT INTEGER OPTIONAL,
   listofParticipants         [3] IMPLICIT SEQUENCE  OF
      POCParticipant OPTIONAL,
   listofTalkBurstExchange    [4] IMPLICIT SEQUENCE  OF
      ListofTalkBurstExchange OPTIONAL,
   pOCControllingAddress      [5] IMPLICIT UTF8String OPTIONAL,
   pOCGroupName               [6] IMPLICIT UTF8String OPTIONAL,
   pOCSessionId               [7] IMPLICIT UTF8String OPTIONAL,
   pOCSessionInitiationType   [8] IMPLICIT POCSessionInitType OPTIONAL,
   pOCEventType               [9] IMPLICIT POCEventType OPTIONAL}

POCParticipant ::= SET {
   called-party-address          [1] InvolvedParty,
   participant-access-priority   [2] IMPLICIT AccessPriority OPTIONAL,
   user-participating-type       [3] IMPLICIT ParticipatingType OPTIONAL}

POCSessionInitType ::= ENUMERATED {
   pre-established    ( 0 ),
   on-demand          ( 1 ) }

POCSessionType ::= ENUMERATED {
   one-to-one-session            ( 0 ),
   chat-group-session            ( 1 ),
   pre-arranged-group-session    ( 2 ),
   ad-hoc-group-session          ( 3 ) }


-- X.721 DMI-EXTENSION. The set is the standard form of the original
-- extensible empty table constraint ({, ...}) and does not change BER.
DMI-EXTENSION ::= CLASS {
    &id     OBJECT IDENTIFIER UNIQUE,
    &Value
}
WITH SYNTAX {
    TYPE &Value
    ID &id
}

ManagementExtensionSet DMI-EXTENSION ::= {...}

END
