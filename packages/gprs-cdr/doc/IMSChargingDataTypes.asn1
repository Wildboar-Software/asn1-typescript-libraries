-- Modified by Jonathan M. Wilbur to fix invalid syntax.
--      Expanded ASN1 Module 'IMSChargingDataTypes'
--SIEMENS ASN.1 Compiler         R6.31  (Production_6.31)
--            Date: 2020-07-10 Time: 16:15:14

IMSChargingDataTypes
{itu-t(0) identified-organization(4) etsi(0) mobileDomain(0) charging(5)
imsChargingDataTypes(4) asn1Module(0) version2(1)}
DEFINITIONS
::=
BEGIN

RecordType ::= INTEGER {
   moCallRecord              ( 0 ),
   mtCallRecord              ( 1 ),
   roamingRecord             ( 2 ),
   incGatewayRecord          ( 3 ),
   outGatewayRecord          ( 4 ),
   transitCallRecord         ( 5 ),
   moSMSRecord               ( 6 ),
   mtSMSRecord               ( 7 ),
   moSMSIWRecord             ( 8 ),
   mtSMSGWRecord             ( 9 ),
   ssActionRecord            ( 10 ),
   hlrIntRecord              ( 11 ),
   locUpdateHLRRecord        ( 12 ),
   locUpdateVLRRecord        ( 13 ),
   commonEquipRecord         ( 14 ),
   moTraceRecord             ( 15 ),
   mtTraceRecord             ( 16 ),
   termCAMELRecord           ( 17 ),
   sgsnPDPRecord             ( 18 ),
   sgsnMMRecord              ( 20 ),
   sgsnSMORecord             ( 21 ),
   sgsnSMTRecord             ( 22 ),
   mtLCSRecord               ( 23 ),
   moLCSRecord               ( 24 ),
   niLCSRecord               ( 25 ),
   sgsnMTLCSRecord           ( 26 ),
   sgsnMOLCSRecord           ( 27 ),
   sgsnNILCSRecord           ( 28 ),
   mMO1SRecord               ( 30 ),
   mMO4FRqRecord             ( 31 ),
   mMO4FRsRecord             ( 32 ),
   mMO4DRecord               ( 33 ),
   mMO1DRecord               ( 34 ),
   mMO4RRecord               ( 35 ),
   mMO1RRecord               ( 36 ),
   mMOMDRecord               ( 37 ),
   mMR4FRecord               ( 38 ),
   mMR1NRqRecord             ( 39 ),
   mMR1NRsRecord             ( 40 ),
   mMR1RtRecord              ( 41 ),
   mMR1AFRecord              ( 42 ),
   mMR4DRqRecord             ( 43 ),
   mMR4DRsRecord             ( 44 ),
   mMR1RRRecord              ( 45 ),
   mMR4RRqRecord             ( 46 ),
   mMR4RRsRecord             ( 47 ),
   mMRMDRecord               ( 48 ),
   mMFRecord                 ( 49 ),
   mMBx1SRecord              ( 50 ),
   mMBx1VRecord              ( 51 ),
   mMBx1URecord              ( 52 ),
   mMBx1DRecord              ( 53 ),
   mM7SRecord                ( 54 ),
   mM7DRqRecord              ( 55 ),
   mM7DRsRecord              ( 56 ),
   mM7CRecord                ( 57 ),
   mM7RRecord                ( 58 ),
   mM7DRRqRecord             ( 59 ),
   mM7DRRsRecord             ( 60 ),
   mM7RRqRecord              ( 61 ),
   mM7RRsRecord              ( 62 ),
   sCSCFRecord               ( 63 ),
   pCSCFRecord               ( 64 ),
   iCSCFRecord               ( 65 ),
   mRFCRecord                ( 66 ),
   mGCFRecord                ( 67 ),
   bGCFRecord                ( 68 ),
   aSRecord                  ( 69 ),
   eCSCFRecord               ( 70 ),
   iBCFRecord                ( 82 ),
   tRFRecord                 ( 89 ),
   tFRecord                  ( 90 ),
   aTCFRecord                ( 91 ),
   lCSGMORecord              ( 71 ),
   lCSRGMTRecord             ( 72 ),
   lCSHGMTRecord             ( 73 ),
   lCSVGMTRecord             ( 74 ),
   lCSGNIRecord              ( 75 ),
   sgsnMBMSRecord            ( 76 ),
   ggsnMBMSRecord            ( 77 ),
   gwMBMSRecord              ( 86 ),
   sUBBMSCRecord             ( 78 ),
   cONTENTBMSCRecord         ( 79 ),
   pPFRecord                 ( 80 ),
   cPFRecord                 ( 81 ),
   sGWRecord                 ( 84 ),
   pGWRecord                 ( 85 ),
   tDFRecord                 ( 92 ),
   iPERecord                 ( 95 ),
   ePDGRecord                ( 96 ),
   tWAGRecord                ( 97 ),
   mMTelRecord               ( 83 ),
   mSCsRVCCRecord            ( 87 ),
   mMTRFRecord               ( 88 ),
   iCSRegisterRecord         ( 99 ),
   sCSMORecord               ( 93 ),
   sCSMTRecord               ( 94 ),
   pFDDRecord                ( 100 ),
   pFEDRecord                ( 101 ),
   pFDCRecord                ( 102 ),
   mECORecord                ( 103 ),
   mERERecord                ( 104 ),
   cPDTSCERecord             ( 105 ),
   cPDTSNNRecord             ( 106 ),
   sCDVTT4Record             ( 110 ),
   sCSMOT4Record             ( 111 ),
   iSMSMORecord              ( 112 ),
   iSMSMTRecord              ( 113 ),
   eASCERecord               ( 120 ),
   chargingFunctionRecord    ( 200 )}

IPBinV6AddressWithPrefixLength ::= SEQUENCE {
   iPBinV6Address           OCTET STRING ( SIZE( 16 ) ),
   pDPAddressPrefixLength   INTEGER ( 1 .. 64 ) DEFAULT 64}

ServiceSpecificInfo ::= SEQUENCE {
   serviceSpecificData   [0] IMPLICIT GraphicString OPTIONAL,
   serviceSpecificType   [1] IMPLICIT INTEGER OPTIONAL}

IPTextRepresentedAddress ::= CHOICE {
   iPTextV4Address     [2] IMPLICIT IA5String  ( SIZE( 7 .. 15 ) ),
   iPTextV6Address     [3] IMPLICIT IA5String  ( SIZE( 15 .. 45 ) )}

IPBinV6AddressWithOrWithoutPrefixLength ::= CHOICE {
   iPBinV6Address               [1] IMPLICIT OCTET STRING ( SIZE( 16 ) ),
   iPBinV6AddressWithPrefix     [4] IMPLICIT IPBinV6AddressWithPrefixLength}

IPBinaryAddress ::= CHOICE {
   iPBinV4Address     [0] IMPLICIT OCTET STRING ( SIZE( 4 ) ),
   iPBinV6Address     IPBinV6AddressWithOrWithoutPrefixLength}

NodeAddress ::= CHOICE {
   iPAddress      [0] ServedPartyIPAddress,
   domainName     [1] IMPLICIT GraphicString}

InvolvedParty ::= CHOICE {
   sIP-URI       [0] IMPLICIT GraphicString,
   tEL-URI       [1] IMPLICIT GraphicString,
   uRN           [2] IMPLICIT GraphicString,
   iSDN-E164     [3] IMPLICIT GraphicString}

SubscriberEquipmentNumber ::= SET {
   subscriberEquipmentNumberType   [0] IMPLICIT ENUMERATED {
      iMEISV           ( 0 ),
      mAC              ( 1 ),
      eUI64            ( 2 ),
      modifiedEUI64    ( 3 ) },
   subscriberEquipmentNumberData   [1] IMPLICIT OCTET STRING}

SubscriptionID ::= SET {
   subscriptionIDType   [0] IMPLICIT ENUMERATED {
      eND-USER-E164       ( 0 ),
      eND-USER-IMSI       ( 1 ),
      eND-USER-SIP-URI    ( 2 ),
      eND-USER-NAI        ( 3 ),
      eND-USER-PRIVATE    ( 4 ) },
   subscriptionIDData   [1] IMPLICIT UTF8String}

ManagementExtension ::= SEQUENCE {
   identifier     DMI-EXTENSION.&id ({ManagementExtensionSet}) ,
   significance   [1] IMPLICIT BOOLEAN DEFAULT FALSE,
   information    [2] DMI-EXTENSION.&Value ({ManagementExtensionSet}{@.identifier}) }

IMSRecord  ::= CHOICE {
   sCSCFRecord     [63] IMPLICIT SCSCFRecord,
   pCSCFRecord     [64] IMPLICIT PCSCFRecord,
   iCSCFRecord     [65] IMPLICIT ICSCFRecord,
   mRFCRecord      [66] IMPLICIT MRFCRecord,
   mGCFRecord      [67] IMPLICIT MGCFRecord,
   bGCFRecord      [68] IMPLICIT BGCFRecord,
   aSRecord        [69] IMPLICIT ASRecord,
   eCSCFRecord     [70] IMPLICIT ECSCFRecord,
   iBCFRecord      [82] IMPLICIT IBCFRecord,
   tRFRecord       [89] IMPLICIT TRFRecord,
   tFRecord        [90] IMPLICIT TFRecord,
   aTCFRecord      [91] IMPLICIT ATCFRecord}

SCSCFRecord ::= SET {
   recordType                              [0] IMPLICIT RecordType,
   retransmission                          [1] IMPLICIT NULL OPTIONAL,
   sIP-Method                              [2] IMPLICIT GraphicString OPTIONAL,
   role-of-Node                            [3] IMPLICIT Role-of-Node OPTIONAL,
   nodeAddress                             [4] NodeAddress OPTIONAL,
   session-Id                              [5] IMPLICIT GraphicString OPTIONAL,
   list-Of-Calling-Party-Address           [6] IMPLICIT SEQUENCE  OF
      InvolvedParty OPTIONAL,
   called-Party-Address                    [7] InvolvedParty OPTIONAL,
   privateUserID                           [8] IMPLICIT GraphicString OPTIONAL,
   serviceRequestTimeStamp                 [9] IMPLICIT OCTET STRING ( SIZE( 9 ) ) OPTIONAL,
   serviceDeliveryStartTimeStamp           [10] IMPLICIT OCTET STRING ( SIZE( 9 ) ) OPTIONAL,
   serviceDeliveryEndTimeStamp             [11] IMPLICIT OCTET STRING ( SIZE( 9 ) ) OPTIONAL,
   recordOpeningTime                       [12] IMPLICIT OCTET STRING ( SIZE( 9 ) ) OPTIONAL,
   recordClosureTime                       [13] IMPLICIT OCTET STRING ( SIZE( 9 ) ) OPTIONAL,
   interOperatorIdentifiers                [14] IMPLICIT SEQUENCE  OF
      InterOperatorIdentifiers OPTIONAL,
   localRecordSequenceNumber               [15] IMPLICIT INTEGER ( 0 .. 4294967295 ) OPTIONAL,
   recordSequenceNumber                    [16] IMPLICIT INTEGER OPTIONAL,
   causeForRecordClosing                   [17] IMPLICIT CauseForRecordClosing OPTIONAL,
   incomplete-CDR-Indication               [18] IMPLICIT Incomplete-CDR-Indication OPTIONAL,
   iMS-Charging-Identifier                 [19] IMPLICIT OCTET STRING OPTIONAL,
   list-Of-SDP-Media-Components            [21] IMPLICIT SEQUENCE  OF
      Media-Components-List OPTIONAL,
   gGSNaddress                             [22] NodeAddress OPTIONAL,
   serviceReasonReturnCode                 [23] IMPLICIT UTF8String OPTIONAL,
   list-Of-Message-Bodies                  [24] IMPLICIT SEQUENCE  OF
      MessageBody OPTIONAL,
   recordExtensions                        [25] IMPLICIT SET  OF
      ManagementExtension OPTIONAL,
   expiresInformation                      [26] IMPLICIT INTEGER OPTIONAL,
   list-Of-Associated-URI                  [27] IMPLICIT SEQUENCE  OF
      InvolvedParty OPTIONAL,
   event                                   [28] IMPLICIT UTF8String OPTIONAL,
   accessNetworkInformation                [29] IMPLICIT OCTET STRING OPTIONAL,
   serviceContextID                        [30] IMPLICIT UTF8String OPTIONAL,
   list-of-subscription-ID                 [31] IMPLICIT SEQUENCE  OF
      SubscriptionID OPTIONAL,
   list-Of-Early-SDP-Media-Components      [32] IMPLICIT SEQUENCE  OF
      Early-Media-Components-List OPTIONAL,
   iMSCommunicationServiceIdentifier       [33] IMPLICIT OCTET STRING OPTIONAL,
   numberPortabilityRouting                [34] IMPLICIT GraphicString OPTIONAL,
   carrierSelectRouting                    [35] IMPLICIT GraphicString OPTIONAL,
   sessionPriority                         [36] IMPLICIT SessionPriority OPTIONAL,
   serviceRequestTimeStampFraction         [37] IMPLICIT INTEGER ( 0 .. 999 ) OPTIONAL,
   serviceDeliveryStartTimeStampFraction   [38] IMPLICIT INTEGER ( 0 .. 999 ) OPTIONAL,
   serviceDeliveryEndTimeStampFraction     [39] IMPLICIT INTEGER ( 0 .. 999 ) OPTIONAL,
   applicationServersInformation           [40] IMPLICIT SEQUENCE  OF
      ApplicationServersInformation OPTIONAL,
   requested-Party-Address                 [41] InvolvedParty OPTIONAL,
   list-Of-Called-Asserted-Identity        [42] IMPLICIT SEQUENCE  OF
      InvolvedParty OPTIONAL,
   online-charging-flag                    [43] IMPLICIT NULL OPTIONAL,
   realTimeTariffInformation               [44] IMPLICIT SEQUENCE  OF
      RealTimeTariffInformation OPTIONAL,
   userLocationInformation                 [47] IMPLICIT OCTET STRING OPTIONAL,
   mSTimeZone                              [48] IMPLICIT OCTET STRING ( SIZE( 2 ) ) OPTIONAL,
   nNI-Information                         [46] IMPLICIT NNI-Information OPTIONAL,
   fromAddress                             [51] IMPLICIT OCTET STRING OPTIONAL,
   iMSEmergencyIndicator                   [52] IMPLICIT NULL OPTIONAL,
   transit-IOI-Lists                       [53] IMPLICIT SEQUENCE  OF
      GraphicString OPTIONAL,
   iMSVisitedNetworkIdentifier             [54] IMPLICIT OCTET STRING OPTIONAL,
   listOfReasonHeader                      [55] IMPLICIT SEQUENCE  OF
      GraphicString OPTIONAL,
   additionalAccessNetworkInformation      [56] IMPLICIT OCTET STRING OPTIONAL,
   instanceId                              [57] IMPLICIT OCTET STRING OPTIONAL,
   subscriberEquipmentNumber               [58] IMPLICIT SubscriberEquipmentNumber OPTIONAL,
   routeHeaderReceived                     [59] IMPLICIT OCTET STRING OPTIONAL,
   routeHeaderTransmitted                  [60] IMPLICIT OCTET STRING OPTIONAL,
   list-Of-AccessNetworkInfoChange         [62] IMPLICIT SEQUENCE  OF
      AccessNetworkInfoChange OPTIONAL,
   listOfCalledIdentityChanges             [63] IMPLICIT SEQUENCE  OF
      CalledIdentityChange OPTIONAL,
   cellularNetworkInformation              [64] IMPLICIT OCTET STRING OPTIONAL,
   fEIdentifierList                        [65] IMPLICIT SEQUENCE  OF
      GraphicString OPTIONAL}

PCSCFRecord ::= SET {
   recordType                              [0] IMPLICIT RecordType,
   retransmission                          [1] IMPLICIT NULL OPTIONAL,
   sIP-Method                              [2] IMPLICIT GraphicString OPTIONAL,
   role-of-Node                            [3] IMPLICIT Role-of-Node OPTIONAL,
   nodeAddress                             [4] NodeAddress OPTIONAL,
   session-Id                              [5] IMPLICIT GraphicString OPTIONAL,
   list-Of-Calling-Party-Address           [6] IMPLICIT SEQUENCE  OF
      InvolvedParty OPTIONAL,
   called-Party-Address                    [7] InvolvedParty OPTIONAL,
   privateUserID                           [8] IMPLICIT GraphicString OPTIONAL,
   serviceRequestTimeStamp                 [9] IMPLICIT OCTET STRING ( SIZE( 9 ) ) OPTIONAL,
   serviceDeliveryStartTimeStamp           [10] IMPLICIT OCTET STRING ( SIZE( 9 ) ) OPTIONAL,
   serviceDeliveryEndTimeStamp             [11] IMPLICIT OCTET STRING ( SIZE( 9 ) ) OPTIONAL,
   recordOpeningTime                       [12] IMPLICIT OCTET STRING ( SIZE( 9 ) ) OPTIONAL,
   recordClosureTime                       [13] IMPLICIT OCTET STRING ( SIZE( 9 ) ) OPTIONAL,
   interOperatorIdentifiers                [14] IMPLICIT InterOperatorIdentifiers OPTIONAL,
   localRecordSequenceNumber               [15] IMPLICIT INTEGER ( 0 .. 4294967295 ) OPTIONAL,
   recordSequenceNumber                    [16] IMPLICIT INTEGER OPTIONAL,
   causeForRecordClosing                   [17] IMPLICIT CauseForRecordClosing OPTIONAL,
   incomplete-CDR-Indication               [18] IMPLICIT Incomplete-CDR-Indication OPTIONAL,
   iMS-Charging-Identifier                 [19] IMPLICIT OCTET STRING OPTIONAL,
   list-Of-SDP-Media-Components            [21] IMPLICIT SEQUENCE  OF
      Media-Components-List OPTIONAL,
   gGSNaddress                             [22] NodeAddress OPTIONAL,
   serviceReasonReturnCode                 [23] IMPLICIT UTF8String OPTIONAL,
   list-Of-Message-Bodies                  [24] IMPLICIT SEQUENCE  OF
      MessageBody OPTIONAL,
   recordExtensions                        [25] IMPLICIT SET  OF
      ManagementExtension OPTIONAL,
   expiresInformation                      [26] IMPLICIT INTEGER OPTIONAL,
   list-Of-Associated-URI                  [27] IMPLICIT SEQUENCE  OF
      InvolvedParty OPTIONAL,
   event                                   [28] IMPLICIT UTF8String OPTIONAL,
   accessNetworkInformation                [29] IMPLICIT OCTET STRING OPTIONAL,
   serviceContextID                        [30] IMPLICIT UTF8String OPTIONAL,
   list-of-subscription-ID                 [31] IMPLICIT SEQUENCE  OF
      SubscriptionID OPTIONAL,
   list-Of-Early-SDP-Media-Components      [32] IMPLICIT SEQUENCE  OF
      Early-Media-Components-List OPTIONAL,
   iMSCommunicationServiceIdentifier       [33] IMPLICIT OCTET STRING OPTIONAL,
   sessionPriority                         [36] IMPLICIT SessionPriority OPTIONAL,
   serviceRequestTimeStampFraction         [37] IMPLICIT INTEGER ( 0 .. 999 ) OPTIONAL,
   serviceDeliveryStartTimeStampFraction   [38] IMPLICIT INTEGER ( 0 .. 999 ) OPTIONAL,
   serviceDeliveryEndTimeStampFraction     [39] IMPLICIT INTEGER ( 0 .. 999 ) OPTIONAL,
   list-of-Requested-Party-Address         [41] IMPLICIT SEQUENCE  OF
      InvolvedParty OPTIONAL,
   list-Of-Called-Asserted-Identity        [42] IMPLICIT SEQUENCE  OF
      InvolvedParty OPTIONAL,
   nNI-Information                         [46] IMPLICIT NNI-Information OPTIONAL,
   userLocationInformation                 [47] IMPLICIT OCTET STRING OPTIONAL,
   mSTimeZone                              [48] IMPLICIT OCTET STRING ( SIZE( 2 ) ) OPTIONAL,
   servedPartyIPAddress                    [50] ServedPartyIPAddress OPTIONAL,
   fromAddress                             [51] IMPLICIT OCTET STRING OPTIONAL,
   iMSEmergencyIndicator                   [52] IMPLICIT NULL OPTIONAL,
   transit-IOI-Lists                       [53] IMPLICIT SEQUENCE  OF
      GraphicString OPTIONAL,
   iMSVisitedNetworkIdentifier             [54] IMPLICIT OCTET STRING OPTIONAL,
   listOfReasonHeader                      [55] IMPLICIT SEQUENCE  OF
      GraphicString OPTIONAL,
   additionalAccessNetworkInformation      [56] IMPLICIT OCTET STRING OPTIONAL,
   instanceId                              [57] IMPLICIT OCTET STRING OPTIONAL,
   subscriberEquipmentNumber               [58] IMPLICIT SubscriberEquipmentNumber OPTIONAL,
   routeHeaderReceived                     [59] IMPLICIT OCTET STRING OPTIONAL,
   routeHeaderTransmitted                  [60] IMPLICIT OCTET STRING OPTIONAL,
   list-Of-AccessNetworkInfoChange         [62] IMPLICIT SEQUENCE  OF
      AccessNetworkInfoChange OPTIONAL,
   listOfCalledIdentityChanges             [63] IMPLICIT SEQUENCE  OF
      CalledIdentityChange OPTIONAL,
   cellularNetworkInformation              [64] IMPLICIT OCTET STRING OPTIONAL,
   initialIMS-Charging-Identifier          [105] IMPLICIT OCTET STRING OPTIONAL,
   list-Of-AccessTransferInformation       [106] IMPLICIT SEQUENCE  OF
      AccessTransferInformation OPTIONAL,
   relatedICID                             [107] IMPLICIT OCTET STRING OPTIONAL,
   relatedICIDGenerationNode               [108] NodeAddress OPTIONAL,
   fEIdentifierList                        [109] IMPLICIT SEQUENCE  OF
      GraphicString OPTIONAL}

ICSCFRecord ::= SET {
   recordType                           [0] IMPLICIT RecordType,
   retransmission                       [1] IMPLICIT NULL OPTIONAL,
   sIP-Method                           [2] IMPLICIT GraphicString OPTIONAL,
   role-of-Node                         [3] IMPLICIT Role-of-Node OPTIONAL,
   nodeAddress                          [4] NodeAddress OPTIONAL,
   session-Id                           [5] IMPLICIT GraphicString OPTIONAL,
   list-Of-Calling-Party-Address        [6] IMPLICIT SEQUENCE  OF
      InvolvedParty OPTIONAL,
   called-Party-Address                 [7] InvolvedParty OPTIONAL,
   serviceRequestTimeStamp              [9] IMPLICIT OCTET STRING ( SIZE( 9 ) ) OPTIONAL,
   interOperatorIdentifiers             [14] IMPLICIT InterOperatorIdentifiers OPTIONAL,
   localRecordSequenceNumber            [15] IMPLICIT INTEGER ( 0 .. 4294967295 ) OPTIONAL,
   causeForRecordClosing                [17] IMPLICIT CauseForRecordClosing OPTIONAL,
   incomplete-CDR-Indication            [18] IMPLICIT Incomplete-CDR-Indication OPTIONAL,
   iMS-Charging-Identifier              [19] IMPLICIT OCTET STRING OPTIONAL,
   serviceReasonReturnCode              [23] IMPLICIT UTF8String OPTIONAL,
   recordExtensions                     [25] IMPLICIT SET  OF
      ManagementExtension OPTIONAL,
   expiresInformation                   [26] IMPLICIT INTEGER OPTIONAL,
   list-Of-Associated-URI               [27] IMPLICIT SEQUENCE  OF
      InvolvedParty OPTIONAL,
   event                                [28] IMPLICIT UTF8String OPTIONAL,
   accessNetworkInformation             [29] IMPLICIT OCTET STRING OPTIONAL,
   serviceContextID                     [30] IMPLICIT UTF8String OPTIONAL,
   numberPortabilityRouting             [34] IMPLICIT GraphicString OPTIONAL,
   carrierSelectRouting                 [35] IMPLICIT GraphicString OPTIONAL,
   sessionPriority                      [36] IMPLICIT SessionPriority OPTIONAL,
   serviceRequestTimeStampFraction      [37] IMPLICIT INTEGER ( 0 .. 999 ) OPTIONAL,
   transit-IOI-List                     [45] IMPLICIT GraphicString OPTIONAL,
   userLocationInformation              [47] IMPLICIT OCTET STRING OPTIONAL,
   mSTimeZone                           [48] IMPLICIT OCTET STRING ( SIZE( 2 ) ) OPTIONAL,
   fromAddress                          [51] IMPLICIT OCTET STRING OPTIONAL,
   iMSEmergencyIndicator                [52] IMPLICIT NULL OPTIONAL,
   listOfReasonHeader                   [55] IMPLICIT SEQUENCE  OF
      GraphicString OPTIONAL,
   additionalAccessNetworkInformation   [56] IMPLICIT OCTET STRING OPTIONAL,
   routeHeaderTransmitted               [60] IMPLICIT OCTET STRING OPTIONAL,
   s-CSCF-Information                   [61] IMPLICIT S-CSCF-Information OPTIONAL,
   cellularNetworkInformation           [64] IMPLICIT OCTET STRING OPTIONAL,
   fEIdentifierList                     [65] IMPLICIT SEQUENCE  OF
      GraphicString OPTIONAL}

MRFCRecord ::= SET {
   recordType                              [0] IMPLICIT RecordType,
   retransmission                          [1] IMPLICIT NULL OPTIONAL,
   sIP-Method                              [2] IMPLICIT GraphicString OPTIONAL,
   nodeAddress                             [4] NodeAddress OPTIONAL,
   session-Id                              [5] IMPLICIT GraphicString OPTIONAL,
   list-Of-Calling-Party-Address           [6] IMPLICIT SEQUENCE  OF
      InvolvedParty OPTIONAL,
   called-Party-Address                    [7] InvolvedParty OPTIONAL,
   serviceRequestTimeStamp                 [9] IMPLICIT OCTET STRING ( SIZE( 9 ) ) OPTIONAL,
   serviceDeliveryStartTimeStamp           [10] IMPLICIT OCTET STRING ( SIZE( 9 ) ) OPTIONAL,
   serviceDeliveryEndTimeStamp             [11] IMPLICIT OCTET STRING ( SIZE( 9 ) ) OPTIONAL,
   recordOpeningTime                       [12] IMPLICIT OCTET STRING ( SIZE( 9 ) ) OPTIONAL,
   recordClosureTime                       [13] IMPLICIT OCTET STRING ( SIZE( 9 ) ) OPTIONAL,
   interOperatorIdentifiers                [14] IMPLICIT InterOperatorIdentifiers OPTIONAL,
   localRecordSequenceNumber               [15] IMPLICIT INTEGER ( 0 .. 4294967295 ) OPTIONAL,
   recordSequenceNumber                    [16] IMPLICIT INTEGER OPTIONAL,
   causeForRecordClosing                   [17] IMPLICIT CauseForRecordClosing OPTIONAL,
   incomplete-CDR-Indication               [18] IMPLICIT Incomplete-CDR-Indication OPTIONAL,
   iMS-Charging-Identifier                 [19] IMPLICIT OCTET STRING OPTIONAL,
   list-Of-SDP-Media-Components            [21] IMPLICIT SEQUENCE  OF
      Media-Components-List OPTIONAL,
   gGSNaddress                             [22] NodeAddress OPTIONAL,
   serviceReasonReturnCode                 [23] IMPLICIT UTF8String OPTIONAL,
   recordExtensions                        [25] IMPLICIT SET  OF
      ManagementExtension OPTIONAL,
   expiresInformation                      [26] IMPLICIT INTEGER OPTIONAL,
   event                                   [28] IMPLICIT UTF8String OPTIONAL,
   accessNetworkInformation                [29] IMPLICIT OCTET STRING OPTIONAL,
   serviceContextID                        [30] IMPLICIT UTF8String OPTIONAL,
   list-of-subscription-ID                 [31] IMPLICIT SEQUENCE  OF
      SubscriptionID OPTIONAL,
   list-Of-Early-SDP-Media-Components      [32] IMPLICIT SEQUENCE  OF
      Early-Media-Components-List OPTIONAL,
   sessionPriority                         [36] IMPLICIT SessionPriority OPTIONAL,
   serviceRequestTimeStampFraction         [37] IMPLICIT INTEGER ( 0 .. 999 ) OPTIONAL,
   serviceDeliveryStartTimeStampFraction   [38] IMPLICIT INTEGER ( 0 .. 999 ) OPTIONAL,
   serviceDeliveryEndTimeStampFraction     [39] IMPLICIT INTEGER ( 0 .. 999 ) OPTIONAL,
   applicationServersInformation           [40] IMPLICIT SEQUENCE  OF
      ApplicationServersInformation OPTIONAL,
   online-charging-flag                    [43] IMPLICIT NULL OPTIONAL,
   transit-IOI-List                        [45] IMPLICIT GraphicString OPTIONAL,
   userLocationInformation                 [47] IMPLICIT OCTET STRING OPTIONAL,
   mSTimeZone                              [48] IMPLICIT OCTET STRING ( SIZE( 2 ) ) OPTIONAL,
   fromAddress                             [51] IMPLICIT OCTET STRING OPTIONAL,
   listOfReasonHeader                      [55] IMPLICIT SEQUENCE  OF
      GraphicString OPTIONAL,
   additionalAccessNetworkInformation      [56] IMPLICIT OCTET STRING OPTIONAL,
   list-Of-AccessNetworkInfoChange         [62] IMPLICIT SEQUENCE  OF
      AccessNetworkInfoChange OPTIONAL,
   cellularNetworkInformation              [64] IMPLICIT OCTET STRING OPTIONAL,
   service-Id                              [70] IMPLICIT GraphicString OPTIONAL,
   requested-Party-Address                 [71] InvolvedParty OPTIONAL,
   list-Of-Called-Asserted-Identity        [72] IMPLICIT SEQUENCE  OF
      InvolvedParty OPTIONAL,
   fEIdentifierList                        [73] IMPLICIT SEQUENCE  OF
      GraphicString OPTIONAL}

MGCFRecord ::= SET {
   recordType                              [0] IMPLICIT RecordType,
   retransmission                          [1] IMPLICIT NULL OPTIONAL,
   sIP-Method                              [2] IMPLICIT GraphicString OPTIONAL,
   role-of-Node                            [3] IMPLICIT Role-of-Node OPTIONAL,
   nodeAddress                             [4] NodeAddress OPTIONAL,
   session-Id                              [5] IMPLICIT GraphicString OPTIONAL,
   list-Of-Calling-Party-Address           [6] IMPLICIT SEQUENCE  OF
      InvolvedParty OPTIONAL,
   called-Party-Address                    [7] InvolvedParty OPTIONAL,
   serviceRequestTimeStamp                 [9] IMPLICIT OCTET STRING ( SIZE( 9 ) ) OPTIONAL,
   serviceDeliveryStartTimeStamp           [10] IMPLICIT OCTET STRING ( SIZE( 9 ) ) OPTIONAL,
   serviceDeliveryEndTimeStamp             [11] IMPLICIT OCTET STRING ( SIZE( 9 ) ) OPTIONAL,
   recordOpeningTime                       [12] IMPLICIT OCTET STRING ( SIZE( 9 ) ) OPTIONAL,
   recordClosureTime                       [13] IMPLICIT OCTET STRING ( SIZE( 9 ) ) OPTIONAL,
   interOperatorIdentifiers                [14] IMPLICIT InterOperatorIdentifiers OPTIONAL,
   localRecordSequenceNumber               [15] IMPLICIT INTEGER ( 0 .. 4294967295 ) OPTIONAL,
   recordSequenceNumber                    [16] IMPLICIT INTEGER OPTIONAL,
   causeForRecordClosing                   [17] IMPLICIT CauseForRecordClosing OPTIONAL,
   incomplete-CDR-Indication               [18] IMPLICIT Incomplete-CDR-Indication OPTIONAL,
   iMS-Charging-Identifier                 [19] IMPLICIT OCTET STRING OPTIONAL,
   list-Of-SDP-Media-Components            [21] IMPLICIT SEQUENCE  OF
      Media-Components-List OPTIONAL,
   serviceReasonReturnCode                 [23] IMPLICIT UTF8String OPTIONAL,
   recordExtensions                        [25] IMPLICIT SET  OF
      ManagementExtension OPTIONAL,
   expiresInformation                      [26] IMPLICIT INTEGER OPTIONAL,
   event                                   [28] IMPLICIT UTF8String OPTIONAL,
   accessNetworkInformation                [29] IMPLICIT OCTET STRING OPTIONAL,
   serviceContextID                        [30] IMPLICIT UTF8String OPTIONAL,
   list-Of-Early-SDP-Media-Components      [32] IMPLICIT SEQUENCE  OF
      Early-Media-Components-List OPTIONAL,
   numberPortabilityRouting                [34] IMPLICIT GraphicString OPTIONAL,
   carrierSelectRouting                    [35] IMPLICIT GraphicString OPTIONAL,
   sessionPriority                         [36] IMPLICIT SessionPriority OPTIONAL,
   serviceRequestTimeStampFraction         [37] IMPLICIT INTEGER ( 0 .. 999 ) OPTIONAL,
   serviceDeliveryStartTimeStampFraction   [38] IMPLICIT INTEGER ( 0 .. 999 ) OPTIONAL,
   serviceDeliveryEndTimeStampFraction     [39] IMPLICIT INTEGER ( 0 .. 999 ) OPTIONAL,
   realTimeTariffInformation               [44] IMPLICIT SEQUENCE  OF
      RealTimeTariffInformation OPTIONAL,
   transit-IOI-List                        [45] IMPLICIT GraphicString OPTIONAL,
   fromAddress                             [51] IMPLICIT OCTET STRING OPTIONAL,
   listOfReasonHeader                      [55] IMPLICIT SEQUENCE  OF
      GraphicString OPTIONAL,
   additionalAccessNetworkInformation      [56] IMPLICIT OCTET STRING OPTIONAL,
   list-Of-AccessNetworkInfoChange         [62] IMPLICIT SEQUENCE  OF
      AccessNetworkInfoChange OPTIONAL,
   cellularNetworkInformation              [64] IMPLICIT OCTET STRING OPTIONAL,
   trunkGroupID                            [80] TrunkGroupID OPTIONAL,
   bearerService                           [81] IMPLICIT TransmissionMedium OPTIONAL,
   iSUPCause                               [82] IMPLICIT ISUPCause OPTIONAL,
   fEIdentifierList                        [83] IMPLICIT SEQUENCE  OF
      GraphicString OPTIONAL}

BGCFRecord ::= SET {
   recordType                              [0] IMPLICIT RecordType,
   retransmission                          [1] IMPLICIT NULL OPTIONAL,
   sIP-Method                              [2] IMPLICIT GraphicString OPTIONAL,
   role-of-Node                            [3] IMPLICIT Role-of-Node OPTIONAL,
   nodeAddress                             [4] NodeAddress OPTIONAL,
   session-Id                              [5] IMPLICIT GraphicString OPTIONAL,
   list-Of-Calling-Party-Address           [6] IMPLICIT SEQUENCE  OF
      InvolvedParty OPTIONAL,
   called-Party-Address                    [7] InvolvedParty OPTIONAL,
   serviceRequestTimeStamp                 [9] IMPLICIT OCTET STRING ( SIZE( 9 ) ) OPTIONAL,
   serviceDeliveryStartTimeStamp           [10] IMPLICIT OCTET STRING ( SIZE( 9 ) ) OPTIONAL,
   serviceDeliveryEndTimeStamp             [11] IMPLICIT OCTET STRING ( SIZE( 9 ) ) OPTIONAL,
   recordOpeningTime                       [12] IMPLICIT OCTET STRING ( SIZE( 9 ) ) OPTIONAL,
   recordClosureTime                       [13] IMPLICIT OCTET STRING ( SIZE( 9 ) ) OPTIONAL,
   interOperatorIdentifiers                [14] IMPLICIT InterOperatorIdentifiers OPTIONAL,
   localRecordSequenceNumber               [15] IMPLICIT INTEGER ( 0 .. 4294967295 ) OPTIONAL,
   recordSequenceNumber                    [16] IMPLICIT INTEGER OPTIONAL,
   causeForRecordClosing                   [17] IMPLICIT CauseForRecordClosing OPTIONAL,
   incomplete-CDR-Indication               [18] IMPLICIT Incomplete-CDR-Indication OPTIONAL,
   iMS-Charging-Identifier                 [19] IMPLICIT OCTET STRING OPTIONAL,
   serviceReasonReturnCode                 [23] IMPLICIT UTF8String OPTIONAL,
   recordExtensions                        [25] IMPLICIT SET  OF
      ManagementExtension OPTIONAL,
   expiresInformation                      [26] IMPLICIT INTEGER OPTIONAL,
   event                                   [28] IMPLICIT UTF8String OPTIONAL,
   accessNetworkInformation                [29] IMPLICIT OCTET STRING OPTIONAL,
   serviceContextID                        [30] IMPLICIT UTF8String OPTIONAL,
   numberPortabilityRouting                [34] IMPLICIT GraphicString OPTIONAL,
   carrierSelectRouting                    [35] IMPLICIT GraphicString OPTIONAL,
   sessionPriority                         [36] IMPLICIT SessionPriority OPTIONAL,
   serviceRequestTimeStampFraction         [37] IMPLICIT INTEGER ( 0 .. 999 ) OPTIONAL,
   serviceDeliveryStartTimeStampFraction   [38] IMPLICIT INTEGER ( 0 .. 999 ) OPTIONAL,
   serviceDeliveryEndTimeStampFraction     [39] IMPLICIT INTEGER ( 0 .. 999 ) OPTIONAL,
   transit-IOI-List                        [45] IMPLICIT GraphicString OPTIONAL,
   nNI-Information                         [46] IMPLICIT NNI-Information OPTIONAL,
   fromAddress                             [51] IMPLICIT OCTET STRING OPTIONAL,
   listOfReasonHeader                      [55] IMPLICIT SEQUENCE  OF
      GraphicString OPTIONAL,
   additionalAccessNetworkInformation      [56] IMPLICIT OCTET STRING OPTIONAL,
   cellularNetworkInformation              [64] IMPLICIT OCTET STRING OPTIONAL,
   fEIdentifierList                        [65] IMPLICIT SEQUENCE  OF
      GraphicString OPTIONAL}

ASRecord   ::= SET {
   recordType                              [0] IMPLICIT RecordType,
   retransmission                          [1] IMPLICIT NULL OPTIONAL,
   sIP-Method                              [2] IMPLICIT GraphicString OPTIONAL,
   role-of-Node                            [3] IMPLICIT Role-of-Node OPTIONAL,
   nodeAddress                             [4] NodeAddress OPTIONAL,
   session-Id                              [5] IMPLICIT GraphicString OPTIONAL,
   list-Of-Calling-Party-Address           [6] IMPLICIT SEQUENCE  OF
      InvolvedParty OPTIONAL,
   called-Party-Address                    [7] InvolvedParty OPTIONAL,
   privateUserID                           [8] IMPLICIT GraphicString OPTIONAL,
   serviceRequestTimeStamp                 [9] IMPLICIT OCTET STRING ( SIZE( 9 ) ) OPTIONAL,
   serviceDeliveryStartTimeStamp           [10] IMPLICIT OCTET STRING ( SIZE( 9 ) ) OPTIONAL,
   serviceDeliveryEndTimeStamp             [11] IMPLICIT OCTET STRING ( SIZE( 9 ) ) OPTIONAL,
   recordOpeningTime                       [12] IMPLICIT OCTET STRING ( SIZE( 9 ) ) OPTIONAL,
   recordClosureTime                       [13] IMPLICIT OCTET STRING ( SIZE( 9 ) ) OPTIONAL,
   interOperatorIdentifiers                [14] IMPLICIT InterOperatorIdentifiers OPTIONAL,
   localRecordSequenceNumber               [15] IMPLICIT INTEGER ( 0 .. 4294967295 ) OPTIONAL,
   recordSequenceNumber                    [16] IMPLICIT INTEGER OPTIONAL,
   causeForRecordClosing                   [17] IMPLICIT CauseForRecordClosing OPTIONAL,
   incomplete-CDR-Indication               [18] IMPLICIT Incomplete-CDR-Indication OPTIONAL,
   iMS-Charging-Identifier                 [19] IMPLICIT OCTET STRING OPTIONAL,
   list-Of-SDP-Media-Components            [21] IMPLICIT SEQUENCE  OF
      Media-Components-List OPTIONAL,
   gGSNaddress                             [22] NodeAddress OPTIONAL,
   serviceReasonReturnCode                 [23] IMPLICIT UTF8String OPTIONAL,
   list-Of-Message-Bodies                  [24] IMPLICIT SEQUENCE  OF
      MessageBody OPTIONAL,
   recordExtensions                        [25] IMPLICIT SET  OF
      ManagementExtension OPTIONAL,
   expiresInformation                      [26] IMPLICIT INTEGER OPTIONAL,
   event                                   [28] IMPLICIT UTF8String OPTIONAL,
   accessNetworkInformation                [29] IMPLICIT OCTET STRING OPTIONAL,
   serviceContextID                        [30] IMPLICIT UTF8String OPTIONAL,
   list-of-subscription-ID                 [31] IMPLICIT SEQUENCE  OF
      SubscriptionID OPTIONAL,
   list-Of-Early-SDP-Media-Components      [32] IMPLICIT SEQUENCE  OF
      Early-Media-Components-List OPTIONAL,
   iMSCommunicationServiceIdentifier       [33] IMPLICIT OCTET STRING OPTIONAL,
   numberPortabilityRouting                [34] IMPLICIT GraphicString OPTIONAL,
   carrierSelectRouting                    [35] IMPLICIT GraphicString OPTIONAL,
   sessionPriority                         [36] IMPLICIT SessionPriority OPTIONAL,
   serviceRequestTimeStampFraction         [37] IMPLICIT INTEGER ( 0 .. 999 ) OPTIONAL,
   serviceDeliveryStartTimeStampFraction   [38] IMPLICIT INTEGER ( 0 .. 999 ) OPTIONAL,
   serviceDeliveryEndTimeStampFraction     [39] IMPLICIT INTEGER ( 0 .. 999 ) OPTIONAL,
   list-of-Requested-Party-Address         [41] IMPLICIT SEQUENCE  OF
      InvolvedParty OPTIONAL,
   online-charging-flag                    [43] IMPLICIT NULL OPTIONAL,
   realTimeTariffInformation               [44] IMPLICIT SEQUENCE  OF
      RealTimeTariffInformation OPTIONAL,
   nNI-Information                         [46] IMPLICIT NNI-Information OPTIONAL,
   userLocationInformation                 [47] IMPLICIT OCTET STRING OPTIONAL,
   mSTimeZone                              [48] IMPLICIT OCTET STRING ( SIZE( 2 ) ) OPTIONAL,
   fromAddress                             [51] IMPLICIT OCTET STRING OPTIONAL,
   transit-IOI-Lists                       [53] IMPLICIT SEQUENCE  OF
      GraphicString OPTIONAL,
   iMSVisitedNetworkIdentifier             [54] IMPLICIT OCTET STRING OPTIONAL,
   listOfReasonHeader                      [55] IMPLICIT SEQUENCE  OF
      GraphicString OPTIONAL,
   additionalAccessNetworkInformation      [56] IMPLICIT OCTET STRING OPTIONAL,
   instanceId                              [57] IMPLICIT OCTET STRING OPTIONAL,
   subscriberEquipmentNumber               [58] IMPLICIT SubscriberEquipmentNumber OPTIONAL,
   list-Of-AccessNetworkInfoChange         [62] IMPLICIT SEQUENCE  OF
      AccessNetworkInfoChange OPTIONAL,
   listOfCalledIdentityChanges             [63] IMPLICIT SEQUENCE  OF
      CalledIdentityChange OPTIONAL,
   cellularNetworkInformation              [64] IMPLICIT OCTET STRING OPTIONAL,
   serviceSpecificInfo                     [100] IMPLICIT SEQUENCE  OF
      ServiceSpecificInfo OPTIONAL,
   requested-Party-Address                 [101] InvolvedParty OPTIONAL,
   list-Of-Called-Asserted-Identity        [102] IMPLICIT SEQUENCE  OF
      InvolvedParty OPTIONAL,
   alternateChargedPartyAddress            [103] IMPLICIT UTF8String OPTIONAL,
   outgoingSessionId                       [104] IMPLICIT GraphicString OPTIONAL,
   initialIMS-Charging-Identifier          [105] IMPLICIT OCTET STRING OPTIONAL,
   list-Of-AccessTransferInformation       [106] IMPLICIT SEQUENCE  OF
      AccessTransferInformation OPTIONAL,
   tADS-Identifier                         [109] IMPLICIT TADIdentifier OPTIONAL,
   vlr-Number                              [110] IMPLICIT OCTET STRING ( SIZE( 1 .. 20 ) ) OPTIONAL,
   msc-Address                             [111] IMPLICIT OCTET STRING ( SIZE( 1 .. 20 ) ) OPTIONAL,
   threeGPPPSDataOffStatus                 [112] IMPLICIT ENUMERATED {
      active      ( 0 ),
      inactive    ( 1 ) } OPTIONAL,
   fEIdentifierList                        [113] IMPLICIT SEQUENCE  OF
      GraphicString OPTIONAL}

ECSCFRecord ::= SET {
   recordType                              [0] IMPLICIT RecordType,
   retransmission                          [1] IMPLICIT NULL OPTIONAL,
   sIP-Method                              [2] IMPLICIT GraphicString OPTIONAL,
   role-of-Node                            [3] IMPLICIT Role-of-Node OPTIONAL,
   nodeAddress                             [4] NodeAddress OPTIONAL,
   session-Id                              [5] IMPLICIT GraphicString OPTIONAL,
   list-Of-Calling-Party-Address           [6] IMPLICIT SEQUENCE  OF
      InvolvedParty OPTIONAL,
   called-Party-Address                    [7] InvolvedParty OPTIONAL,
   serviceRequestTimeStamp                 [9] IMPLICIT OCTET STRING ( SIZE( 9 ) ) OPTIONAL,
   serviceDeliveryStartTimeStamp           [10] IMPLICIT OCTET STRING ( SIZE( 9 ) ) OPTIONAL,
   serviceDeliveryEndTimeStamp             [11] IMPLICIT OCTET STRING ( SIZE( 9 ) ) OPTIONAL,
   recordOpeningTime                       [12] IMPLICIT OCTET STRING ( SIZE( 9 ) ) OPTIONAL,
   recordClosureTime                       [13] IMPLICIT OCTET STRING ( SIZE( 9 ) ) OPTIONAL,
   interOperatorIdentifiers                [14] IMPLICIT SEQUENCE  OF
      InterOperatorIdentifiers OPTIONAL,
   localRecordSequenceNumber               [15] IMPLICIT INTEGER ( 0 .. 4294967295 ) OPTIONAL,
   recordSequenceNumber                    [16] IMPLICIT INTEGER OPTIONAL,
   causeForRecordClosing                   [17] IMPLICIT CauseForRecordClosing OPTIONAL,
   incomplete-CDR-Indication               [18] IMPLICIT Incomplete-CDR-Indication OPTIONAL,
   iMS-Charging-Identifier                 [19] IMPLICIT OCTET STRING OPTIONAL,
   list-Of-SDP-Media-Components            [21] IMPLICIT SEQUENCE  OF
      Media-Components-List OPTIONAL,
   gGSNaddress                             [22] NodeAddress OPTIONAL,
   serviceReasonReturnCode                 [23] IMPLICIT UTF8String OPTIONAL,
   list-Of-Message-Bodies                  [24] IMPLICIT SEQUENCE  OF
      MessageBody OPTIONAL,
   recordExtensions                        [25] IMPLICIT SET  OF
      ManagementExtension OPTIONAL,
   expiresInformation                      [26] IMPLICIT INTEGER OPTIONAL,
   event                                   [28] IMPLICIT UTF8String OPTIONAL,
   accessNetworkInformation                [29] IMPLICIT OCTET STRING OPTIONAL,
   serviceContextID                        [30] IMPLICIT UTF8String OPTIONAL,
   list-of-subscription-ID                 [31] IMPLICIT SEQUENCE  OF
      SubscriptionID OPTIONAL,
   list-Of-Early-SDP-Media-Components      [32] IMPLICIT SEQUENCE  OF
      Early-Media-Components-List OPTIONAL,
   iMSCommunicationServiceIdentifier       [33] IMPLICIT OCTET STRING OPTIONAL,
   sessionPriority                         [36] IMPLICIT SessionPriority OPTIONAL,
   serviceRequestTimeStampFraction         [37] IMPLICIT INTEGER ( 0 .. 999 ) OPTIONAL,
   serviceDeliveryStartTimeStampFraction   [38] IMPLICIT INTEGER ( 0 .. 999 ) OPTIONAL,
   serviceDeliveryEndTimeStampFraction     [39] IMPLICIT INTEGER ( 0 .. 999 ) OPTIONAL,
   applicationServersInformation           [40] IMPLICIT SEQUENCE  OF
      ApplicationServersInformation OPTIONAL,
   requested-Party-Address                 [41] InvolvedParty OPTIONAL,
   list-Of-Called-Asserted-Identity        [42] IMPLICIT SEQUENCE  OF
      InvolvedParty OPTIONAL,
   userLocationInformation                 [47] IMPLICIT OCTET STRING OPTIONAL,
   mSTimeZone                              [48] IMPLICIT OCTET STRING ( SIZE( 2 ) ) OPTIONAL,
   fromAddress                             [51] IMPLICIT OCTET STRING OPTIONAL,
   transit-IOI-Lists                       [53] IMPLICIT SEQUENCE  OF
      GraphicString OPTIONAL,
   listOfReasonHeader                      [55] IMPLICIT SEQUENCE  OF
      GraphicString OPTIONAL,
   additionalAccessNetworkInformation      [56] IMPLICIT OCTET STRING OPTIONAL,
   list-Of-AccessNetworkInfoChange         [62] IMPLICIT SEQUENCE  OF
      AccessNetworkInfoChange OPTIONAL,
   listOfCalledIdentityChanges             [63] IMPLICIT SEQUENCE  OF
      CalledIdentityChange OPTIONAL,
   cellularNetworkInformation              [64] IMPLICIT OCTET STRING OPTIONAL,
   fEIdentifierList                        [65] IMPLICIT SEQUENCE  OF
      GraphicString OPTIONAL}

IBCFRecord ::= SET {
   recordType                              [0] IMPLICIT RecordType,
   retransmission                          [1] IMPLICIT NULL OPTIONAL,
   sIP-Method                              [2] IMPLICIT GraphicString OPTIONAL,
   role-of-Node                            [3] IMPLICIT Role-of-Node OPTIONAL,
   nodeAddress                             [4] NodeAddress OPTIONAL,
   session-Id                              [5] IMPLICIT GraphicString OPTIONAL,
   list-Of-Calling-Party-Address           [6] IMPLICIT SEQUENCE  OF
      InvolvedParty OPTIONAL,
   called-Party-Address                    [7] InvolvedParty OPTIONAL,
   privateUserID                           [8] IMPLICIT GraphicString OPTIONAL,
   serviceRequestTimeStamp                 [9] IMPLICIT OCTET STRING ( SIZE( 9 ) ) OPTIONAL,
   serviceDeliveryStartTimeStamp           [10] IMPLICIT OCTET STRING ( SIZE( 9 ) ) OPTIONAL,
   serviceDeliveryEndTimeStamp             [11] IMPLICIT OCTET STRING ( SIZE( 9 ) ) OPTIONAL,
   recordOpeningTime                       [12] IMPLICIT OCTET STRING ( SIZE( 9 ) ) OPTIONAL,
   recordClosureTime                       [13] IMPLICIT OCTET STRING ( SIZE( 9 ) ) OPTIONAL,
   interOperatorIdentifiers                [14] IMPLICIT InterOperatorIdentifiers OPTIONAL,
   localRecordSequenceNumber               [15] IMPLICIT INTEGER ( 0 .. 4294967295 ) OPTIONAL,
   recordSequenceNumber                    [16] IMPLICIT INTEGER OPTIONAL,
   causeForRecordClosing                   [17] IMPLICIT CauseForRecordClosing OPTIONAL,
   incomplete-CDR-Indication               [18] IMPLICIT Incomplete-CDR-Indication OPTIONAL,
   iMS-Charging-Identifier                 [19] IMPLICIT OCTET STRING OPTIONAL,
   list-Of-SDP-Media-Components            [21] IMPLICIT SEQUENCE  OF
      Media-Components-List OPTIONAL,
   gGSNaddress                             [22] NodeAddress OPTIONAL,
   serviceReasonReturnCode                 [23] IMPLICIT UTF8String OPTIONAL,
   list-Of-Message-Bodies                  [24] IMPLICIT SEQUENCE  OF
      MessageBody OPTIONAL,
   recordExtensions                        [25] IMPLICIT SET  OF
      ManagementExtension OPTIONAL,
   expiresInformation                      [26] IMPLICIT INTEGER OPTIONAL,
   event                                   [28] IMPLICIT UTF8String OPTIONAL,
   accessNetworkInformation                [29] IMPLICIT OCTET STRING OPTIONAL,
   serviceContextID                        [30] IMPLICIT UTF8String OPTIONAL,
   list-of-subscription-ID                 [31] IMPLICIT SEQUENCE  OF
      SubscriptionID OPTIONAL,
   list-Of-Early-SDP-Media-Components      [32] IMPLICIT SEQUENCE  OF
      Early-Media-Components-List OPTIONAL,
   iMSCommunicationServiceIdentifier       [33] IMPLICIT OCTET STRING OPTIONAL,
   sessionPriority                         [36] IMPLICIT SessionPriority OPTIONAL,
   serviceRequestTimeStampFraction         [37] IMPLICIT INTEGER ( 0 .. 999 ) OPTIONAL,
   serviceDeliveryStartTimeStampFraction   [38] IMPLICIT INTEGER ( 0 .. 999 ) OPTIONAL,
   serviceDeliveryEndTimeStampFraction     [39] IMPLICIT INTEGER ( 0 .. 999 ) OPTIONAL,
   list-of-Requested-Party-Address         [41] IMPLICIT SEQUENCE  OF
      InvolvedParty OPTIONAL,
   list-Of-Called-Asserted-Identity        [42] IMPLICIT SEQUENCE  OF
      InvolvedParty OPTIONAL,
   transit-IOI-List                        [45] IMPLICIT GraphicString OPTIONAL,
   nNI-Information                         [46] IMPLICIT SEQUENCE  OF
      NNI-Information OPTIONAL,
   userLocationInformation                 [47] IMPLICIT OCTET STRING OPTIONAL,
   mSTimeZone                              [48] IMPLICIT OCTET STRING ( SIZE( 2 ) ) OPTIONAL,
   fromAddress                             [51] IMPLICIT OCTET STRING OPTIONAL,
   listOfReasonHeader                      [55] IMPLICIT SEQUENCE  OF
      GraphicString OPTIONAL,
   additionalAccessNetworkInformation      [56] IMPLICIT OCTET STRING OPTIONAL,
   routeHeaderReceived                     [59] IMPLICIT OCTET STRING OPTIONAL,
   list-Of-AccessNetworkInfoChange         [62] IMPLICIT SEQUENCE  OF
      AccessNetworkInfoChange OPTIONAL,
   cellularNetworkInformation              [64] IMPLICIT OCTET STRING OPTIONAL,
   initialIMS-Charging-Identifier          [105] IMPLICIT OCTET STRING OPTIONAL,
   list-Of-AccessTransferInformation       [106] IMPLICIT SEQUENCE  OF
      AccessTransferInformation OPTIONAL,
   fEIdentifierList                        [107] IMPLICIT SEQUENCE  OF
      GraphicString OPTIONAL}

TRFRecord  ::= SET {
   recordType                              [0] IMPLICIT RecordType,
   retransmission                          [1] IMPLICIT NULL OPTIONAL,
   sIP-Method                              [2] IMPLICIT GraphicString OPTIONAL,
   role-of-Node                            [3] IMPLICIT Role-of-Node OPTIONAL,
   nodeAddress                             [4] NodeAddress OPTIONAL,
   session-Id                              [5] IMPLICIT GraphicString OPTIONAL,
   list-Of-Calling-Party-Address           [6] IMPLICIT SEQUENCE  OF
      InvolvedParty OPTIONAL,
   called-Party-Address                    [7] InvolvedParty OPTIONAL,
   serviceRequestTimeStamp                 [9] IMPLICIT OCTET STRING ( SIZE( 9 ) ) OPTIONAL,
   serviceDeliveryStartTimeStamp           [10] IMPLICIT OCTET STRING ( SIZE( 9 ) ) OPTIONAL,
   serviceDeliveryEndTimeStamp             [11] IMPLICIT OCTET STRING ( SIZE( 9 ) ) OPTIONAL,
   recordOpeningTime                       [12] IMPLICIT OCTET STRING ( SIZE( 9 ) ) OPTIONAL,
   recordClosureTime                       [13] IMPLICIT OCTET STRING ( SIZE( 9 ) ) OPTIONAL,
   interOperatorIdentifiers                [14] IMPLICIT SEQUENCE  OF
      InterOperatorIdentifiers OPTIONAL,
   localRecordSequenceNumber               [15] IMPLICIT INTEGER ( 0 .. 4294967295 ) OPTIONAL,
   recordSequenceNumber                    [16] IMPLICIT INTEGER OPTIONAL,
   causeForRecordClosing                   [17] IMPLICIT CauseForRecordClosing OPTIONAL,
   incomplete-CDR-Indication               [18] IMPLICIT Incomplete-CDR-Indication OPTIONAL,
   iMS-Charging-Identifier                 [19] IMPLICIT OCTET STRING OPTIONAL,
   list-Of-SDP-Media-Components            [21] IMPLICIT SEQUENCE  OF
      Media-Components-List OPTIONAL,
   serviceReasonReturnCode                 [23] IMPLICIT UTF8String OPTIONAL,
   list-Of-Message-Bodies                  [24] IMPLICIT SEQUENCE  OF
      MessageBody OPTIONAL,
   recordExtensions                        [25] IMPLICIT SET  OF
      ManagementExtension OPTIONAL,
   expiresInformation                      [26] IMPLICIT INTEGER OPTIONAL,
   event                                   [28] IMPLICIT UTF8String OPTIONAL,
   serviceContextID                        [30] IMPLICIT UTF8String OPTIONAL,
   list-of-subscription-ID                 [31] IMPLICIT SEQUENCE  OF
      SubscriptionID OPTIONAL,
   list-Of-Early-SDP-Media-Components      [32] IMPLICIT SEQUENCE  OF
      Early-Media-Components-List OPTIONAL,
   iMSCommunicationServiceIdentifier       [33] IMPLICIT OCTET STRING OPTIONAL,
   numberPortabilityRouting                [34] IMPLICIT GraphicString OPTIONAL,
   carrierSelectRouting                    [35] IMPLICIT GraphicString OPTIONAL,
   sessionPriority                         [36] IMPLICIT SessionPriority OPTIONAL,
   serviceRequestTimeStampFraction         [37] IMPLICIT INTEGER ( 0 .. 999 ) OPTIONAL,
   serviceDeliveryStartTimeStampFraction   [38] IMPLICIT INTEGER ( 0 .. 999 ) OPTIONAL,
   serviceDeliveryEndTimeStampFraction     [39] IMPLICIT INTEGER ( 0 .. 999 ) OPTIONAL,
   applicationServersInformation           [40] IMPLICIT SEQUENCE  OF
      ApplicationServersInformation OPTIONAL,
   requested-Party-Address                 [41] InvolvedParty OPTIONAL,
   list-Of-Called-Asserted-Identity        [42] IMPLICIT SEQUENCE  OF
      InvolvedParty OPTIONAL,
   nNI-Information                         [46] IMPLICIT SEQUENCE  OF
      NNI-Information OPTIONAL,
   userLocationInformation                 [47] IMPLICIT OCTET STRING OPTIONAL,
   mSTimeZone                              [48] IMPLICIT OCTET STRING ( SIZE( 2 ) ) OPTIONAL,
   transit-IOI-Lists                       [53] IMPLICIT SEQUENCE  OF
      GraphicString OPTIONAL,
   listOfReasonHeader                      [55] IMPLICIT SEQUENCE  OF
      GraphicString OPTIONAL,
   routeHeaderReceived                     [59] IMPLICIT OCTET STRING OPTIONAL,
   listOfCalledIdentityChanges             [63] IMPLICIT SEQUENCE  OF
      CalledIdentityChange OPTIONAL,
   fEIdentifierList                        [64] IMPLICIT SEQUENCE  OF
      GraphicString OPTIONAL}

ATCFRecord ::= SET {
   recordType                              [0] IMPLICIT RecordType,
   retransmission                          [1] IMPLICIT NULL OPTIONAL,
   sIP-Method                              [2] IMPLICIT GraphicString OPTIONAL,
   role-of-Node                            [3] IMPLICIT Role-of-Node OPTIONAL,
   nodeAddress                             [4] NodeAddress OPTIONAL,
   session-Id                              [5] IMPLICIT GraphicString OPTIONAL,
   list-Of-Calling-Party-Address           [6] IMPLICIT SEQUENCE  OF
      InvolvedParty OPTIONAL,
   called-Party-Address                    [7] InvolvedParty OPTIONAL,
   privateUserID                           [8] IMPLICIT GraphicString OPTIONAL,
   serviceRequestTimeStamp                 [9] IMPLICIT OCTET STRING ( SIZE( 9 ) ) OPTIONAL,
   serviceDeliveryStartTimeStamp           [10] IMPLICIT OCTET STRING ( SIZE( 9 ) ) OPTIONAL,
   serviceDeliveryEndTimeStamp             [11] IMPLICIT OCTET STRING ( SIZE( 9 ) ) OPTIONAL,
   recordOpeningTime                       [12] IMPLICIT OCTET STRING ( SIZE( 9 ) ) OPTIONAL,
   recordClosureTime                       [13] IMPLICIT OCTET STRING ( SIZE( 9 ) ) OPTIONAL,
   interOperatorIdentifiers                [14] IMPLICIT InterOperatorIdentifiers OPTIONAL,
   localRecordSequenceNumber               [15] IMPLICIT INTEGER ( 0 .. 4294967295 ) OPTIONAL,
   recordSequenceNumber                    [16] IMPLICIT INTEGER OPTIONAL,
   causeForRecordClosing                   [17] IMPLICIT CauseForRecordClosing OPTIONAL,
   incomplete-CDR-Indication               [18] IMPLICIT Incomplete-CDR-Indication OPTIONAL,
   iMS-Charging-Identifier                 [19] IMPLICIT OCTET STRING OPTIONAL,
   list-Of-SDP-Media-Components            [21] IMPLICIT SEQUENCE  OF
      Media-Components-List OPTIONAL,
   gGSNaddress                             [22] NodeAddress OPTIONAL,
   serviceReasonReturnCode                 [23] IMPLICIT UTF8String OPTIONAL,
   list-Of-Message-Bodies                  [24] IMPLICIT SEQUENCE  OF
      MessageBody OPTIONAL,
   recordExtensions                        [25] IMPLICIT SET  OF
      ManagementExtension OPTIONAL,
   expiresInformation                      [26] IMPLICIT INTEGER OPTIONAL,
   event                                   [28] IMPLICIT UTF8String OPTIONAL,
   accessNetworkInformation                [29] IMPLICIT OCTET STRING OPTIONAL,
   serviceContextID                        [30] IMPLICIT UTF8String OPTIONAL,
   list-of-subscription-ID                 [31] IMPLICIT SEQUENCE  OF
      SubscriptionID OPTIONAL,
   list-Of-Early-SDP-Media-Components      [32] IMPLICIT SEQUENCE  OF
      Early-Media-Components-List OPTIONAL,
   iMSCommunicationServiceIdentifier       [33] IMPLICIT OCTET STRING OPTIONAL,
   sessionPriority                         [36] IMPLICIT SessionPriority OPTIONAL,
   serviceRequestTimeStampFraction         [37] IMPLICIT INTEGER ( 0 .. 999 ) OPTIONAL,
   serviceDeliveryStartTimeStampFraction   [38] IMPLICIT INTEGER ( 0 .. 999 ) OPTIONAL,
   serviceDeliveryEndTimeStampFraction     [39] IMPLICIT INTEGER ( 0 .. 999 ) OPTIONAL,
   list-of-Requested-Party-Address         [41] IMPLICIT SEQUENCE  OF
      InvolvedParty OPTIONAL,
   list-Of-Called-Asserted-Identity        [42] IMPLICIT SEQUENCE  OF
      InvolvedParty OPTIONAL,
   nNI-Information                         [46] IMPLICIT NNI-Information OPTIONAL,
   userLocationInformation                 [47] IMPLICIT OCTET STRING OPTIONAL,
   mSTimeZone                              [48] IMPLICIT OCTET STRING ( SIZE( 2 ) ) OPTIONAL,
   fromAddress                             [51] IMPLICIT OCTET STRING OPTIONAL,
   listOfReasonHeader                      [55] IMPLICIT SEQUENCE  OF
      GraphicString OPTIONAL,
   additionalAccessNetworkInformation      [56] IMPLICIT OCTET STRING OPTIONAL,
   routeHeaderReceived                     [59] IMPLICIT OCTET STRING OPTIONAL,
   routeHeaderTransmitted                  [60] IMPLICIT OCTET STRING OPTIONAL,
   list-Of-AccessNetworkInfoChange         [62] IMPLICIT SEQUENCE  OF
      AccessNetworkInfoChange OPTIONAL,
   listOfCalledIdentityChanges             [63] IMPLICIT SEQUENCE  OF
      CalledIdentityChange OPTIONAL,
   cellularNetworkInformation              [64] IMPLICIT OCTET STRING OPTIONAL,
   initialIMS-Charging-Identifier          [105] IMPLICIT OCTET STRING OPTIONAL,
   list-Of-AccessTransferInformation       [106] IMPLICIT SEQUENCE  OF
      AccessTransferInformation OPTIONAL,
   fEIdentifierList                        [107] IMPLICIT SEQUENCE  OF
      GraphicString OPTIONAL}

TFRecord   ::= SET {
   recordType                              [0] IMPLICIT RecordType,
   retransmission                          [1] IMPLICIT NULL OPTIONAL,
   sIP-Method                              [2] IMPLICIT GraphicString OPTIONAL,
   role-of-Node                            [3] IMPLICIT Role-of-Node OPTIONAL,
   nodeAddress                             [4] NodeAddress OPTIONAL,
   session-Id                              [5] IMPLICIT GraphicString OPTIONAL,
   list-Of-Calling-Party-Address           [6] IMPLICIT SEQUENCE  OF
      InvolvedParty OPTIONAL,
   called-Party-Address                    [7] InvolvedParty OPTIONAL,
   serviceRequestTimeStamp                 [9] IMPLICIT OCTET STRING ( SIZE( 9 ) ) OPTIONAL,
   serviceDeliveryStartTimeStamp           [10] IMPLICIT OCTET STRING ( SIZE( 9 ) ) OPTIONAL,
   serviceDeliveryEndTimeStamp             [11] IMPLICIT OCTET STRING ( SIZE( 9 ) ) OPTIONAL,
   recordOpeningTime                       [12] IMPLICIT OCTET STRING ( SIZE( 9 ) ) OPTIONAL,
   recordClosureTime                       [13] IMPLICIT OCTET STRING ( SIZE( 9 ) ) OPTIONAL,
   interOperatorIdentifiers                [14] IMPLICIT SEQUENCE  OF
      InterOperatorIdentifiers OPTIONAL,
   localRecordSequenceNumber               [15] IMPLICIT INTEGER ( 0 .. 4294967295 ) OPTIONAL,
   recordSequenceNumber                    [16] IMPLICIT INTEGER OPTIONAL,
   causeForRecordClosing                   [17] IMPLICIT CauseForRecordClosing OPTIONAL,
   incomplete-CDR-Indication               [18] IMPLICIT Incomplete-CDR-Indication OPTIONAL,
   iMS-Charging-Identifier                 [19] IMPLICIT OCTET STRING OPTIONAL,
   list-Of-SDP-Media-Components            [21] IMPLICIT SEQUENCE  OF
      Media-Components-List OPTIONAL,
   serviceReasonReturnCode                 [23] IMPLICIT UTF8String OPTIONAL,
   list-Of-Message-Bodies                  [24] IMPLICIT SEQUENCE  OF
      MessageBody OPTIONAL,
   recordExtensions                        [25] IMPLICIT SET  OF
      ManagementExtension OPTIONAL,
   expiresInformation                      [26] IMPLICIT INTEGER OPTIONAL,
   event                                   [28] IMPLICIT UTF8String OPTIONAL,
   serviceContextID                        [30] IMPLICIT UTF8String OPTIONAL,
   list-Of-Early-SDP-Media-Components      [32] IMPLICIT SEQUENCE  OF
      Early-Media-Components-List OPTIONAL,
   iMSCommunicationServiceIdentifier       [33] IMPLICIT OCTET STRING OPTIONAL,
   numberPortabilityRouting                [34] IMPLICIT GraphicString OPTIONAL,
   carrierSelectRouting                    [35] IMPLICIT GraphicString OPTIONAL,
   sessionPriority                         [36] IMPLICIT SessionPriority OPTIONAL,
   serviceRequestTimeStampFraction         [37] IMPLICIT INTEGER ( 0 .. 999 ) OPTIONAL,
   serviceDeliveryStartTimeStampFraction   [38] IMPLICIT INTEGER ( 0 .. 999 ) OPTIONAL,
   serviceDeliveryEndTimeStampFraction     [39] IMPLICIT INTEGER ( 0 .. 999 ) OPTIONAL,
   applicationServersInformation           [40] IMPLICIT SEQUENCE  OF
      ApplicationServersInformation OPTIONAL,
   requested-Party-Address                 [41] InvolvedParty OPTIONAL,
   list-Of-Called-Asserted-Identity        [42] IMPLICIT SEQUENCE  OF
      InvolvedParty OPTIONAL,
   nNI-Information                         [46] IMPLICIT NNI-Information OPTIONAL,
   fromAddress                             [51] IMPLICIT OCTET STRING OPTIONAL,
   transit-IOI-Lists                       [53] IMPLICIT SEQUENCE  OF
      GraphicString OPTIONAL,
   listOfReasonHeader                      [55] IMPLICIT SEQUENCE  OF
      GraphicString OPTIONAL,
   routeHeaderReceived                     [59] IMPLICIT OCTET STRING OPTIONAL,
   routeHeaderTransmitted                  [60] IMPLICIT OCTET STRING OPTIONAL,
   listOfCalledIdentityChanges             [63] IMPLICIT SEQUENCE  OF
      CalledIdentityChange OPTIONAL,
   fEIdentifierList                        [64] IMPLICIT SEQUENCE  OF
      GraphicString OPTIONAL}

AccessCorrelationID ::= CHOICE {
   gPRS-Charging-Id                    [2] IMPLICIT INTEGER ( 0 .. 4294967295 ),
   accessNetworkChargingIdentifier     [4] IMPLICIT GraphicString}

AccessNetworkInfoChange ::= SEQUENCE {
   accessNetworkInformation             [0] IMPLICIT OCTET STRING OPTIONAL,
   additionalAccessNetworkInformation   [1] IMPLICIT OCTET STRING OPTIONAL,
   accessChangeTime                     [2] IMPLICIT OCTET STRING ( SIZE( 9 ) ) OPTIONAL,
   cellularNetworkInformation           [3] IMPLICIT OCTET STRING OPTIONAL}

AccessTransferType ::= ENUMERATED {
   pSToCS      ( 0 ),
   cSToPS      ( 1 ),
   pSToPS      ( 2 ),
   cSToCS      ( 3 ) }

AccessTransferInformation ::= SEQUENCE {
   accessTransferType                   [0] IMPLICIT AccessTransferType OPTIONAL,
   accessNetworkInformation             [1] IMPLICIT OCTET STRING OPTIONAL,
   additionalAccessNetworkInformation   [2] IMPLICIT OCTET STRING OPTIONAL,
   inter-UE-Transfer                    [3] IMPLICIT NULL OPTIONAL,
   relatedICID                          [4] IMPLICIT OCTET STRING OPTIONAL,
   relatedICIDGenerationNode            [5] NodeAddress OPTIONAL,
   accessTransferTime                   [6] IMPLICIT OCTET STRING ( SIZE( 9 ) ) OPTIONAL,
   subscriberEquipmentNumber            [7] IMPLICIT SubscriberEquipmentNumber OPTIONAL,
   instanceId                           [8] IMPLICIT OCTET STRING OPTIONAL,
   cellularNetworkInformation           [9] IMPLICIT OCTET STRING OPTIONAL}

ACRInterimLost ::= ENUMERATED {
   no          ( 0 ),
   yes         ( 1 ),
   unknown     ( 2 ) }

AoCCostInformation ::= SEQUENCE {
   accumulatedCost   [0] IMPLICIT REAL,
   incrementalCost   [1] IMPLICIT REAL,
   currencyCode      [2] IMPLICIT INTEGER}

AoCInformation ::= SET {
   tariffInformation    [0] IMPLICIT TariffInformation OPTIONAL,
   aoCCostInformation   [1] IMPLICIT AoCCostInformation OPTIONAL}

ApplicationServersInformation ::= SEQUENCE {
   applicationServersInvolved         [0] NodeAddress OPTIONAL,
   applicationProvidedCalledParties   [1] IMPLICIT SEQUENCE  OF
      InvolvedParty OPTIONAL,
   sTatus                             [2] IMPLICIT Status OPTIONAL}

CalledIdentityChange ::= SEQUENCE {
   calledIdentity   [0] InvolvedParty OPTIONAL,
   changeTime       [1] IMPLICIT OCTET STRING ( SIZE( 9 ) ) OPTIONAL}

CarrierSelectRouting ::= GraphicString

CauseForRecordClosing ::= ENUMERATED {
   serviceDeliveryEndSuccessfully    ( 0 ),
   unSuccessfulServiceDelivery       ( 1 ),
   timeLimit                         ( 3 ),
   serviceChange                     ( 4 ),
   managementIntervention            ( 5 ) }

Early-Media-Components-List ::= SEQUENCE {
   sDP-Offer-Timestamp       [0] IMPLICIT OCTET STRING ( SIZE( 9 ) ) OPTIONAL,
   sDP-Answer-Timestamp      [1] IMPLICIT OCTET STRING ( SIZE( 9 ) ) OPTIONAL,
   sDP-Media-Components      [2] IMPLICIT SEQUENCE  OF
      SDP-Media-Component OPTIONAL,
   mediaInitiatorFlag        [3] IMPLICIT NULL OPTIONAL,
   sDP-Session-Description   [4] IMPLICIT SEQUENCE  OF
      GraphicString OPTIONAL,
   sDP-Type                  [5] IMPLICIT SDP-Type OPTIONAL}

FEIdentifierList ::= SEQUENCE  OF
   GraphicString

IMS-Charging-Identifier ::= OCTET STRING

IMSCommunicationServiceIdentifier ::= OCTET STRING

Incomplete-CDR-Indication ::= SET {
   aCRStartLost     [0] IMPLICIT BOOLEAN,
   aCRInterimLost   [1] IMPLICIT ACRInterimLost,
   aCRStopLost      [2] IMPLICIT BOOLEAN}

InterOperatorIdentifierList ::= SEQUENCE  OF
   InterOperatorIdentifiers

InterOperatorIdentifiers ::= SEQUENCE {
   originatingIOI   [0] IMPLICIT GraphicString OPTIONAL,
   terminatingIOI   [1] IMPLICIT GraphicString OPTIONAL}

ISUPCause  ::= SEQUENCE {
   iSUPCauseLocation      [0] IMPLICIT INTEGER OPTIONAL,
   iSUPCauseValue         [1] IMPLICIT INTEGER OPTIONAL,
   iSUPCauseDiagnostics   [2] IMPLICIT OCTET STRING OPTIONAL}

ListOfInvolvedParties ::= SEQUENCE  OF
   InvolvedParty

ListOfReasonHeader ::= SEQUENCE  OF
   GraphicString

Media-Components-List ::= SEQUENCE {
   sIP-Request-Timestamp             [0] IMPLICIT OCTET STRING ( SIZE( 9 ) ) OPTIONAL,
   sIP-Response-Timestamp            [1] IMPLICIT OCTET STRING ( SIZE( 9 ) ) OPTIONAL,
   sDP-Media-Components              [2] IMPLICIT SEQUENCE  OF
      SDP-Media-Component OPTIONAL,
   mediaInitiatorFlag                [3] IMPLICIT NULL OPTIONAL,
   sDP-Session-Description           [4] IMPLICIT SEQUENCE  OF
      GraphicString OPTIONAL,
   mediaInitiatorParty               [5] InvolvedParty OPTIONAL,
   sIP-Request-Timestamp-Fraction    [6] IMPLICIT INTEGER ( 0 .. 999 ) OPTIONAL,
   sIP-Response-Timestamp-Fraction   [7] IMPLICIT INTEGER ( 0 .. 999 ) OPTIONAL,
   sDP-Type                          [8] IMPLICIT SDP-Type OPTIONAL}

MessageBody ::= SEQUENCE {
   content-Type          [0] IMPLICIT GraphicString,
   content-Disposition   [1] IMPLICIT GraphicString OPTIONAL,
   content-Length        [2] IMPLICIT INTEGER,
   originator            [3] InvolvedParty OPTIONAL}

Milliseconds ::= INTEGER ( 0 .. 999 )

NNI-Information ::= SEQUENCE {
   sessionDirection       [0] IMPLICIT SessionDirection OPTIONAL,
   nNIType                [1] IMPLICIT NNIType OPTIONAL,
   relationshipMode       [2] IMPLICIT RelationshipMode OPTIONAL,
   neighbourNodeAddress   [3] ServedPartyIPAddress OPTIONAL}

NNIType    ::= ENUMERATED {
   non-roaming                 ( 0 ),
   roaming-without-loopback    ( 1 ),
   roaming-with-loopback       ( 2 ) }

NumberPortabilityRouting ::= GraphicString

RateElement ::= SEQUENCE {
   unitType             [0] IMPLICIT INTEGER,
   unitValue            [1] IMPLICIT REAL,
   unitCost             [2] IMPLICIT REAL,
   unitQuotaThreshold   [3] IMPLICIT REAL}

RealTimeTariffInformation ::= CHOICE {
   tariffInformation     [0] IMPLICIT TariffInformation,
   tariffXml             [1] IMPLICIT UTF8String}

ReasonHeaderInformation ::= GraphicString

RelationshipMode ::= ENUMERATED {
   trusted        ( 0 ),
   non-trusted    ( 1 ) }

Role-of-Node ::= ENUMERATED {
   originating    ( 0 ),
   terminating    ( 1 ) }

S-CSCF-Information ::= SEQUENCE {
   mandatoryCapabilities   [0] IMPLICIT SEQUENCE  OF
      GraphicString OPTIONAL,
   optionalCapabilities    [1] IMPLICIT SEQUENCE  OF
      GraphicString OPTIONAL,
   serverName              [2] IMPLICIT GraphicString OPTIONAL}

SDP-Media-Component ::= SEQUENCE {
   sDP-Media-Name                 [0] IMPLICIT GraphicString OPTIONAL,
   sDP-Media-Descriptions         [1] IMPLICIT SEQUENCE  OF
      GraphicString OPTIONAL,
   accessCorrelationID            AccessCorrelationID OPTIONAL,
   localGWInsertedIndication      [5] IMPLICIT BOOLEAN OPTIONAL,
   iPRealmDefaultIndication       [6] IMPLICIT BOOLEAN OPTIONAL,
   transcoderInsertedIndication   [7] IMPLICIT BOOLEAN OPTIONAL}

SDP-Media-Description ::= SEQUENCE  OF
   GraphicString

ServedPartyIPAddress ::= CHOICE {
   iPBinaryAddress              IPBinaryAddress,
   iPTextRepresentedAddress     IPTextRepresentedAddress}

Service-Id ::= GraphicString

SessionDirection ::= ENUMERATED {
   inbound     ( 0 ),
   outbound    ( 1 ) }

SessionPriority ::= ENUMERATED {
   pRIORITY-0    ( 0 ),
   pRIORITY-1    ( 1 ),
   pRIORITY-2    ( 2 ),
   pRIORITY-3    ( 3 ),
   pRIORITY-4    ( 4 ) }

SIP-Method ::= GraphicString

SDP-Type   ::= ENUMERATED {
   sDP-offer     ( 0 ),
   sDP-answer    ( 1 ) }

Status     ::= ENUMERATED {
   fourxx      ( 0 ),
   fivexx      ( 1 ),
   time-out    ( 2 ) }

TADIdentifier ::= ENUMERATED {
   cS          ( 0 ),
   pS          ( 1 ) }

TariffInformation ::= SEQUENCE {
   currencyCode   [0] IMPLICIT INTEGER,
   scaleFactor    [1] IMPLICIT REAL,
   rateElements   [2] IMPLICIT SEQUENCE  OF
      RateElement OPTIONAL}

TransitIOILists ::= SEQUENCE  OF
   GraphicString

TransmissionMedium ::= SEQUENCE {
   tMR        [0] IMPLICIT OCTET STRING ( SIZE( 1 ) ) OPTIONAL,
   tMU        [1] IMPLICIT OCTET STRING ( SIZE( 1 ) ) OPTIONAL}

TrunkGroupID ::= CHOICE {
   incoming     [0] IMPLICIT GraphicString,
   outgoing     [1] IMPLICIT GraphicString}


-- X.721 DMI-EXTENSION. The set is the standard form of the original
-- extensible empty table constraint ({, ...}) and does not change BER.
DMI-EXTENSION ::= CLASS {
    &id     OBJECT IDENTIFIER UNIQUE,
    &Value
}
WITH SYNTAX {
    TYPE &Value
    ID &id
}

ManagementExtensionSet DMI-EXTENSION ::= {...}

END
