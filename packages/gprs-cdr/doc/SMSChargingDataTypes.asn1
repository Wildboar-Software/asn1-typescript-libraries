-- Modified by Jonathan M. Wilbur to fix invalid syntax.
--      Expanded ASN1 Module 'SMSChargingDataTypes'
--SIEMENS ASN.1 Compiler         R6.31  (Production_6.31)
--            Date: 2020-07-10 Time: 16:17:14

SMSChargingDataTypes
{itu-t(0) identified-organization(4) etsi(0) mobileDomain(0) charging(5)
smsChargingDataTypes(10) asn1Module(0) version2(1)}
DEFINITIONS
::=
BEGIN

RecordType ::= INTEGER {
   moCallRecord              ( 0 ),
   mtCallRecord              ( 1 ),
   roamingRecord             ( 2 ),
   incGatewayRecord          ( 3 ),
   outGatewayRecord          ( 4 ),
   transitCallRecord         ( 5 ),
   moSMSRecord               ( 6 ),
   mtSMSRecord               ( 7 ),
   moSMSIWRecord             ( 8 ),
   mtSMSGWRecord             ( 9 ),
   ssActionRecord            ( 10 ),
   hlrIntRecord              ( 11 ),
   locUpdateHLRRecord        ( 12 ),
   locUpdateVLRRecord        ( 13 ),
   commonEquipRecord         ( 14 ),
   moTraceRecord             ( 15 ),
   mtTraceRecord             ( 16 ),
   termCAMELRecord           ( 17 ),
   sgsnPDPRecord             ( 18 ),
   sgsnMMRecord              ( 20 ),
   sgsnSMORecord             ( 21 ),
   sgsnSMTRecord             ( 22 ),
   mtLCSRecord               ( 23 ),
   moLCSRecord               ( 24 ),
   niLCSRecord               ( 25 ),
   sgsnMTLCSRecord           ( 26 ),
   sgsnMOLCSRecord           ( 27 ),
   sgsnNILCSRecord           ( 28 ),
   mMO1SRecord               ( 30 ),
   mMO4FRqRecord             ( 31 ),
   mMO4FRsRecord             ( 32 ),
   mMO4DRecord               ( 33 ),
   mMO1DRecord               ( 34 ),
   mMO4RRecord               ( 35 ),
   mMO1RRecord               ( 36 ),
   mMOMDRecord               ( 37 ),
   mMR4FRecord               ( 38 ),
   mMR1NRqRecord             ( 39 ),
   mMR1NRsRecord             ( 40 ),
   mMR1RtRecord              ( 41 ),
   mMR1AFRecord              ( 42 ),
   mMR4DRqRecord             ( 43 ),
   mMR4DRsRecord             ( 44 ),
   mMR1RRRecord              ( 45 ),
   mMR4RRqRecord             ( 46 ),
   mMR4RRsRecord             ( 47 ),
   mMRMDRecord               ( 48 ),
   mMFRecord                 ( 49 ),
   mMBx1SRecord              ( 50 ),
   mMBx1VRecord              ( 51 ),
   mMBx1URecord              ( 52 ),
   mMBx1DRecord              ( 53 ),
   mM7SRecord                ( 54 ),
   mM7DRqRecord              ( 55 ),
   mM7DRsRecord              ( 56 ),
   mM7CRecord                ( 57 ),
   mM7RRecord                ( 58 ),
   mM7DRRqRecord             ( 59 ),
   mM7DRRsRecord             ( 60 ),
   mM7RRqRecord              ( 61 ),
   mM7RRsRecord              ( 62 ),
   sCSCFRecord               ( 63 ),
   pCSCFRecord               ( 64 ),
   iCSCFRecord               ( 65 ),
   mRFCRecord                ( 66 ),
   mGCFRecord                ( 67 ),
   bGCFRecord                ( 68 ),
   aSRecord                  ( 69 ),
   eCSCFRecord               ( 70 ),
   iBCFRecord                ( 82 ),
   tRFRecord                 ( 89 ),
   tFRecord                  ( 90 ),
   aTCFRecord                ( 91 ),
   lCSGMORecord              ( 71 ),
   lCSRGMTRecord             ( 72 ),
   lCSHGMTRecord             ( 73 ),
   lCSVGMTRecord             ( 74 ),
   lCSGNIRecord              ( 75 ),
   sgsnMBMSRecord            ( 76 ),
   ggsnMBMSRecord            ( 77 ),
   gwMBMSRecord              ( 86 ),
   sUBBMSCRecord             ( 78 ),
   cONTENTBMSCRecord         ( 79 ),
   pPFRecord                 ( 80 ),
   cPFRecord                 ( 81 ),
   sGWRecord                 ( 84 ),
   pGWRecord                 ( 85 ),
   tDFRecord                 ( 92 ),
   iPERecord                 ( 95 ),
   ePDGRecord                ( 96 ),
   tWAGRecord                ( 97 ),
   mMTelRecord               ( 83 ),
   mSCsRVCCRecord            ( 87 ),
   mMTRFRecord               ( 88 ),
   iCSRegisterRecord         ( 99 ),
   sCSMORecord               ( 93 ),
   sCSMTRecord               ( 94 ),
   pFDDRecord                ( 100 ),
   pFEDRecord                ( 101 ),
   pFDCRecord                ( 102 ),
   mECORecord                ( 103 ),
   mERERecord                ( 104 ),
   cPDTSCERecord             ( 105 ),
   cPDTSNNRecord             ( 106 ),
   sCDVTT4Record             ( 110 ),
   sCSMOT4Record             ( 111 ),
   iSMSMORecord              ( 112 ),
   iSMSMTRecord              ( 113 ),
   eASCERecord               ( 120 ),
   chargingFunctionRecord    ( 200 )}

PriorityType ::= ENUMERATED {
   low         ( 0 ),
   normal      ( 1 ),
   high        ( 2 ) }

MessageClass ::= ENUMERATED {
   personal               ( 0 ),
   advertisement          ( 1 ),
   information-service    ( 2 ),
   auto                   ( 3 ) }

PositionMethodFailure-Diagnostic ::= ENUMERATED {
   congestion                                  ( 0 ),
   insufficientResources                       ( 1 ),
   insufficientMeasurementData                 ( 2 ),
   inconsistentMeasurementData                 ( 3 ),
   locationProcedureNotCompleted               ( 4 ),
   locationProcedureNotSupportedByTargetMS     ( 5 ),
   qoSNotAttainable                            ( 6 ),
   positionMethodNotAvailableInNetwork         ( 7 ),
   positionMethodNotAvailableInLocationArea    ( 8 ),
   ...  }

UnauthorizedLCSClient-Diagnostic ::= ENUMERATED {
   noAdditionalInformation                           ( 0 ),
   clientNotInMSPrivacyExceptionList                 ( 1 ),
   callToClientNotSetup                              ( 2 ),
   privacyOverrideNotApplicable                      ( 3 ),
   disallowedByLocalRegulatoryRequirements           ( 4 ),
   ... ,
   unauthorizedPrivacyClass                          ( 5 ),
   unauthorizedCallSessionUnrelatedExternalClient    ( 6 ),
   unauthorizedCallSessionRelatedExternalClient      ( 7 ) }

IPBinV6AddressWithPrefixLength ::= SEQUENCE {
   iPBinV6Address           OCTET STRING ( SIZE( 16 ) ),
   pDPAddressPrefixLength   INTEGER ( 1 .. 64 ) DEFAULT 64}

IPTextRepresentedAddress ::= CHOICE {
   iPTextV4Address     [2] IMPLICIT IA5String  ( SIZE( 7 .. 15 ) ),
   iPTextV6Address     [3] IMPLICIT IA5String  ( SIZE( 15 .. 45 ) )}

IPBinV6AddressWithOrWithoutPrefixLength ::= CHOICE {
   iPBinV6Address               [1] IMPLICIT OCTET STRING ( SIZE( 16 ) ),
   iPBinV6AddressWithPrefix     [4] IMPLICIT IPBinV6AddressWithPrefixLength}

IPBinaryAddress ::= CHOICE {
   iPBinV4Address     [0] IMPLICIT OCTET STRING ( SIZE( 4 ) ),
   iPBinV6Address     IPBinV6AddressWithOrWithoutPrefixLength}

IPAddress ::= CHOICE {
   iPBinaryAddress              IPBinaryAddress,
   iPTextRepresentedAddress     IPTextRepresentedAddress}

PDPAddress ::= CHOICE {
   iPAddress     [0] IPAddress}

NodeAddress ::= CHOICE {
   iPAddress      [0] IPAddress,
   domainName     [1] IMPLICIT GraphicString}

SubscriberEquipmentNumber ::= SET {
   subscriberEquipmentNumberType   [0] IMPLICIT ENUMERATED {
      iMEISV           ( 0 ),
      mAC              ( 1 ),
      eUI64            ( 2 ),
      modifiedEUI64    ( 3 ) },
   subscriberEquipmentNumberData   [1] IMPLICIT OCTET STRING}

ManagementExtension ::= SEQUENCE {
   identifier     DMI-EXTENSION.&id ({ManagementExtensionSet}) ,
   significance   [1] IMPLICIT BOOLEAN DEFAULT FALSE,
   information    [2] DMI-EXTENSION.&Value ({ManagementExtensionSet}{@.identifier}) }

SMSResult ::= CHOICE {
   gsm0408Cause                                [0] IMPLICIT INTEGER,
   gsm0902MapErrorValue                        [1] IMPLICIT INTEGER,
   itu-tQ767Cause                              [2] IMPLICIT INTEGER,
   networkSpecificCause                        [3] IMPLICIT ManagementExtension,
   manufacturerSpecificCause                   [4] IMPLICIT ManagementExtension,
   positionMethodFailureCause                  [5] IMPLICIT PositionMethodFailure-Diagnostic,
   unauthorizedLCSClientCause                  [6] IMPLICIT UnauthorizedLCSClient-Diagnostic,
   diameterResultCodeAndExperimentalResult     [7] IMPLICIT INTEGER}

SMSRecordType ::= CHOICE {
   sCSMORecord       [93] IMPLICIT SCSMORecord,
   sCSMTRecord       [94] IMPLICIT SCSMTRecord,
   sCDVTT4Record     [110] IMPLICIT SCDVTT4Record,
   sCSMOT4Record     [111] IMPLICIT SCSMTRecord,
   iSMSMORecord      [112] IMPLICIT ISMSMORecord,
   iSMSMTRecord      [113] IMPLICIT ISMSMTRecord}

SCSMORecord ::= SET {
   recordType                  [0] IMPLICIT RecordType,
   sMSNodeAddress              [1] IMPLICIT OCTET STRING ( SIZE( 1 .. 20 ) ),
   originatorInfo              [2] IMPLICIT OriginatorInfo OPTIONAL,
   recipientInfo               [3] IMPLICIT SEQUENCE  OF
      RecipientInfo OPTIONAL,
   servedIMEI                  [4] IMPLICIT OCTET STRING ( SIZE( 8 ) ) OPTIONAL,
   eventtimestamp              [5] IMPLICIT OCTET STRING ( SIZE( 9 ) ),
   messageReference            [6] IMPLICIT OCTET STRING,
   sMTotalNumber               [7] IMPLICIT INTEGER OPTIONAL,
   sMSequenceNumber            [8] IMPLICIT INTEGER OPTIONAL,
   messageSize                 [9] IMPLICIT INTEGER OPTIONAL,
   messageClass                [10] IMPLICIT MessageClass OPTIONAL,
   sMdeliveryReportRequested   [11] IMPLICIT BOOLEAN OPTIONAL,
   sMDataCodingScheme          [12] IMPLICIT INTEGER OPTIONAL,
   sMMessageType               [13] IMPLICIT SMMessageType OPTIONAL,
   sMReplyPathRequested        [14] IMPLICIT NULL OPTIONAL,
   sMUserDataHeader            [15] IMPLICIT OCTET STRING OPTIONAL,
   userLocationInfo            [16] IMPLICIT OCTET STRING OPTIONAL,
   rATType                     [17] IMPLICIT INTEGER ( 0 .. 255 ) OPTIONAL,
   uETimeZone                  [18] IMPLICIT OCTET STRING ( SIZE( 2 ) ) OPTIONAL,
   sMSResult                   [19] SMSResult OPTIONAL,
   localSequenceNumber         [22] IMPLICIT INTEGER ( 0 .. 4294967295 ) OPTIONAL,
   recordExtensions            [23] IMPLICIT SET  OF
      ManagementExtension OPTIONAL}

SCSMOT4Record ::= SET {
   recordType                  [0] IMPLICIT RecordType,
   sMSNodeAddress              [1] IMPLICIT OCTET STRING ( SIZE( 1 .. 20 ) ),
   originatorInfo              [2] IMPLICIT OriginatorInfo OPTIONAL,
   recipientInfo               [3] IMPLICIT RecipientInfo OPTIONAL,
   servedIMEI                  [4] IMPLICIT OCTET STRING ( SIZE( 8 ) ) OPTIONAL,
   eventtimestamp              [5] IMPLICIT OCTET STRING ( SIZE( 9 ) ),
   messageReference            [6] IMPLICIT OCTET STRING,
   messageSize                 [9] IMPLICIT INTEGER OPTIONAL,
   messageClass                [10] IMPLICIT MessageClass OPTIONAL,
   sMdeliveryReportRequested   [11] IMPLICIT BOOLEAN OPTIONAL,
   sMDataCodingScheme          [12] IMPLICIT INTEGER OPTIONAL,
   sMMessageType               [13] IMPLICIT SMMessageType OPTIONAL,
   sMReplyPathRequested        [14] IMPLICIT NULL OPTIONAL,
   sMUserDataHeader            [15] IMPLICIT OCTET STRING OPTIONAL,
   userLocationInfo            [16] IMPLICIT OCTET STRING OPTIONAL,
   rATType                     [17] IMPLICIT INTEGER ( 0 .. 255 ) OPTIONAL,
   uETimeZone                  [18] IMPLICIT OCTET STRING ( SIZE( 2 ) ) OPTIONAL,
   sMSResult                   [19] SMSResult OPTIONAL,
   mTCIWFAddress               [20] NodeAddress OPTIONAL,
   sMSApplicationPortID        [21] IMPLICIT INTEGER OPTIONAL,
   externalIdentifier          [22] IMPLICIT SET {
      subscriptionIDType   [0] IMPLICIT ENUMERATED {
         eND-USER-E164       ( 0 ),
         eND-USER-IMSI       ( 1 ),
         eND-USER-SIP-URI    ( 2 ),
         eND-USER-NAI        ( 3 ),
         eND-USER-PRIVATE    ( 4 ) },
      subscriptionIDData   [1] IMPLICIT UTF8String} OPTIONAL,
   localSequenceNumber         [23] IMPLICIT INTEGER ( 0 .. 4294967295 ) OPTIONAL,
   recordExtensions            [24] IMPLICIT SET  OF
      ManagementExtension OPTIONAL}

SCSMTRecord ::= SET {
   recordType                   [0] IMPLICIT RecordType,
   sMSNodeAddress               [1] IMPLICIT OCTET STRING ( SIZE( 1 .. 20 ) ),
   recipientInfo                [2] IMPLICIT RecipientInfo OPTIONAL,
   originatorInfo               [3] IMPLICIT OriginatorInfo OPTIONAL,
   servedIMEI                   [4] IMPLICIT OCTET STRING ( SIZE( 8 ) ) OPTIONAL,
   submissionTime               [5] IMPLICIT OCTET STRING ( SIZE( 9 ) ) OPTIONAL,
   eventtimestamp               [6] IMPLICIT OCTET STRING ( SIZE( 9 ) ),
   sMPriority                   [7] IMPLICIT PriorityType OPTIONAL,
   messageReference             [8] IMPLICIT OCTET STRING OPTIONAL,
   sMTotalNumber                [9] IMPLICIT INTEGER OPTIONAL,
   sMSequenceNumber             [10] IMPLICIT INTEGER OPTIONAL,
   messageSize                  [11] IMPLICIT INTEGER OPTIONAL,
   messageClass                 [12] IMPLICIT MessageClass OPTIONAL,
   sMdeliveryReportRequested    [13] IMPLICIT BOOLEAN OPTIONAL,
   sMDataCodingScheme           [14] IMPLICIT INTEGER OPTIONAL,
   sMMessageType                [15] IMPLICIT SMMessageType OPTIONAL,
   sMReplyPathRequested         [16] IMPLICIT NULL OPTIONAL,
   sMUserDataHeader             [17] IMPLICIT OCTET STRING OPTIONAL,
   sMSStatus                    [18] IMPLICIT OCTET STRING ( SIZE( 1 ) ) OPTIONAL,
   sMDischargeTime              [19] IMPLICIT OCTET STRING ( SIZE( 9 ) ) OPTIONAL,
   userLocationInfo             [20] IMPLICIT OCTET STRING OPTIONAL,
   rATType                      [21] IMPLICIT INTEGER ( 0 .. 255 ) OPTIONAL,
   uETimeZone                   [22] IMPLICIT OCTET STRING ( SIZE( 2 ) ) OPTIONAL,
   sMSResult                    [23] SMSResult OPTIONAL,
   sMDeviceTriggerInformation   [25] IMPLICIT SMDeviceTriggerInformation OPTIONAL,
   localSequenceNumber          [26] IMPLICIT INTEGER ( 0 .. 4294967295 ) OPTIONAL,
   recordExtensions             [27] IMPLICIT SET  OF
      ManagementExtension OPTIONAL}

SCDVTT4Record ::= SET {
   recordType                   [0] IMPLICIT RecordType,
   sMSNodeAddress               [1] IMPLICIT OCTET STRING ( SIZE( 1 .. 20 ) ),
   eventtimestamp               [2] IMPLICIT OCTET STRING ( SIZE( 9 ) ),
   originatorInfo               [3] IMPLICIT OriginatorInfo OPTIONAL,
   recipientInfo                [4] IMPLICIT RecipientInfo OPTIONAL,
   sMDeviceTriggerIndicator     [5] IMPLICIT SMDeviceTriggerIndicator OPTIONAL,
   sMDeviceTriggerInformation   [6] IMPLICIT SMDeviceTriggerInformation OPTIONAL,
   sMSResult                    [7] SMSResult OPTIONAL,
   localSequenceNumber          [9] IMPLICIT INTEGER ( 0 .. 4294967295 ) OPTIONAL,
   recordExtensions             [10] IMPLICIT SET  OF
      ManagementExtension OPTIONAL}

ISMSMORecord ::= SET {
   recordType                  [0] IMPLICIT RecordType,
   sMSNodeAddress              [1] NodeAddress,
   originatorInfo              [2] IMPLICIT OriginatorInfo OPTIONAL,
   recipientInfo               [3] IMPLICIT SEQUENCE  OF
      RecipientInfo OPTIONAL,
   subscriberEquipmentNumber   [4] IMPLICIT SubscriberEquipmentNumber OPTIONAL,
   eventtimestamp              [5] IMPLICIT OCTET STRING ( SIZE( 9 ) ),
   messageReference            [6] IMPLICIT OCTET STRING,
   sMTotalNumber               [7] IMPLICIT INTEGER OPTIONAL,
   sMSequenceNumber            [8] IMPLICIT INTEGER OPTIONAL,
   messageSize                 [9] IMPLICIT INTEGER OPTIONAL,
   messageClass                [10] IMPLICIT MessageClass OPTIONAL,
   sMdeliveryReportRequested   [11] IMPLICIT BOOLEAN OPTIONAL,
   sMDataCodingScheme          [12] IMPLICIT INTEGER OPTIONAL,
   sMMessageType               [13] IMPLICIT SMMessageType OPTIONAL,
   sMReplyPathRequested        [14] IMPLICIT NULL OPTIONAL,
   sMUserDataHeader            [15] IMPLICIT OCTET STRING OPTIONAL,
   sMSResult                   [16] SMSResult OPTIONAL,
   userLocationInfo            [17] IMPLICIT OCTET STRING OPTIONAL,
   rATType                     [18] IMPLICIT INTEGER ( 0 .. 255 ) OPTIONAL,
   uETimeZone                  [19] IMPLICIT OCTET STRING ( SIZE( 2 ) ) OPTIONAL,
   pDPAddress                  [20] PDPAddress OPTIONAL,
   session-Id                  [21] IMPLICIT GraphicString OPTIONAL,
   numberPortabilityRouting    [22] IMPLICIT GraphicString OPTIONAL,
   carrierSelectRouting        [23] IMPLICIT GraphicString OPTIONAL,
   localSequenceNumber         [24] IMPLICIT INTEGER ( 0 .. 4294967295 ) OPTIONAL,
   recordExtensions            [25] IMPLICIT SET  OF
      ManagementExtension OPTIONAL}

ISMSMTRecord ::= SET {
   recordType                  [0] IMPLICIT RecordType,
   sMSNodeAddress              [1] NodeAddress,
   recipientInfo               [2] IMPLICIT RecipientInfo OPTIONAL,
   originatorInfo              [3] IMPLICIT OriginatorInfo OPTIONAL,
   subscriberEquipmentNumber   [4] IMPLICIT SubscriberEquipmentNumber OPTIONAL,
   submissionTime              [5] IMPLICIT OCTET STRING ( SIZE( 9 ) ) OPTIONAL,
   eventtimestamp              [6] IMPLICIT OCTET STRING ( SIZE( 9 ) ),
   sMPriority                  [7] IMPLICIT PriorityType OPTIONAL,
   messageReference            [8] IMPLICIT OCTET STRING,
   sMTotalNumber               [9] IMPLICIT INTEGER OPTIONAL,
   sMSequenceNumber            [10] IMPLICIT INTEGER OPTIONAL,
   messageSize                 [11] IMPLICIT INTEGER OPTIONAL,
   messageClass                [12] IMPLICIT MessageClass OPTIONAL,
   sMdeliveryReportRequested   [13] IMPLICIT BOOLEAN OPTIONAL,
   sMDataCodingScheme          [14] IMPLICIT INTEGER OPTIONAL,
   sMMessageType               [15] IMPLICIT SMMessageType OPTIONAL,
   sMReplyPathRequested        [16] IMPLICIT NULL OPTIONAL,
   sMUserDataHeader            [17] IMPLICIT OCTET STRING OPTIONAL,
   sMSStatus                   [18] IMPLICIT OCTET STRING ( SIZE( 1 ) ) OPTIONAL,
   sMDischargeTime             [19] IMPLICIT OCTET STRING ( SIZE( 9 ) ) OPTIONAL,
   userLocationInfo            [20] IMPLICIT OCTET STRING OPTIONAL,
   rATType                     [21] IMPLICIT INTEGER ( 0 .. 255 ) OPTIONAL,
   uETimeZone                  [22] IMPLICIT OCTET STRING ( SIZE( 2 ) ) OPTIONAL,
   sMSResult                   [23] SMSResult OPTIONAL,
   pDPAddress                  [24] PDPAddress OPTIONAL,
   session-Id                  [25] IMPLICIT GraphicString OPTIONAL,
   numberPortabilityRouting    [26] IMPLICIT GraphicString OPTIONAL,
   carrierSelectRouting        [27] IMPLICIT GraphicString OPTIONAL,
   localSequenceNumber         [28] IMPLICIT INTEGER ( 0 .. 4294967295 ) OPTIONAL,
   recordExtensions            [29] IMPLICIT SET  OF
      ManagementExtension OPTIONAL}

OriginatorInfo ::= SEQUENCE {
   originatorIMSI              [0] IMPLICIT OCTET STRING ( SIZE( 3 .. 8 ) ) OPTIONAL,
   originatorMSISDN            [1] IMPLICIT OCTET STRING ( SIZE( 1 .. 20 ) ) ( SIZE( 1 .. 9 ) ) OPTIONAL,
   originatorOtherAddress      [2] IMPLICIT SMAddressInfo OPTIONAL,
   originatorSCCPAddress       [3] IMPLICIT OCTET STRING ( SIZE( 1 .. 20 ) ) OPTIONAL,
   originatorReceivedAddress   [4] IMPLICIT SMAddressInfo OPTIONAL,
   sMOriginatorInterface       [5] IMPLICIT SMInterface OPTIONAL,
   sMOriginatorProtocolID      [6] IMPLICIT OCTET STRING OPTIONAL}

RecipientInfo ::= SEQUENCE {
   recipientIMSI              [0] IMPLICIT OCTET STRING ( SIZE( 3 .. 8 ) ) OPTIONAL,
   recipientMSISDN            [1] IMPLICIT OCTET STRING ( SIZE( 1 .. 20 ) ) ( SIZE( 1 .. 9 ) ) OPTIONAL,
   recipientOtherAddress      [2] IMPLICIT SMAddressInfo OPTIONAL,
   recipientSCCPAddress       [3] IMPLICIT OCTET STRING ( SIZE( 1 .. 20 ) ) OPTIONAL,
   recipientReceivedAddress   [4] IMPLICIT SMAddressInfo OPTIONAL,
   sMDestinationInterface     [5] IMPLICIT SMInterface OPTIONAL,
   sMRecipientProtocolID      [6] IMPLICIT OCTET STRING OPTIONAL}

SMAddressDomain ::= SEQUENCE {
   sMDomainName           [0] IMPLICIT GraphicString OPTIONAL,
   threeGPPIMSI-MCC-MNC   [1] IMPLICIT OCTET STRING ( SIZE( 3 ) ) OPTIONAL}

SMAddressInfo ::= SEQUENCE {
   sMAddressType     [0] IMPLICIT SMAddressType OPTIONAL,
   sMAddressData     [1] IMPLICIT GraphicString OPTIONAL,
   sMAddressDomain   [2] IMPLICIT SMAddressDomain OPTIONAL}

SMAddressType ::= ENUMERATED {
   emailAddress             ( 0 ),
   mSISDN                   ( 1 ),
   iPv4Address              ( 2 ),
   iPv6Address              ( 3 ),
   numericShortCode         ( 4 ),
   alphanumericShortCode    ( 5 ),
   other                    ( 6 ),
   iMSI                     ( 7 ) }

SMDeviceTriggerIndicator ::= ENUMERATED {
   notDeviceTrigger        ( 0 ),
   deviceTriggerRequest    ( 1 ),
   deviceTriggerReplace    ( 2 ),
   deviceTriggerRecall     ( 3 ) }

SMDeviceTriggerInformation ::= SEQUENCE {
   mTCIWFAddress            [0] NodeAddress OPTIONAL,
   sMDTReferenceNumber      [1] IMPLICIT INTEGER OPTIONAL,
   sMServingNode            [2] IMPLICIT SMServingNode OPTIONAL,
   sMDTValidityPeriod       [3] IMPLICIT INTEGER OPTIONAL,
   sMDTPriorityIndication   [4] IMPLICIT SMDTPriorityIndication OPTIONAL,
   sMSApplicationPortID     [5] IMPLICIT INTEGER OPTIONAL}

SMDTPriorityIndication ::= ENUMERATED {
   nonpriority    ( 0 ),
   priority       ( 1 ) }

SMInterface ::= SEQUENCE {
   interfaceId     [0] IMPLICIT GraphicString OPTIONAL,
   interfaceText   [1] IMPLICIT GraphicString OPTIONAL,
   interfacePort   [2] IMPLICIT GraphicString OPTIONAL,
   interfaceType   [3] IMPLICIT SMInterfaceType OPTIONAL}

SMInterfaceType ::= ENUMERATED {
   unkown                    ( 0 ),
   mobileOriginating         ( 1 ),
   mobileTerminating         ( 2 ),
   applicationOriginating    ( 3 ),
   applicationTerminating    ( 4 ),
   deviceTrigger             ( 5 ) }

SMMessageType ::= ENUMERATED {
   submission          ( 0 ),
   deliveryReport      ( 1 ),
   sMServiceRequest    ( 2 ),
   delivery            ( 3 ),
   t4DeviceTrigger     ( 4 ),
   sMDeviceTrigger     ( 5 ) }

SMServingNode ::= SEQUENCE {
   sGSNName            [0] IMPLICIT OCTET STRING OPTIONAL,
   sGSNRealm           [1] IMPLICIT OCTET STRING OPTIONAL,
   sGSNNumber          [2] IMPLICIT OCTET STRING ( SIZE( 1 .. 20 ) ) OPTIONAL,
   mMEName             [3] IMPLICIT OCTET STRING OPTIONAL,
   mMERealm            [4] IMPLICIT OCTET STRING OPTIONAL,
   mMENumberForMTSMS   [5] IMPLICIT OCTET STRING ( SIZE( 1 .. 20 ) ) OPTIONAL,
   mSCNumber           [6] IMPLICIT OCTET STRING ( SIZE( 1 .. 20 ) ) OPTIONAL,
   iPSMGWNumber        [7] IMPLICIT OCTET STRING ( SIZE( 1 .. 20 ) ) OPTIONAL,
   iPSMGWName          [8] IMPLICIT OCTET STRING OPTIONAL}

SMSStatus  ::= OCTET STRING ( SIZE( 1 ) )


-- X.721 DMI-EXTENSION. The set is the standard form of the original
-- extensible empty table constraint ({, ...}) and does not change BER.
DMI-EXTENSION ::= CLASS {
    &id     OBJECT IDENTIFIER UNIQUE,
    &Value
}
WITH SYNTAX {
    TYPE &Value
    ID &id
}

ManagementExtensionSet DMI-EXTENSION ::= {...}

END
