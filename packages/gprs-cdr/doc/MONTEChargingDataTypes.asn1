-- Modified by Jonathan M. Wilbur to fix invalid syntax.
--     Expanded ASN1 Module 'MONTEChargingDataTypes'
--SIEMENS ASN.1 Compiler         R6.31  (Production_6.31)
--            Date: 2020-07-10 Time: 16:16:27

MONTEChargingDataTypes
{itu-t(0) identified-organization(4) etsi(0) mobileDomain(0) charging(5)
mONTEChargingDataType(12) asn1Module(0) version2(1)}
DEFINITIONS
::=
BEGIN

RecordType ::= INTEGER {
   moCallRecord              ( 0 ),
   mtCallRecord              ( 1 ),
   roamingRecord             ( 2 ),
   incGatewayRecord          ( 3 ),
   outGatewayRecord          ( 4 ),
   transitCallRecord         ( 5 ),
   moSMSRecord               ( 6 ),
   mtSMSRecord               ( 7 ),
   moSMSIWRecord             ( 8 ),
   mtSMSGWRecord             ( 9 ),
   ssActionRecord            ( 10 ),
   hlrIntRecord              ( 11 ),
   locUpdateHLRRecord        ( 12 ),
   locUpdateVLRRecord        ( 13 ),
   commonEquipRecord         ( 14 ),
   moTraceRecord             ( 15 ),
   mtTraceRecord             ( 16 ),
   termCAMELRecord           ( 17 ),
   sgsnPDPRecord             ( 18 ),
   sgsnMMRecord              ( 20 ),
   sgsnSMORecord             ( 21 ),
   sgsnSMTRecord             ( 22 ),
   mtLCSRecord               ( 23 ),
   moLCSRecord               ( 24 ),
   niLCSRecord               ( 25 ),
   sgsnMTLCSRecord           ( 26 ),
   sgsnMOLCSRecord           ( 27 ),
   sgsnNILCSRecord           ( 28 ),
   mMO1SRecord               ( 30 ),
   mMO4FRqRecord             ( 31 ),
   mMO4FRsRecord             ( 32 ),
   mMO4DRecord               ( 33 ),
   mMO1DRecord               ( 34 ),
   mMO4RRecord               ( 35 ),
   mMO1RRecord               ( 36 ),
   mMOMDRecord               ( 37 ),
   mMR4FRecord               ( 38 ),
   mMR1NRqRecord             ( 39 ),
   mMR1NRsRecord             ( 40 ),
   mMR1RtRecord              ( 41 ),
   mMR1AFRecord              ( 42 ),
   mMR4DRqRecord             ( 43 ),
   mMR4DRsRecord             ( 44 ),
   mMR1RRRecord              ( 45 ),
   mMR4RRqRecord             ( 46 ),
   mMR4RRsRecord             ( 47 ),
   mMRMDRecord               ( 48 ),
   mMFRecord                 ( 49 ),
   mMBx1SRecord              ( 50 ),
   mMBx1VRecord              ( 51 ),
   mMBx1URecord              ( 52 ),
   mMBx1DRecord              ( 53 ),
   mM7SRecord                ( 54 ),
   mM7DRqRecord              ( 55 ),
   mM7DRsRecord              ( 56 ),
   mM7CRecord                ( 57 ),
   mM7RRecord                ( 58 ),
   mM7DRRqRecord             ( 59 ),
   mM7DRRsRecord             ( 60 ),
   mM7RRqRecord              ( 61 ),
   mM7RRsRecord              ( 62 ),
   sCSCFRecord               ( 63 ),
   pCSCFRecord               ( 64 ),
   iCSCFRecord               ( 65 ),
   mRFCRecord                ( 66 ),
   mGCFRecord                ( 67 ),
   bGCFRecord                ( 68 ),
   aSRecord                  ( 69 ),
   eCSCFRecord               ( 70 ),
   iBCFRecord                ( 82 ),
   tRFRecord                 ( 89 ),
   tFRecord                  ( 90 ),
   aTCFRecord                ( 91 ),
   lCSGMORecord              ( 71 ),
   lCSRGMTRecord             ( 72 ),
   lCSHGMTRecord             ( 73 ),
   lCSVGMTRecord             ( 74 ),
   lCSGNIRecord              ( 75 ),
   sgsnMBMSRecord            ( 76 ),
   ggsnMBMSRecord            ( 77 ),
   gwMBMSRecord              ( 86 ),
   sUBBMSCRecord             ( 78 ),
   cONTENTBMSCRecord         ( 79 ),
   pPFRecord                 ( 80 ),
   cPFRecord                 ( 81 ),
   sGWRecord                 ( 84 ),
   pGWRecord                 ( 85 ),
   tDFRecord                 ( 92 ),
   iPERecord                 ( 95 ),
   ePDGRecord                ( 96 ),
   tWAGRecord                ( 97 ),
   mMTelRecord               ( 83 ),
   mSCsRVCCRecord            ( 87 ),
   mMTRFRecord               ( 88 ),
   iCSRegisterRecord         ( 99 ),
   sCSMORecord               ( 93 ),
   sCSMTRecord               ( 94 ),
   pFDDRecord                ( 100 ),
   pFEDRecord                ( 101 ),
   pFDCRecord                ( 102 ),
   mECORecord                ( 103 ),
   mERERecord                ( 104 ),
   cPDTSCERecord             ( 105 ),
   cPDTSNNRecord             ( 106 ),
   sCDVTT4Record             ( 110 ),
   sCSMOT4Record             ( 111 ),
   iSMSMORecord              ( 112 ),
   iSMSMTRecord              ( 113 ),
   eASCERecord               ( 120 ),
   chargingFunctionRecord    ( 200 )}

UserCSGInformation ::= SEQUENCE {
   cSGId                     [0] IMPLICIT OCTET STRING ( SIZE( 4 ) ),
   cSGAccessMode             [1] IMPLICIT ENUMERATED {
      closedMode    ( 0 ),
      hybridMode    ( 1 ) },
   cSGMembershipIndication   [2] IMPLICIT NULL OPTIONAL}

ManagementExtension ::= SEQUENCE {
   identifier     DMI-EXTENSION.&id ({ManagementExtensionSet}) ,
   significance   [1] IMPLICIT BOOLEAN DEFAULT FALSE,
   information    [2] DMI-EXTENSION.&Value ({ManagementExtensionSet}{@.identifier}) }

MERecordType ::= CHOICE {
   mECORecord     [103] IMPLICIT MECORecord,
   mERERecord     [104] IMPLICIT MERERecord}

MECORecord ::= SET {
   recordType                             [0] IMPLICIT RecordType,
   retransmission                         [1] IMPLICIT NULL OPTIONAL,
   serviceContextID                       [2] IMPLICIT UTF8String OPTIONAL,
   nodeID                                 [3] IMPLICIT IA5String  ( SIZE( 1 .. 20 ) ) OPTIONAL,
   recordTimeStamp                        [4] IMPLICIT OCTET STRING ( SIZE( 9 ) ) OPTIONAL,
   eventTimestamp                         [5] IMPLICIT OCTET STRING ( SIZE( 9 ) ) OPTIONAL,
   monitoringEventConfigurationActivity   [6] IMPLICIT MonitoringEventConfigurationActivity OPTIONAL,
   sCEFReferenceID                        [7] IMPLICIT INTEGER ( 0 .. 4294967295 ) OPTIONAL,
   sCEFID                                 [8] IMPLICIT OCTET STRING OPTIONAL,
   monitoringType                         [9] IMPLICIT MonitoringType OPTIONAL,
   maximumNumberofReports                 [10] IMPLICIT INTEGER OPTIONAL,
   monitoringDuration                     [11] IMPLICIT OCTET STRING ( SIZE( 9 ) ) OPTIONAL,
   chargeablePartyIdentifier              [12] IMPLICIT UTF8String OPTIONAL,
   monitoredUser                          [13] IMPLICIT OCTET STRING ( SIZE( 3 .. 8 ) ) OPTIONAL,
   maximumDetectionTime                   [14] IMPLICIT INTEGER OPTIONAL,
   localRecordSequenceNumber              [15] IMPLICIT INTEGER ( 0 .. 4294967295 ) OPTIONAL,
   reachabilityConfiguration              [16] IMPLICIT ReachabilityConfiguration OPTIONAL,
   locationType                           [17] IMPLICIT LocationType OPTIONAL,
   accuracy                               [18] IMPLICIT Accuracy OPTIONAL,
   listofLocations                        [19] IMPLICIT SEQUENCE  OF
      EPSLocationInfo OPTIONAL,
   monitoringEventConfigStatus            [20] IMPLICIT MonitoringEventConfigStatus OPTIONAL,
   recordExtensions                       [21] IMPLICIT SET  OF
      ManagementExtension OPTIONAL}

MERERecord ::= SET {
   recordType                        [0] IMPLICIT RecordType,
   retransmission                    [1] IMPLICIT NULL OPTIONAL,
   serviceContextID                  [2] IMPLICIT UTF8String OPTIONAL,
   nodeID                            [3] IMPLICIT IA5String  ( SIZE( 1 .. 20 ) ) OPTIONAL,
   recordTimeStamp                   [4] IMPLICIT OCTET STRING ( SIZE( 9 ) ) OPTIONAL,
   localRecordSequenceNumber         [5] IMPLICIT INTEGER ( 0 .. 4294967295 ) OPTIONAL,
   listofMonitoringEventReportData   [6] IMPLICIT SEQUENCE  OF
      MonitoringEventReportData OPTIONAL,
   recordExtensions                  [7] IMPLICIT SET  OF
      ManagementExtension OPTIONAL}

Accuracy   ::= ENUMERATED {
   cGIECGI     ( 0 ),
   eNB         ( 1 ),
   lATARA      ( 2 ),
   pRA         ( 3 ) }

CauseType  ::= ENUMERATED {
   radioNetworkLayer    ( 0 ),
   transportLayer       ( 1 ),
   nAS                  ( 2 ),
   protocol             ( 3 ),
   miscellaneous        ( 4 ) }

CommunicationFailureInfo ::= SEQUENCE {
   causeType    [0] IMPLICIT CauseType OPTIONAL,
   s1APCause    [1] IMPLICIT INTEGER OPTIONAL,
   rANAPCause   [2] IMPLICIT INTEGER OPTIONAL,
   bSSGPCause   [3] IMPLICIT INTEGER OPTIONAL,
   gMMCause     [4] IMPLICIT INTEGER OPTIONAL,
   sMCause      [5] IMPLICIT INTEGER OPTIONAL}

CurrentLocationRetrieved ::= ENUMERATED {
   activeLocationRetrieval    ( 0 ) }

EPSLocationInfo ::= SEQUENCE {
   mMELocationInformation    [0] IMPLICIT MMELocationInformation OPTIONAL,
   sGSNLocationInformation   [1] IMPLICIT SGSNLocationInformation OPTIONAL}

LocationType ::= ENUMERATED {
   currentLocation      ( 0 ),
   lastKnownLocation    ( 1 ) }

MMELocationInformation ::= SEQUENCE {
   eUTRANCellGlobalIdentity   [0] IMPLICIT OCTET STRING OPTIONAL,
   trackingAreaIdentity       [1] IMPLICIT OCTET STRING OPTIONAL,
   geographicalInformation    [2] IMPLICIT OCTET STRING OPTIONAL,
   geodeticInformation        [3] IMPLICIT OCTET STRING OPTIONAL,
   currentLocationRetrieved   [4] IMPLICIT CurrentLocationRetrieved OPTIONAL,
   ageOfLocationInformation   [5] IMPLICIT INTEGER OPTIONAL,
   userCSGInformation         [6] IMPLICIT UserCSGInformation OPTIONAL,
   eNodeBID                   [7] IMPLICIT OCTET STRING OPTIONAL}

MonitoringEventConfigStatus ::= SEQUENCE {
   serviceResult     [0] IMPLICIT ServiceResult OPTIONAL,
   sCEFReferenceID   [1] IMPLICIT INTEGER ( 0 .. 4294967295 ) OPTIONAL,
   sCEFID            [2] IMPLICIT OCTET STRING OPTIONAL}

MonitoringEventConfigurationActivity ::= ENUMERATED {
   create      ( 0 ),
   transfer    ( 1 ),
   update      ( 2 ),
   delete      ( 3 ) }

MonitoringEventReportData ::= SEQUENCE {
   eventTimestamp                      [0] IMPLICIT OCTET STRING ( SIZE( 9 ) ) OPTIONAL,
   sCEFReferenceID                     [1] IMPLICIT INTEGER ( 0 .. 4294967295 ) OPTIONAL,
   sCEFID                              [2] IMPLICIT OCTET STRING OPTIONAL,
   monitoringEventReportNumber         [3] IMPLICIT INTEGER OPTIONAL,
   chargeablePartyIdentifier           [4] IMPLICIT UTF8String OPTIONAL,
   monitoredUser                       [5] IMPLICIT OCTET STRING ( SIZE( 3 .. 8 ) ) OPTIONAL,
   monitoringType                      [6] IMPLICIT MonitoringType OPTIONAL,
   reachabilityInformation             [7] IMPLICIT ReachabilityType OPTIONAL,
   reportedLocation                    [8] IMPLICIT EPSLocationInfo OPTIONAL,
   communicationFailureInformation     [9] IMPLICIT SEQUENCE  OF
      CommunicationFailureInfo OPTIONAL,
   listOfNumberOfUEPerLocationReport   [10] IMPLICIT SEQUENCE  OF
      NumberOfUEPerLocationReport OPTIONAL}

MonitoringType ::= ENUMERATED {
   lossOfConnectivity               ( 0 ),
   ueReachability                   ( 1 ),
   locationReporting                ( 2 ),
   changeOfIMSIIMEISVAssociation    ( 3 ),
   roamingStatus                    ( 4 ),
   communicationFailure             ( 5 ),
   availabilityAfterDDNFailure      ( 6 ),
   numberOfUEPerLocation            ( 7 ) }

NumberOfUEPerLocationReport ::= SEQUENCE {
   ePSLocationInformation   [0] IMPLICIT EPSLocationInfo OPTIONAL,
   uECount                  [1] IMPLICIT INTEGER OPTIONAL}

ReachabilityConfiguration ::= SEQUENCE {
   reachabilityType      [0] IMPLICIT ReachabilityType OPTIONAL,
   maximumLatency        [1] IMPLICIT INTEGER OPTIONAL,
   maximumResponseTime   [2] IMPLICIT INTEGER OPTIONAL}

ReachabilityType ::= ENUMERATED {
   reachabilityforSMS     ( 0 ),
   reachabilityforData    ( 1 ) }

SGSNLocationInformation ::= SEQUENCE {
   cellGlobalIdentity         [0] IMPLICIT OCTET STRING OPTIONAL,
   locationAreaIdentity       [1] IMPLICIT OCTET STRING OPTIONAL,
   serviceAreaIdentity        [2] IMPLICIT OCTET STRING OPTIONAL,
   routingAreaIdentity        [3] IMPLICIT OCTET STRING OPTIONAL,
   geographicalInformation    [4] IMPLICIT OCTET STRING OPTIONAL,
   geodeticInformation        [5] IMPLICIT OCTET STRING OPTIONAL,
   currentLocationRetrieved   [6] IMPLICIT CurrentLocationRetrieved OPTIONAL,
   ageOfLocationInformation   [7] IMPLICIT INTEGER OPTIONAL,
   userCSGInformation         [8] IMPLICIT UserCSGInformation OPTIONAL}

SCEFReferenceID ::= INTEGER ( 0 .. 4294967295 )

ServiceResult ::= SEQUENCE {
   vendorId            [0] IMPLICIT INTEGER OPTIONAL,
   serviceResultCode   [1] IMPLICIT INTEGER OPTIONAL}


-- X.721 DMI-EXTENSION. The set is the standard form of the original
-- extensible empty table constraint ({, ...}) and does not change BER.
DMI-EXTENSION ::= CLASS {
    &id     OBJECT IDENTIFIER UNIQUE,
    &Value
}
WITH SYNTAX {
    TYPE &Value
    ID &id
}

ManagementExtensionSet DMI-EXTENSION ::= {...}

END
