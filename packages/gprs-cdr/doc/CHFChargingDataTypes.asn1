-- Modified by Jonathan M. Wilbur to fix invalid syntax.
--      Expanded ASN1 Module 'CHFChargingDataTypes'
--SIEMENS ASN.1 Compiler         R6.31  (Production_6.31)
--            Date: 2020-07-10 Time: 16:17:27

CHFChargingDataTypes
{itu-t(0) identified-organization(4) etsi(0) mobileDomain(0) charging(5)
chfChargingDataTypes(15) asn1Module(0) version1(0)}
DEFINITIONS
::=
BEGIN

CauseForRecClosing ::= INTEGER {
   normalRelease                    ( 0 ),
   abnormalRelease                  ( 4 ),
   cAMELInitCallRelease             ( 5 ),
   volumeLimit                      ( 16 ),
   timeLimit                        ( 17 ),
   servingNodeChange                ( 18 ),
   maxChangeCond                    ( 19 ),
   managementIntervention           ( 20 ),
   intraSGSNIntersystemChange       ( 21 ),
   rATChange                        ( 22 ),
   mSTimeZoneChange                 ( 23 ),
   sGSNPLMNIDChange                 ( 24 ),
   sGWChange                        ( 25 ),
   aPNAMBRChange                    ( 26 ),
   mOExceptionDataCounterReceipt    ( 27 ),
   unauthorizedRequestingNetwork    ( 52 ),
   unauthorizedLCSClient            ( 53 ),
   positionMethodFailure            ( 54 ),
   unknownOrUnreachableLCSClient    ( 58 ),
   listofDownstreamNodeChange       ( 59 )}

RecordType ::= INTEGER {
   moCallRecord              ( 0 ),
   mtCallRecord              ( 1 ),
   roamingRecord             ( 2 ),
   incGatewayRecord          ( 3 ),
   outGatewayRecord          ( 4 ),
   transitCallRecord         ( 5 ),
   moSMSRecord               ( 6 ),
   mtSMSRecord               ( 7 ),
   moSMSIWRecord             ( 8 ),
   mtSMSGWRecord             ( 9 ),
   ssActionRecord            ( 10 ),
   hlrIntRecord              ( 11 ),
   locUpdateHLRRecord        ( 12 ),
   locUpdateVLRRecord        ( 13 ),
   commonEquipRecord         ( 14 ),
   moTraceRecord             ( 15 ),
   mtTraceRecord             ( 16 ),
   termCAMELRecord           ( 17 ),
   sgsnPDPRecord             ( 18 ),
   sgsnMMRecord              ( 20 ),
   sgsnSMORecord             ( 21 ),
   sgsnSMTRecord             ( 22 ),
   mtLCSRecord               ( 23 ),
   moLCSRecord               ( 24 ),
   niLCSRecord               ( 25 ),
   sgsnMTLCSRecord           ( 26 ),
   sgsnMOLCSRecord           ( 27 ),
   sgsnNILCSRecord           ( 28 ),
   mMO1SRecord               ( 30 ),
   mMO4FRqRecord             ( 31 ),
   mMO4FRsRecord             ( 32 ),
   mMO4DRecord               ( 33 ),
   mMO1DRecord               ( 34 ),
   mMO4RRecord               ( 35 ),
   mMO1RRecord               ( 36 ),
   mMOMDRecord               ( 37 ),
   mMR4FRecord               ( 38 ),
   mMR1NRqRecord             ( 39 ),
   mMR1NRsRecord             ( 40 ),
   mMR1RtRecord              ( 41 ),
   mMR1AFRecord              ( 42 ),
   mMR4DRqRecord             ( 43 ),
   mMR4DRsRecord             ( 44 ),
   mMR1RRRecord              ( 45 ),
   mMR4RRqRecord             ( 46 ),
   mMR4RRsRecord             ( 47 ),
   mMRMDRecord               ( 48 ),
   mMFRecord                 ( 49 ),
   mMBx1SRecord              ( 50 ),
   mMBx1VRecord              ( 51 ),
   mMBx1URecord              ( 52 ),
   mMBx1DRecord              ( 53 ),
   mM7SRecord                ( 54 ),
   mM7DRqRecord              ( 55 ),
   mM7DRsRecord              ( 56 ),
   mM7CRecord                ( 57 ),
   mM7RRecord                ( 58 ),
   mM7DRRqRecord             ( 59 ),
   mM7DRRsRecord             ( 60 ),
   mM7RRqRecord              ( 61 ),
   mM7RRsRecord              ( 62 ),
   sCSCFRecord               ( 63 ),
   pCSCFRecord               ( 64 ),
   iCSCFRecord               ( 65 ),
   mRFCRecord                ( 66 ),
   mGCFRecord                ( 67 ),
   bGCFRecord                ( 68 ),
   aSRecord                  ( 69 ),
   eCSCFRecord               ( 70 ),
   iBCFRecord                ( 82 ),
   tRFRecord                 ( 89 ),
   tFRecord                  ( 90 ),
   aTCFRecord                ( 91 ),
   lCSGMORecord              ( 71 ),
   lCSRGMTRecord             ( 72 ),
   lCSHGMTRecord             ( 73 ),
   lCSVGMTRecord             ( 74 ),
   lCSGNIRecord              ( 75 ),
   sgsnMBMSRecord            ( 76 ),
   ggsnMBMSRecord            ( 77 ),
   gwMBMSRecord              ( 86 ),
   sUBBMSCRecord             ( 78 ),
   cONTENTBMSCRecord         ( 79 ),
   pPFRecord                 ( 80 ),
   cPFRecord                 ( 81 ),
   sGWRecord                 ( 84 ),
   pGWRecord                 ( 85 ),
   tDFRecord                 ( 92 ),
   iPERecord                 ( 95 ),
   ePDGRecord                ( 96 ),
   tWAGRecord                ( 97 ),
   mMTelRecord               ( 83 ),
   mSCsRVCCRecord            ( 87 ),
   mMTRFRecord               ( 88 ),
   iCSRegisterRecord         ( 99 ),
   sCSMORecord               ( 93 ),
   sCSMTRecord               ( 94 ),
   pFDDRecord                ( 100 ),
   pFEDRecord                ( 101 ),
   pFDCRecord                ( 102 ),
   mECORecord                ( 103 ),
   mERERecord                ( 104 ),
   cPDTSCERecord             ( 105 ),
   cPDTSNNRecord             ( 106 ),
   sCDVTT4Record             ( 110 ),
   sCSMOT4Record             ( 111 ),
   iSMSMORecord              ( 112 ),
   iSMSMTRecord              ( 113 ),
   eASCERecord               ( 120 ),
   chargingFunctionRecord    ( 200 )}

ThreeGPPPSDataOffStatus ::= ENUMERATED {
   active      ( 0 ),
   inactive    ( 1 ) }

SMAddressType ::= ENUMERATED {
   emailAddress             ( 0 ),
   mSISDN                   ( 1 ),
   iPv4Address              ( 2 ),
   iPv6Address              ( 3 ),
   numericShortCode         ( 4 ),
   alphanumericShortCode    ( 5 ),
   other                    ( 6 ),
   iMSI                     ( 7 ) }

ChChSelectionMode ::= ENUMERATED {
   servingNodeSupplied     ( 0 ),
   subscriptionSpecific    ( 1 ),
   aPNSpecific             ( 2 ),
   homeDefault             ( 3 ),
   roamingDefault          ( 4 ),
   visitingDefault         ( 5 ),
   fixedDefault            ( 6 ) }

PositionMethodFailure-Diagnostic ::= ENUMERATED {
   congestion                                  ( 0 ),
   insufficientResources                       ( 1 ),
   insufficientMeasurementData                 ( 2 ),
   inconsistentMeasurementData                 ( 3 ),
   locationProcedureNotCompleted               ( 4 ),
   locationProcedureNotSupportedByTargetMS     ( 5 ),
   qoSNotAttainable                            ( 6 ),
   positionMethodNotAvailableInNetwork         ( 7 ),
   positionMethodNotAvailableInLocationArea    ( 8 ),
   ...  }

UnauthorizedLCSClient-Diagnostic ::= ENUMERATED {
   noAdditionalInformation                           ( 0 ),
   clientNotInMSPrivacyExceptionList                 ( 1 ),
   callToClientNotSetup                              ( 2 ),
   privacyOverrideNotApplicable                      ( 3 ),
   disallowedByLocalRegulatoryRequirements           ( 4 ),
   ... ,
   unauthorizedPrivacyClass                          ( 5 ),
   unauthorizedCallSessionUnrelatedExternalClient    ( 6 ),
   unauthorizedCallSessionRelatedExternalClient      ( 7 ) }

IPBinV6AddressWithPrefixLength ::= SEQUENCE {
   iPBinV6Address           OCTET STRING ( SIZE( 16 ) ),
   pDPAddressPrefixLength   INTEGER ( 1 .. 64 ) DEFAULT 64}

IPTextRepresentedAddress ::= CHOICE {
   iPTextV4Address     [2] IMPLICIT IA5String  ( SIZE( 7 .. 15 ) ),
   iPTextV6Address     [3] IMPLICIT IA5String  ( SIZE( 15 .. 45 ) )}

SMAddressDomain ::= SEQUENCE {
   sMDomainName           [0] IMPLICIT GraphicString OPTIONAL,
   threeGPPIMSI-MCC-MNC   [1] IMPLICIT OCTET STRING ( SIZE( 3 ) ) OPTIONAL}

IPBinV6AddressWithOrWithoutPrefixLength ::= CHOICE {
   iPBinV6Address               [1] IMPLICIT OCTET STRING ( SIZE( 16 ) ),
   iPBinV6AddressWithPrefix     [4] IMPLICIT IPBinV6AddressWithPrefixLength}

IPBinaryAddress ::= CHOICE {
   iPBinV4Address     [0] IMPLICIT OCTET STRING ( SIZE( 4 ) ),
   iPBinV6Address     IPBinV6AddressWithOrWithoutPrefixLength}

IPAddress ::= CHOICE {
   iPBinaryAddress              IPBinaryAddress,
   iPTextRepresentedAddress     IPTextRepresentedAddress}

NodeAddress ::= CHOICE {
   iPAddress      [0] IPAddress,
   domainName     [1] IMPLICIT GraphicString}

InvolvedParty ::= CHOICE {
   sIP-URI       [0] IMPLICIT GraphicString,
   tEL-URI       [1] IMPLICIT GraphicString,
   uRN           [2] IMPLICIT GraphicString,
   iSDN-E164     [3] IMPLICIT GraphicString}

SubscriberEquipmentNumber ::= SET {
   subscriberEquipmentNumberType   [0] IMPLICIT ENUMERATED {
      iMEISV           ( 0 ),
      mAC              ( 1 ),
      eUI64            ( 2 ),
      modifiedEUI64    ( 3 ) },
   subscriberEquipmentNumberData   [1] IMPLICIT OCTET STRING}

SubscriptionID ::= SET {
   subscriptionIDType   [0] IMPLICIT ENUMERATED {
      eND-USER-E164       ( 0 ),
      eND-USER-IMSI       ( 1 ),
      eND-USER-SIP-URI    ( 2 ),
      eND-USER-NAI        ( 3 ),
      eND-USER-PRIVATE    ( 4 ) },
   subscriptionIDData   [1] IMPLICIT UTF8String}

ManagementExtension ::= SEQUENCE {
   identifier     DMI-EXTENSION.&id ({ManagementExtensionSet}) ,
   significance   [1] IMPLICIT BOOLEAN DEFAULT FALSE,
   information    [2] DMI-EXTENSION.&Value ({ManagementExtensionSet}{@.identifier}) }

SMAddress ::= SEQUENCE {
   sMAddressType     [0] IMPLICIT SMAddressType OPTIONAL,
   sMAddressData     [1] IMPLICIT GraphicString OPTIONAL,
   sMAddressDomain   [2] IMPLICIT SMAddressDomain OPTIONAL}

SMInterface ::= SEQUENCE {
   interfaceId     [0] IMPLICIT GraphicString OPTIONAL,
   interfaceText   [1] IMPLICIT GraphicString OPTIONAL,
   interfacePort   [2] IMPLICIT GraphicString OPTIONAL,
   interfaceType   [3] IMPLICIT ENUMERATED {
      unkown                    ( 0 ),
      mobileOriginating         ( 1 ),
      mobileTerminating         ( 2 ),
      applicationOriginating    ( 3 ),
      applicationTerminating    ( 4 ),
      deviceTrigger             ( 5 ) } OPTIONAL}

PresenceReportingAreaInfo ::= SEQUENCE {
   presenceReportingAreaIdentifier     [0] IMPLICIT OCTET STRING,
   presenceReportingAreaStatus         [1] IMPLICIT ENUMERATED {
      insideArea     ( 0 ),
      outsideArea    ( 1 ),
      inactive       ( 2 ),
      unknown        ( 3 ) } OPTIONAL,
   presenceReportingAreaElementsList   [2] IMPLICIT OCTET STRING OPTIONAL,
   presenceReportingAreaNode           [3] IMPLICIT BIT STRING {
      oCS  (0 ),
      pCRF  (1 )} OPTIONAL}

RecipientInfos ::= SEQUENCE {
   recipientIMSI              [0] IMPLICIT OCTET STRING ( SIZE( 3 .. 8 ) ) OPTIONAL,
   recipientMSISDN            [1] IMPLICIT OCTET STRING ( SIZE( 1 .. 20 ) ) ( SIZE( 1 .. 9 ) ) OPTIONAL,
   recipientOtherAddress      [2] IMPLICIT SMAddress OPTIONAL,
   recipientSCCPAddress       [3] IMPLICIT OCTET STRING ( SIZE( 1 .. 20 ) ) OPTIONAL,
   recipientReceivedAddress   [4] IMPLICIT SMAddress OPTIONAL,
   sMDestinationInterface     [5] IMPLICIT SMInterface OPTIONAL,
   sMRecipientProtocolID      [6] IMPLICIT OCTET STRING OPTIONAL}

OriginatorInfo ::= SEQUENCE {
   originatorIMSI              [0] IMPLICIT OCTET STRING ( SIZE( 3 .. 8 ) ) OPTIONAL,
   originatorMSISDN            [1] IMPLICIT OCTET STRING ( SIZE( 1 .. 20 ) ) ( SIZE( 1 .. 9 ) ) OPTIONAL,
   originatorOtherAddress      [2] IMPLICIT SMAddress OPTIONAL,
   originatorSCCPAddress       [3] IMPLICIT OCTET STRING ( SIZE( 1 .. 20 ) ) OPTIONAL,
   originatorReceivedAddress   [4] IMPLICIT SMAddress OPTIONAL,
   sMOriginatorInterface       [5] IMPLICIT SMInterface OPTIONAL,
   sMOriginatorProtocolID      [6] IMPLICIT OCTET STRING OPTIONAL}

Diagnostics ::= CHOICE {
   gsm0408Cause                                [0] IMPLICIT INTEGER,
   gsm0902MapErrorValue                        [1] IMPLICIT INTEGER,
   itu-tQ767Cause                              [2] IMPLICIT INTEGER,
   networkSpecificCause                        [3] IMPLICIT ManagementExtension,
   manufacturerSpecificCause                   [4] IMPLICIT ManagementExtension,
   positionMethodFailureCause                  [5] IMPLICIT PositionMethodFailure-Diagnostic,
   unauthorizedLCSClientCause                  [6] IMPLICIT UnauthorizedLCSClient-Diagnostic,
   diameterResultCodeAndExperimentalResult     [7] IMPLICIT INTEGER}

CHFRecord  ::= CHOICE {
   chargingFunctionRecord     [200] IMPLICIT ChargingRecord}

ChargingRecord ::= SET {
   recordType                        [0] IMPLICIT RecordType,
   recordingNetworkFunctionID        [1] IMPLICIT IA5String  ( SIZE( 1 .. 36 ) ),
   subscriberIdentifier              [2] IMPLICIT SubscriptionID OPTIONAL,
   nFunctionConsumerInformation      [3] IMPLICIT NetworkFunctionInformation,
   triggers                          [4] IMPLICIT SEQUENCE  OF
      Trigger OPTIONAL,
   listOfMultipleUnitUsage           [5] IMPLICIT SEQUENCE  OF
      MultipleUnitUsage OPTIONAL,
   recordOpeningTime                 [6] IMPLICIT OCTET STRING ( SIZE( 9 ) ),
   duration                          [7] IMPLICIT INTEGER,
   recordSequenceNumber              [8] IMPLICIT INTEGER OPTIONAL,
   causeForRecClosing                [9] IMPLICIT CauseForRecClosing,
   diagnostics                       [10] Diagnostics OPTIONAL,
   localRecordSequenceNumber         [11] IMPLICIT INTEGER ( 0 .. 4294967295 ) OPTIONAL,
   recordExtensions                  [12] IMPLICIT SET  OF
      ManagementExtension OPTIONAL,
   pDUSessionChargingInformation     [13] IMPLICIT PDUSessionChargingInformation OPTIONAL,
   roamingQBCInformation             [14] IMPLICIT RoamingQBCInformation OPTIONAL,
   sMSChargingInformation            [15] IMPLICIT SMSChargingInformation OPTIONAL,
   chargingSessionIdentifier         [16] IMPLICIT OCTET STRING OPTIONAL,
   serviceSpecificationInformation   [17] IMPLICIT OCTET STRING OPTIONAL}

PDUSessionChargingInformation ::= SET {
   pDUSessionChargingID         [0] IMPLICIT INTEGER ( 0 .. 4294967295 ),
   userIdentifier               [1] InvolvedParty OPTIONAL,
   userEquipmentInfo            [2] IMPLICIT SubscriberEquipmentNumber OPTIONAL,
   userLocationInformation      [3] IMPLICIT OCTET STRING OPTIONAL,
   userRoamerInOut              [4] IMPLICIT RoamerInOut OPTIONAL,
   presenceReportingAreaInfo    [5] IMPLICIT PresenceReportingAreaInfo OPTIONAL,
   pDUSessionId                 [6] IMPLICIT INTEGER ( 0 .. 255 ),
   networkSliceInstanceID       [7] IMPLICIT NetworkSliceInstanceID OPTIONAL,
   pDUType                      [8] IMPLICIT PDUSessionType OPTIONAL,
   sSCMode                      [9] IMPLICIT INTEGER {
      sSCMode1    ( 1 ),
      sSCMode2    ( 2 ),
      sSCMode3    ( 3 )} OPTIONAL,
   sUPIPLMNIdentifier           [10] IMPLICIT OCTET STRING ( SIZE( 3 ) ) OPTIONAL,
   servingNetworkFunctionID     [11] IMPLICIT SEQUENCE  OF
      ServingNetworkFunctionID OPTIONAL,
   rATType                      [12] IMPLICIT INTEGER ( 0 .. 255 ) OPTIONAL,
   dataNetworkNameIdentifier    [13] IMPLICIT IA5String  ( SIZE( 1 .. 63 ) ) OPTIONAL,
   pDUAddress                   [14] IMPLICIT PDUAddress OPTIONAL,
   authorizedQoSInformation     [15] IMPLICIT AuthorizedQoSInformation OPTIONAL,
   uETimeZone                   [16] IMPLICIT OCTET STRING ( SIZE( 2 ) ) OPTIONAL,
   pDUSessionstartTime          [17] IMPLICIT OCTET STRING ( SIZE( 9 ) ) OPTIONAL,
   pDUSessionstopTime           [18] IMPLICIT OCTET STRING ( SIZE( 9 ) ) OPTIONAL,
   diagnostics                  [19] Diagnostics OPTIONAL,
   chargingCharacteristics      [20] IMPLICIT OCTET STRING ( SIZE( 2 ) ),
   chChSelectionMode            [21] IMPLICIT ChChSelectionMode OPTIONAL,
   threeGPPPSDataOffStatus      [22] IMPLICIT ThreeGPPPSDataOffStatus OPTIONAL,
   rANSecondaryRATUsageReport   [23] IMPLICIT SEQUENCE  OF
      NGRANSecondaryRATUsageReport OPTIONAL,
   subscribedQoSInformation     [24] IMPLICIT SubscribedQoSInformation OPTIONAL,
   authorizedSessionAMBR        [25] IMPLICIT SessionAMBR OPTIONAL,
   subscribedSessionAMBR        [26] IMPLICIT SessionAMBR OPTIONAL,
   servingCNPLMNID              [27] IMPLICIT OCTET STRING ( SIZE( 3 ) ) OPTIONAL,
   sUPIunauthenticatedFlag      [28] IMPLICIT NULL OPTIONAL,
   dNNSelectionMode             [29] IMPLICIT DNNSelectionMode OPTIONAL}

RoamingQBCInformation ::= SET {
   multipleQFIcontainer     [0] IMPLICIT SEQUENCE  OF
      MultipleQFIContainer OPTIONAL,
   uPFID                    [1] IMPLICIT IA5String  ( SIZE( 1 .. 36 ) ) OPTIONAL,
   roamingChargingProfile   [2] IMPLICIT RoamingChargingProfile OPTIONAL}

SMSChargingInformation ::= SET {
   sMSNodeAddress              [0] IMPLICIT OCTET STRING ( SIZE( 1 .. 20 ) ),
   originatorInfo              [1] IMPLICIT OriginatorInfo OPTIONAL,
   recipientInfos              [2] IMPLICIT SEQUENCE  OF
      RecipientInfos OPTIONAL,
   userEquipmentInfo           [3] IMPLICIT SubscriberEquipmentNumber OPTIONAL,
   userLocationInformation     [4] IMPLICIT OCTET STRING OPTIONAL,
   uETimeZone                  [5] IMPLICIT OCTET STRING ( SIZE( 2 ) ) OPTIONAL,
   rATType                     [6] IMPLICIT INTEGER ( 0 .. 255 ) OPTIONAL,
   sMSCAddress                 [7] IMPLICIT OCTET STRING ( SIZE( 1 .. 20 ) ) OPTIONAL,
   eventtimestamp              [8] IMPLICIT OCTET STRING ( SIZE( 9 ) ),
   sMDataCodingScheme          [20] IMPLICIT INTEGER OPTIONAL,
   sMMessageType               [21] IMPLICIT ENUMERATED {
      submission          ( 0 ),
      deliveryReport      ( 1 ),
      sMServiceRequest    ( 2 ),
      delivery            ( 3 ),
      t4DeviceTrigger     ( 4 ),
      sMDeviceTrigger     ( 5 ) } OPTIONAL,
   sMReplyPathRequested        [22] IMPLICIT SMReplyPathRequested OPTIONAL,
   sMUserDataHeader            [23] IMPLICIT OCTET STRING OPTIONAL,
   sMSStatus                   [24] IMPLICIT OCTET STRING ( SIZE( 1 ) ) OPTIONAL,
   sMDischargeTime             [25] IMPLICIT OCTET STRING ( SIZE( 9 ) ) OPTIONAL,
   sMTotalNumber               [26] IMPLICIT INTEGER OPTIONAL,
   sMServiceType               [27] IMPLICIT SMServiceType OPTIONAL,
   sMSequenceNumber            [28] IMPLICIT INTEGER OPTIONAL,
   sMSResult                   [29] Diagnostics OPTIONAL,
   submissionTime              [30] IMPLICIT OCTET STRING ( SIZE( 9 ) ) OPTIONAL,
   sMPriority                  [31] IMPLICIT ENUMERATED {
      low         ( 0 ),
      normal      ( 1 ),
      high        ( 2 ) } OPTIONAL,
   messageReference            [32] IMPLICIT OCTET STRING,
   messageSize                 [33] IMPLICIT INTEGER OPTIONAL,
   messageClass                [34] IMPLICIT ENUMERATED {
      personal               ( 0 ),
      advertisement          ( 1 ),
      information-service    ( 2 ),
      auto                   ( 3 ) } OPTIONAL,
   sMdeliveryReportRequested   [35] IMPLICIT SMdeliveryReportRequested OPTIONAL}

PDUContainerInformation ::= SEQUENCE {
   chargingRuleBaseName                 [0] IMPLICIT IA5String  OPTIONAL,
   aFCorrelationInformation             [1] IMPLICIT OCTET STRING OPTIONAL,
   timeOfFirstUsage                     [2] IMPLICIT OCTET STRING ( SIZE( 9 ) ) OPTIONAL,
   timeOfLastUsage                      [3] IMPLICIT OCTET STRING ( SIZE( 9 ) ) OPTIONAL,
   qoSInformation                       [4] IMPLICIT FiveGQoSInformation OPTIONAL,
   userLocationInformation              [5] IMPLICIT OCTET STRING OPTIONAL,
   presenceReportingAreaInfo            [6] IMPLICIT PresenceReportingAreaInfo OPTIONAL,
   rATType                              [7] IMPLICIT INTEGER ( 0 .. 255 ) OPTIONAL,
   sponsorIdentity                      [8] IMPLICIT OCTET STRING OPTIONAL,
   applicationServiceProviderIdentity   [9] IMPLICIT OCTET STRING OPTIONAL,
   servingNetworkFunctionID             [10] IMPLICIT SEQUENCE  OF
      ServingNetworkFunctionID OPTIONAL,
   uETimeZone                           [11] IMPLICIT OCTET STRING ( SIZE( 2 ) ) OPTIONAL,
   threeGPPPSDataOffStatus              [12] IMPLICIT ThreeGPPPSDataOffStatus OPTIONAL}

MultipleQFIContainer ::= SEQUENCE {
   qosFlowId                   [0] IMPLICIT INTEGER OPTIONAL,
   triggers                    [1] IMPLICIT SEQUENCE  OF
      Trigger,
   triggerTimeStamp            [2] IMPLICIT OCTET STRING ( SIZE( 9 ) ) OPTIONAL,
   dataTotalVolume             [3] IMPLICIT INTEGER OPTIONAL,
   dataVolumeUplink            [4] IMPLICIT INTEGER OPTIONAL,
   dataVolumeDownlink          [5] IMPLICIT INTEGER OPTIONAL,
   localSequenceNumber         [6] IMPLICIT INTEGER ( 0 .. 4294967295 ) OPTIONAL,
   timeOfFirstUsage            [8] IMPLICIT OCTET STRING ( SIZE( 9 ) ) OPTIONAL,
   timeOfLastUsage             [9] IMPLICIT OCTET STRING ( SIZE( 9 ) ) OPTIONAL,
   qoSInformation              [10] IMPLICIT FiveGQoSInformation OPTIONAL,
   userLocationInformation     [11] IMPLICIT OCTET STRING OPTIONAL,
   uETimeZone                  [12] IMPLICIT OCTET STRING ( SIZE( 2 ) ) OPTIONAL,
   presenceReportingAreaInfo   [13] IMPLICIT PresenceReportingAreaInfo OPTIONAL,
   rATType                     [14] IMPLICIT INTEGER ( 0 .. 255 ) OPTIONAL,
   reportTime                  [15] IMPLICIT OCTET STRING ( SIZE( 9 ) ),
   servingNetworkFunctionID    [16] IMPLICIT SEQUENCE  OF
      ServingNetworkFunctionID OPTIONAL,
   threeGPPPSDataOffStatus     [17] IMPLICIT ThreeGPPPSDataOffStatus OPTIONAL}

AllocationRetentionPriority ::= SEQUENCE {
   priorityLevel             [1] IMPLICIT INTEGER,
   preemptionCapability      [2] IMPLICIT PreemptionCapability,
   preemptionVulnerability   [3] IMPLICIT PreemptionVulnerability}

AMFID      ::= OCTET STRING ( SIZE( 6 ) )

AuthorizedQoSInformation ::= SEQUENCE {
   fiveQi            [1] IMPLICIT INTEGER,
   aRP               [2] IMPLICIT AllocationRetentionPriority,
   priorityLevel     [3] IMPLICIT INTEGER OPTIONAL,
   averWindow        [4] IMPLICIT INTEGER OPTIONAL,
   maxDataBurstVol   [5] IMPLICIT INTEGER OPTIONAL}

Bitrate    ::= OCTET STRING

ChargingSessionIdentifier ::= OCTET STRING

DataNetworkNameIdentifier ::= IA5String  ( SIZE( 1 .. 63 ) )

DNNSelectionMode ::= ENUMERATED {
   uEorNetworkProvidedSubscriptionVerified    ( 0 ),
   uEProvidedSubscriptionNotVerified          ( 1 ),
   networkProvidedSubscriptionNotVerified     ( 2 ) }

FiveGQoSInformation ::= SEQUENCE {
   fiveQi                   [1] IMPLICIT INTEGER,
   aRP                      [2] IMPLICIT AllocationRetentionPriority,
   qoSNotificationControl   [3] IMPLICIT BOOLEAN OPTIONAL,
   reflectiveQos            [4] IMPLICIT BOOLEAN OPTIONAL,
   maxbitrateUL             [5] IMPLICIT OCTET STRING OPTIONAL,
   maxbitrateDL             [6] IMPLICIT OCTET STRING OPTIONAL,
   guaranteedbitrateUL      [7] IMPLICIT OCTET STRING OPTIONAL,
   guaranteedbitrateDL      [8] IMPLICIT OCTET STRING OPTIONAL,
   priorityLevel            [9] IMPLICIT INTEGER OPTIONAL,
   averWindow               [10] IMPLICIT INTEGER OPTIONAL,
   maxDataBurstVol          [11] IMPLICIT INTEGER OPTIONAL,
   maxPacketLossRateDL      [12] IMPLICIT INTEGER OPTIONAL,
   maxPacketLossRateUL      [13] IMPLICIT INTEGER OPTIONAL}

MultipleUnitUsage ::= SEQUENCE {
   ratingGroup          [0] IMPLICIT INTEGER,
   usedUnitContainers   [1] IMPLICIT SEQUENCE  OF
      UsedUnitContainer OPTIONAL,
   uPFID                [2] IMPLICIT IA5String  ( SIZE( 1 .. 36 ) ) OPTIONAL}

NetworkFunctionality ::= ENUMERATED {
   cHF         ( 0 ),
   sMF         ( 1 ),
   aMF         ( 2 ),
   sMSF        ( 3 ) }

NetworkFunctionInformation ::= SEQUENCE {
   networkFunctionality            [0] IMPLICIT NetworkFunctionality,
   networkFunctionName             [1] IMPLICIT IA5String  ( SIZE( 1 .. 36 ) ) OPTIONAL,
   networkFunctionIPv4Address      [2] IPAddress OPTIONAL,
   networkFunctionPLMNIdentifier   [3] IMPLICIT OCTET STRING ( SIZE( 3 ) ) OPTIONAL,
   networkFunctionIPv6Address      [4] IPAddress,
   networkFunctionFQDN             [5] NodeAddress}

NetworkFunctionName ::= IA5String  ( SIZE( 1 .. 36 ) )

NetworkSliceInstanceID ::= SEQUENCE {
   sST        [0] IMPLICIT INTEGER ( 0 .. 255 ),
   sD         [1] IMPLICIT OCTET STRING ( SIZE( 3 ) ) OPTIONAL}

NGRANSecondaryRATType ::= OCTET STRING

NGRANSecondaryRATUsageReport ::= SEQUENCE {
   nGRANSecondaryRATType   [0] IMPLICIT OCTET STRING OPTIONAL,
   qosFlowsUsageReports    [1] IMPLICIT SEQUENCE  OF
      QosFlowsUsageReport OPTIONAL}

QoSFlowId  ::= INTEGER

QosFlowsUsageReport ::= SEQUENCE {
   qosFlowId            [0] IMPLICIT INTEGER OPTIONAL,
   startTime            [1] IMPLICIT OCTET STRING ( SIZE( 9 ) ),
   endTime              [2] IMPLICIT OCTET STRING ( SIZE( 9 ) ),
   dataVolumeDownlink   [3] IMPLICIT INTEGER,
   dataVolumeUplink     [4] IMPLICIT INTEGER}

PartialRecordMethod ::= ENUMERATED {
   default       ( 0 ),
   individual    ( 1 ) }

PDUAddress ::= SEQUENCE {
   pDUIPv4Address             [0] IPAddress OPTIONAL,
   pDUIPv6AddresswithPrefix   [1] IPAddress OPTIONAL,
   iPV4dynamicAddressFlag     [2] IMPLICIT BOOLEAN OPTIONAL,
   iPV6dynamicPrefixFlag      [3] IMPLICIT BOOLEAN OPTIONAL}

PDUSessionId ::= INTEGER ( 0 .. 255 )

PDUSessionType ::= ENUMERATED {
   iPv4v6          ( 0 ),
   iPv4            ( 1 ),
   iPv6            ( 2 ),
   unstructured    ( 3 ),
   ethernet        ( 4 ) }

PreemptionCapability ::= ENUMERATED {
   nOT-PREEMPT    ( 0 ),
   mAY-PREEMPT    ( 1 ) }

PreemptionVulnerability ::= ENUMERATED {
   nOT-PREEMPTABLE    ( 0 ),
   pREEMPTABLE        ( 1 ) }

RatingIndicator ::= BOOLEAN

RoamingChargingProfile ::= SEQUENCE {
   roamingTriggers       [0] IMPLICIT SEQUENCE  OF
      RoamingTrigger OPTIONAL,
   partialRecordMethod   [1] IMPLICIT PartialRecordMethod OPTIONAL}

RoamerInOut ::= ENUMERATED {
   roamerInBound     ( 0 ),
   roamerOutBound    ( 1 ) }

RoamingTrigger ::= SEQUENCE {
   trigger                   [0] IMPLICIT SMFTrigger OPTIONAL,
   triggerCategory           [1] IMPLICIT TriggerCategory OPTIONAL,
   timeLimit                 [2] IMPLICIT INTEGER OPTIONAL,
   volumeLimit               [3] IMPLICIT INTEGER OPTIONAL,
   maxNbChargingConditions   [4] IMPLICIT INTEGER OPTIONAL}

ServingNetworkFunctionID ::= SEQUENCE {
   servingNetworkFunctionInformation   [0] IMPLICIT NetworkFunctionInformation,
   aMFIdentifier                       [1] IMPLICIT OCTET STRING ( SIZE( 6 ) ) OPTIONAL}

SessionAMBR ::= SEQUENCE {
   ambrUL     [1] IMPLICIT OCTET STRING,
   ambrDL     [2] IMPLICIT OCTET STRING}

SliceDifferentiator ::= OCTET STRING ( SIZE( 3 ) )

SliceServiceType ::= INTEGER ( 0 .. 255 )

SMdeliveryReportRequested ::= ENUMERATED {
   yes         ( 0 ),
   no          ( 1 ) }

SMFTrigger ::= INTEGER {
   startOfPDUSession                           ( 1 ),
   startOfServiceDataFlowNoSession             ( 2 ),
   qoSChange                                   ( 100 ),
   userLocationChange                          ( 101 ),
   servingNodeChange                           ( 102 ),
   presenceReportingAreaChange                 ( 103 ),
   threeGPPPSDataOffStatusChange               ( 104 ),
   tariffTimeChange                            ( 105 ),
   uETimeZoneChange                            ( 106 ),
   pLMNChange                                  ( 107 ),
   rATTypeChange                               ( 108 ),
   sessionAMBRChange                           ( 109 ),
   additionOfUPF                               ( 110 ),
   removalOfUPF                                ( 111 ),
   gFBRGuaranteedStatusChange                  ( 115 ),
   pDUSessionExpiryDataTimeLimit               ( 200 ),
   pDUSessionExpiryDataVolumeLimit             ( 201 ),
   pDUSessionExpiryDataEventLimit              ( 202 ),
   pDUSessionExpiryChargingConditionChanges    ( 203 ),
   ratingGroupDataTimeLimit                    ( 300 ),
   ratingGroupDataVolumeLimit                  ( 301 ),
   ratingGroupDataEventLimit                   ( 302 ),
   timeThresholdReached                        ( 400 ),
   volumeThresholdReached                      ( 401 ),
   unitThresholdReached                        ( 402 ),
   timeQuotaExhausted                          ( 403 ),
   volumeQuotaExhausted                        ( 404 ),
   unitQuotaExhausted                          ( 405 ),
   expiryOfQuotaValidityTime                   ( 406 ),
   reAuthorizationRequest                      ( 407 ),
   startOfServiceDataFlowNoValidQuota          ( 408 ),
   otherQuotaType                              ( 409 ),
   terminationOfServiceDataFlow                ( 500 ),
   managementIntervention                      ( 501 ),
   unitCountInactivityTimer                    ( 502 ),
   endOfPDUSession                             ( 503 ),
   cHFResponseWithSessionTermination           ( 504 ),
   cHFAbortRequest                             ( 505 ),
   abnormalRelease                             ( 506 ),
   qoSFlowExpiryDataTimeLimit                  ( 600 ),
   qoSFlowExpiryDataVolumeLimit                ( 601 )}

SMReplyPathRequested ::= ENUMERATED {
   noReplyPathSet    ( 0 ),
   replyPathSet      ( 1 ) }

SMServiceType ::= INTEGER {
   contentProcessing                  ( 0 ),
   forwarding                         ( 1 ),
   forwardingMultipleSubscriptions    ( 2 ),
   filtering                          ( 3 ),
   receipt                            ( 4 ),
   networkStorage                     ( 5 ),
   toMultipleDestinations             ( 6 ),
   virtualPrivateNetwork              ( 7 ),
   autoreply                          ( 8 ),
   personalSignature                  ( 9 ),
   deferredDelivery                   ( 10 )}

SSCMode    ::= INTEGER {
   sSCMode1    ( 1 ),
   sSCMode2    ( 2 ),
   sSCMode3    ( 3 )}

SubscribedQoSInformation ::= SEQUENCE {
   fiveQi          [1] IMPLICIT INTEGER,
   aRP             [2] IMPLICIT AllocationRetentionPriority OPTIONAL,
   priorityLevel   [3] IMPLICIT INTEGER OPTIONAL}

Trigger    ::= CHOICE {
   sMFTrigger     [0] IMPLICIT SMFTrigger}

TriggerCategory ::= ENUMERATED {
   immediateReport    ( 0 ),
   deferredReport     ( 1 ) }

UsedUnitContainer ::= SEQUENCE {
   serviceIdentifier          [0] IMPLICIT INTEGER ( 0 .. 4294967295 ) OPTIONAL,
   time                       [1] IMPLICIT INTEGER OPTIONAL,
   triggers                   [2] IMPLICIT SEQUENCE  OF
      Trigger,
   triggerTimeStamp           [3] IMPLICIT OCTET STRING ( SIZE( 9 ) ) OPTIONAL,
   dataTotalVolume            [4] IMPLICIT INTEGER OPTIONAL,
   dataVolumeUplink           [5] IMPLICIT INTEGER OPTIONAL,
   dataVolumeDownlink         [6] IMPLICIT INTEGER OPTIONAL,
   serviceSpecificUnits       [7] IMPLICIT INTEGER OPTIONAL,
   eventTimeStamp             [8] IMPLICIT OCTET STRING ( SIZE( 9 ) ) OPTIONAL,
   localSequenceNumber        [9] IMPLICIT INTEGER ( 0 .. 4294967295 ) OPTIONAL,
   ratingIndicator            [10] IMPLICIT BOOLEAN OPTIONAL,
   pDUContainerInformation    [11] IMPLICIT PDUContainerInformation OPTIONAL,
   quotaManagementIndicator   [12] IMPLICIT BOOLEAN OPTIONAL}

UserLocationInformation ::= OCTET STRING


-- X.721 DMI-EXTENSION. The set is the standard form of the original
-- extensible empty table constraint ({, ...}) and does not change BER.
DMI-EXTENSION ::= CLASS {
    &id     OBJECT IDENTIFIER UNIQUE,
    &Value
}
WITH SYNTAX {
    TYPE &Value
    ID &id
}

ManagementExtensionSet DMI-EXTENSION ::= {...}

END
