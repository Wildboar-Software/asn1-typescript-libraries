-- Modified by Jonathan M. Wilbur to fix invalid syntax.
--     Expanded ASN1 Module 'MBMSChargingDataTypes'
--SIEMENS ASN.1 Compiler         R6.31  (Production_6.31)
--            Date: 2020-07-10 Time: 16:15:40

MBMSChargingDataTypes
{itu-t(0) identified-organization(4) etsi(0) mobileDomain(0) charging(5)
mbmsChargingDataTypes(8) asn1Module(0) version2(1)}
DEFINITIONS
::=
BEGIN

RecordType ::= INTEGER {
   moCallRecord              ( 0 ),
   mtCallRecord              ( 1 ),
   roamingRecord             ( 2 ),
   incGatewayRecord          ( 3 ),
   outGatewayRecord          ( 4 ),
   transitCallRecord         ( 5 ),
   moSMSRecord               ( 6 ),
   mtSMSRecord               ( 7 ),
   moSMSIWRecord             ( 8 ),
   mtSMSGWRecord             ( 9 ),
   ssActionRecord            ( 10 ),
   hlrIntRecord              ( 11 ),
   locUpdateHLRRecord        ( 12 ),
   locUpdateVLRRecord        ( 13 ),
   commonEquipRecord         ( 14 ),
   moTraceRecord             ( 15 ),
   mtTraceRecord             ( 16 ),
   termCAMELRecord           ( 17 ),
   sgsnPDPRecord             ( 18 ),
   sgsnMMRecord              ( 20 ),
   sgsnSMORecord             ( 21 ),
   sgsnSMTRecord             ( 22 ),
   mtLCSRecord               ( 23 ),
   moLCSRecord               ( 24 ),
   niLCSRecord               ( 25 ),
   sgsnMTLCSRecord           ( 26 ),
   sgsnMOLCSRecord           ( 27 ),
   sgsnNILCSRecord           ( 28 ),
   mMO1SRecord               ( 30 ),
   mMO4FRqRecord             ( 31 ),
   mMO4FRsRecord             ( 32 ),
   mMO4DRecord               ( 33 ),
   mMO1DRecord               ( 34 ),
   mMO4RRecord               ( 35 ),
   mMO1RRecord               ( 36 ),
   mMOMDRecord               ( 37 ),
   mMR4FRecord               ( 38 ),
   mMR1NRqRecord             ( 39 ),
   mMR1NRsRecord             ( 40 ),
   mMR1RtRecord              ( 41 ),
   mMR1AFRecord              ( 42 ),
   mMR4DRqRecord             ( 43 ),
   mMR4DRsRecord             ( 44 ),
   mMR1RRRecord              ( 45 ),
   mMR4RRqRecord             ( 46 ),
   mMR4RRsRecord             ( 47 ),
   mMRMDRecord               ( 48 ),
   mMFRecord                 ( 49 ),
   mMBx1SRecord              ( 50 ),
   mMBx1VRecord              ( 51 ),
   mMBx1URecord              ( 52 ),
   mMBx1DRecord              ( 53 ),
   mM7SRecord                ( 54 ),
   mM7DRqRecord              ( 55 ),
   mM7DRsRecord              ( 56 ),
   mM7CRecord                ( 57 ),
   mM7RRecord                ( 58 ),
   mM7DRRqRecord             ( 59 ),
   mM7DRRsRecord             ( 60 ),
   mM7RRqRecord              ( 61 ),
   mM7RRsRecord              ( 62 ),
   sCSCFRecord               ( 63 ),
   pCSCFRecord               ( 64 ),
   iCSCFRecord               ( 65 ),
   mRFCRecord                ( 66 ),
   mGCFRecord                ( 67 ),
   bGCFRecord                ( 68 ),
   aSRecord                  ( 69 ),
   eCSCFRecord               ( 70 ),
   iBCFRecord                ( 82 ),
   tRFRecord                 ( 89 ),
   tFRecord                  ( 90 ),
   aTCFRecord                ( 91 ),
   lCSGMORecord              ( 71 ),
   lCSRGMTRecord             ( 72 ),
   lCSHGMTRecord             ( 73 ),
   lCSVGMTRecord             ( 74 ),
   lCSGNIRecord              ( 75 ),
   sgsnMBMSRecord            ( 76 ),
   ggsnMBMSRecord            ( 77 ),
   gwMBMSRecord              ( 86 ),
   sUBBMSCRecord             ( 78 ),
   cONTENTBMSCRecord         ( 79 ),
   pPFRecord                 ( 80 ),
   cPFRecord                 ( 81 ),
   sGWRecord                 ( 84 ),
   pGWRecord                 ( 85 ),
   tDFRecord                 ( 92 ),
   iPERecord                 ( 95 ),
   ePDGRecord                ( 96 ),
   tWAGRecord                ( 97 ),
   mMTelRecord               ( 83 ),
   mSCsRVCCRecord            ( 87 ),
   mMTRFRecord               ( 88 ),
   iCSRegisterRecord         ( 99 ),
   sCSMORecord               ( 93 ),
   sCSMTRecord               ( 94 ),
   pFDDRecord                ( 100 ),
   pFEDRecord                ( 101 ),
   pFDCRecord                ( 102 ),
   mECORecord                ( 103 ),
   mERERecord                ( 104 ),
   cPDTSCERecord             ( 105 ),
   cPDTSNNRecord             ( 106 ),
   sCDVTT4Record             ( 110 ),
   sCSMOT4Record             ( 111 ),
   iSMSMORecord              ( 112 ),
   iSMSMTRecord              ( 113 ),
   eASCERecord               ( 120 ),
   chargingFunctionRecord    ( 200 )}

PositionMethodFailure-Diagnostic ::= ENUMERATED {
   congestion                                  ( 0 ),
   insufficientResources                       ( 1 ),
   insufficientMeasurementData                 ( 2 ),
   inconsistentMeasurementData                 ( 3 ),
   locationProcedureNotCompleted               ( 4 ),
   locationProcedureNotSupportedByTargetMS     ( 5 ),
   qoSNotAttainable                            ( 6 ),
   positionMethodNotAvailableInNetwork         ( 7 ),
   positionMethodNotAvailableInLocationArea    ( 8 ),
   ...  }

UnauthorizedLCSClient-Diagnostic ::= ENUMERATED {
   noAdditionalInformation                           ( 0 ),
   clientNotInMSPrivacyExceptionList                 ( 1 ),
   callToClientNotSetup                              ( 2 ),
   privacyOverrideNotApplicable                      ( 3 ),
   disallowedByLocalRegulatoryRequirements           ( 4 ),
   ... ,
   unauthorizedPrivacyClass                          ( 5 ),
   unauthorizedCallSessionUnrelatedExternalClient    ( 6 ),
   unauthorizedCallSessionRelatedExternalClient      ( 7 ) }

ChangeCondition ::= ENUMERATED {
   qoSChange                        ( 0 ),
   tariffTime                       ( 1 ),
   recordClosure                    ( 2 ),
   cGI-SAICHange                    ( 6 ),
   rAIChange                        ( 7 ),
   dT-Establishment                 ( 8 ),
   dT-Removal                       ( 9 ),
   eCGIChange                       ( 10 ),
   tAIChange                        ( 11 ),
   userLocationChange               ( 12 ),
   userCSGInformationChange         ( 13 ),
   presenceInPRAChange              ( 14 ),
   removalOfAccess                  ( 15 ),
   unusabilityOfAccess              ( 16 ),
   indirectChangeCondition          ( 17 ),
   userPlaneToUEChange              ( 18 ),
   servingPLMNRateControlChange     ( 19 ),
   threeGPPPSDataOffStatusChange    ( 20 ),
   aPNRateControlChange             ( 21 ) }

IPBinV6AddressWithPrefixLength ::= SEQUENCE {
   iPBinV6Address           OCTET STRING ( SIZE( 16 ) ),
   pDPAddressPrefixLength   INTEGER ( 1 .. 64 ) DEFAULT 64}

AccessCorrelationID ::= CHOICE {
   gPRS-Charging-Id                    [2] IMPLICIT INTEGER ( 0 .. 4294967295 ),
   accessNetworkChargingIdentifier     [4] IMPLICIT GraphicString}

IPTextRepresentedAddress ::= CHOICE {
   iPTextV4Address     [2] IMPLICIT IA5String  ( SIZE( 7 .. 15 ) ),
   iPTextV6Address     [3] IMPLICIT IA5String  ( SIZE( 15 .. 45 ) )}

IPBinV6AddressWithOrWithoutPrefixLength ::= CHOICE {
   iPBinV6Address               [1] IMPLICIT OCTET STRING ( SIZE( 16 ) ),
   iPBinV6AddressWithPrefix     [4] IMPLICIT IPBinV6AddressWithPrefixLength}

IPBinaryAddress ::= CHOICE {
   iPBinV4Address     [0] IMPLICIT OCTET STRING ( SIZE( 4 ) ),
   iPBinV6Address     IPBinV6AddressWithOrWithoutPrefixLength}

IPAddress ::= CHOICE {
   iPBinaryAddress              IPBinaryAddress,
   iPTextRepresentedAddress     IPTextRepresentedAddress}

PDPAddress ::= CHOICE {
   iPAddress     [0] IPAddress}

InvolvedParty ::= CHOICE {
   sIP-URI       [0] IMPLICIT GraphicString,
   tEL-URI       [1] IMPLICIT GraphicString,
   uRN           [2] IMPLICIT GraphicString,
   iSDN-E164     [3] IMPLICIT GraphicString}

ManagementExtension ::= SEQUENCE {
   identifier     DMI-EXTENSION.&id ({ManagementExtensionSet}) ,
   significance   [1] IMPLICIT BOOLEAN DEFAULT FALSE,
   information    [2] DMI-EXTENSION.&Value ({ManagementExtensionSet}{@.identifier}) }

SDP-Media-Components ::= SEQUENCE {
   sDP-Media-Name                 [0] IMPLICIT GraphicString OPTIONAL,
   sDP-Media-Descriptions         [1] IMPLICIT SEQUENCE  OF
      GraphicString OPTIONAL,
   accessCorrelationID            AccessCorrelationID OPTIONAL,
   localGWInsertedIndication      [5] IMPLICIT BOOLEAN OPTIONAL,
   iPRealmDefaultIndication       [6] IMPLICIT BOOLEAN OPTIONAL,
   transcoderInsertedIndication   [7] IMPLICIT BOOLEAN OPTIONAL}

BearerServiceDescription ::= SEQUENCE {
   sIP-Request-Timestamp             [0] IMPLICIT OCTET STRING ( SIZE( 9 ) ) OPTIONAL,
   sIP-Response-Timestamp            [1] IMPLICIT OCTET STRING ( SIZE( 9 ) ) OPTIONAL,
   sDP-Media-Components              [2] IMPLICIT SEQUENCE  OF
      SDP-Media-Components OPTIONAL,
   mediaInitiatorFlag                [3] IMPLICIT NULL OPTIONAL,
   sDP-Session-Description           [4] IMPLICIT SEQUENCE  OF
      GraphicString OPTIONAL,
   mediaInitiatorParty               [5] InvolvedParty OPTIONAL,
   sIP-Request-Timestamp-Fraction    [6] IMPLICIT INTEGER ( 0 .. 999 ) OPTIONAL,
   sIP-Response-Timestamp-Fraction   [7] IMPLICIT INTEGER ( 0 .. 999 ) OPTIONAL,
   sDP-Type                          [8] IMPLICIT ENUMERATED {
      sDP-offer     ( 0 ),
      sDP-answer    ( 1 ) } OPTIONAL}

ListOfTrafficVolumes ::= SEQUENCE {
   qosRequested              [1] IMPLICIT OCTET STRING ( SIZE( 4 .. 255 ) ) OPTIONAL,
   qosNegotiated             [2] IMPLICIT OCTET STRING ( SIZE( 4 .. 255 ) ) OPTIONAL,
   dataVolumeMBMSUplink      [3] IMPLICIT INTEGER OPTIONAL,
   dataVolumeMBMSDownlink    [4] IMPLICIT INTEGER,
   changeCondition           [5] IMPLICIT ChangeCondition,
   changeTime                [6] IMPLICIT OCTET STRING ( SIZE( 9 ) ),
   failureHandlingContinue   [7] IMPLICIT BOOLEAN OPTIONAL}

MBMSInformation ::= SET {
   tMGI                        [1] IMPLICIT OCTET STRING OPTIONAL,
   mBMSSessionIdentity         [2] IMPLICIT OCTET STRING ( SIZE( 1 ) ) OPTIONAL,
   mBMSServiceType             [3] IMPLICIT ENUMERATED {
      mULTICAST    ( 0 ),
      bROADCAST    ( 1 ) } OPTIONAL,
   mBMSUserServiceType         [4] IMPLICIT ENUMERATED {
      dOWNLOAD     ( 0 ),
      sTREAMING    ( 1 ) } OPTIONAL,
   mBMS2G3GIndicator           [5] IMPLICIT ENUMERATED {
      twoG               ( 0 ),
      threeG             ( 1 ),
      twoG-AND-threeG    ( 2 ) } OPTIONAL,
   fileRepairSupported         [6] IMPLICIT BOOLEAN OPTIONAL,
   rAI                         [7] IMPLICIT OCTET STRING ( SIZE( 1 ) ) OPTIONAL,
   mBMSServiceArea             [8] IMPLICIT OCTET STRING OPTIONAL,
   requiredMBMSBearerCaps      [9] IMPLICIT OCTET STRING ( SIZE( 3 .. 14 ) ) OPTIONAL,
   mBMSGWAddress               [10] IPAddress OPTIONAL,
   cNIPMulticastDistribution   [11] IMPLICIT ENUMERATED {
      nO-IP-MULTICAST    ( 0 ),
      iP-MULTICAST       ( 1 ) } OPTIONAL,
   mBMSDataTransferStart       [12] IMPLICIT OCTET STRING ( SIZE( 8 ) ) OPTIONAL,
   mBMSDataTransferStop        [13] IMPLICIT OCTET STRING ( SIZE( 8 ) ) OPTIONAL}

Diagnostics ::= CHOICE {
   gsm0408Cause                                [0] IMPLICIT INTEGER,
   gsm0902MapErrorValue                        [1] IMPLICIT INTEGER,
   itu-tQ767Cause                              [2] IMPLICIT INTEGER,
   networkSpecificCause                        [3] IMPLICIT ManagementExtension,
   manufacturerSpecificCause                   [4] IMPLICIT ManagementExtension,
   positionMethodFailureCause                  [5] IMPLICIT PositionMethodFailure-Diagnostic,
   unauthorizedLCSClientCause                  [6] IMPLICIT UnauthorizedLCSClient-Diagnostic,
   diameterResultCodeAndExperimentalResult     [7] IMPLICIT INTEGER}

MBMSRecord ::= CHOICE {
   sUBBMSCRecord         [78] IMPLICIT SUBBMSCRecord,
   cONTENTBMSCRecord     [79] IMPLICIT CONTENTBMSCRecord}

SUBBMSCRecord ::= SET {
   recordType                 [0] IMPLICIT RecordType,
   servedIMSI                 [1] IMPLICIT OCTET STRING ( SIZE( 3 .. 8 ) ),
   ggsnAddress                [2] IPAddress OPTIONAL,
   accessPointNameNI          [3] IMPLICIT IA5String  ( SIZE( 1 .. 63 ) ) OPTIONAL,
   servedPDPAddress           [4] PDPAddress OPTIONAL,
   listOfTrafficVolumes       [5] IMPLICIT SEQUENCE  OF
      ListOfTrafficVolumes OPTIONAL,
   recordOpeningTime          [6] IMPLICIT OCTET STRING ( SIZE( 9 ) ),
   duration                   [7] IMPLICIT INTEGER,
   causeForRecClosing         [8] IMPLICIT INTEGER {
      normalRelease                 ( 0 ),
      abnormalRelease               ( 4 ),
      volumeLimit                   ( 16 ),
      timeLimit                     ( 17 ),
      maxChangeCond                 ( 19 ),
      managementIntervention        ( 20 ),
      listofDownstreamNodeChange    ( 59 )},
   diagnostics                [9] Diagnostics OPTIONAL,
   recordSequenceNumber       [10] IMPLICIT INTEGER OPTIONAL,
   nodeID                     [11] IMPLICIT IA5String  ( SIZE( 1 .. 20 ) ) OPTIONAL,
   recordExtensions           [12] IMPLICIT SET  OF
      ManagementExtension OPTIONAL,
   localSequenceNumber        [13] IMPLICIT INTEGER ( 0 .. 4294967295 ) OPTIONAL,
   servedMSISDN               [14] IMPLICIT OCTET STRING ( SIZE( 1 .. 20 ) ) ( SIZE( 1 .. 9 ) ) OPTIONAL,
   bearerServiceDescription   [15] IMPLICIT BearerServiceDescription OPTIONAL,
   mbmsInformation            [16] IMPLICIT MBMSInformation OPTIONAL,
   serviceContextID           [17] IMPLICIT UTF8String OPTIONAL}

CONTENTBMSCRecord ::= SET {
   recordType                 [0] IMPLICIT RecordType,
   contentProviderId          [1] IMPLICIT GraphicString,
   listofDownstreamNodes      [2] IMPLICIT SEQUENCE  OF
      IPAddress,
   accessPointNameNI          [3] IMPLICIT IA5String  ( SIZE( 1 .. 63 ) ) OPTIONAL,
   servedPDPAddress           [4] PDPAddress OPTIONAL,
   listOfTrafficVolumes       [5] IMPLICIT SEQUENCE  OF
      ListOfTrafficVolumes OPTIONAL,
   recordOpeningTime          [6] IMPLICIT OCTET STRING ( SIZE( 9 ) ),
   duration                   [7] IMPLICIT INTEGER,
   causeForRecClosing         [8] IMPLICIT INTEGER {
      normalRelease                 ( 0 ),
      abnormalRelease               ( 4 ),
      volumeLimit                   ( 16 ),
      timeLimit                     ( 17 ),
      maxChangeCond                 ( 19 ),
      managementIntervention        ( 20 ),
      listofDownstreamNodeChange    ( 59 )},
   diagnostics                [9] Diagnostics OPTIONAL,
   recordSequenceNumber       [10] IMPLICIT INTEGER OPTIONAL,
   nodeID                     [11] IMPLICIT IA5String  ( SIZE( 1 .. 20 ) ) OPTIONAL,
   recordExtensions           [12] IMPLICIT SET  OF
      ManagementExtension OPTIONAL,
   localSequenceNumber        [13] IMPLICIT INTEGER ( 0 .. 4294967295 ) OPTIONAL,
   recipientAddressList       [14] IMPLICIT SEQUENCE  OF
      OCTET STRING ( SIZE( 1 .. 20 ) ) ( SIZE( 1 .. 9 ) ),
   bearerServiceDescription   [15] IMPLICIT BearerServiceDescription OPTIONAL,
   mbmsInformation            [16] IMPLICIT MBMSInformation OPTIONAL,
   serviceContextID           [17] IMPLICIT UTF8String OPTIONAL,
   servedpdpPDNType           [18] IMPLICIT OCTET STRING ( SIZE( 2 ) ) OPTIONAL}

MBMSCauseForRecClosing ::= INTEGER {
   normalRelease                 ( 0 ),
   abnormalRelease               ( 4 ),
   volumeLimit                   ( 16 ),
   timeLimit                     ( 17 ),
   maxChangeCond                 ( 19 ),
   managementIntervention        ( 20 ),
   listofDownstreamNodeChange    ( 59 )}


-- X.721 DMI-EXTENSION. The set is the standard form of the original
-- extensible empty table constraint ({, ...}) and does not change BER.
DMI-EXTENSION ::= CLASS {
    &id     OBJECT IDENTIFIER UNIQUE,
    &Value
}
WITH SYNTAX {
    TYPE &Value
    ID &id
}

ManagementExtensionSet DMI-EXTENSION ::= {...}

END
