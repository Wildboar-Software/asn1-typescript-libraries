-- Modified by Jonathan M. Wilbur to fix invalid syntax.
--      Expanded ASN1 Module 'CSChargingDataTypes'
--SIEMENS ASN.1 Compiler         R6.31  (Production_6.31)
--            Date: 2020-07-10 Time: 16:14:24

CSChargingDataTypes
{itu-t(0) identified-organization(4) etsi(0) mobileDomain(0) charging(5)
csChargingDataTypes(1) asn1Module(0) version2(1)}
DEFINITIONS
::=
BEGIN

CauseForTerm ::= INTEGER {
   normalRelease                       ( 0 ),
   partialRecord                       ( 1 ),
   partialRecordCallReestablishment    ( 2 ),
   unsuccessfulCallAttempt             ( 3 ),
   abnormalRelease                     ( 4 ),
   cAMELInitCallRelease                ( 5 ),
   unauthorizedRequestingNetwork       ( 52 ),
   unauthorizedLCSClient               ( 53 ),
   positionMethodFailure               ( 54 ),
   unknownOrUnreachableLCSClient       ( 58 )}

RecordType ::= INTEGER {
   moCallRecord              ( 0 ),
   mtCallRecord              ( 1 ),
   roamingRecord             ( 2 ),
   incGatewayRecord          ( 3 ),
   outGatewayRecord          ( 4 ),
   transitCallRecord         ( 5 ),
   moSMSRecord               ( 6 ),
   mtSMSRecord               ( 7 ),
   moSMSIWRecord             ( 8 ),
   mtSMSGWRecord             ( 9 ),
   ssActionRecord            ( 10 ),
   hlrIntRecord              ( 11 ),
   locUpdateHLRRecord        ( 12 ),
   locUpdateVLRRecord        ( 13 ),
   commonEquipRecord         ( 14 ),
   moTraceRecord             ( 15 ),
   mtTraceRecord             ( 16 ),
   termCAMELRecord           ( 17 ),
   sgsnPDPRecord             ( 18 ),
   sgsnMMRecord              ( 20 ),
   sgsnSMORecord             ( 21 ),
   sgsnSMTRecord             ( 22 ),
   mtLCSRecord               ( 23 ),
   moLCSRecord               ( 24 ),
   niLCSRecord               ( 25 ),
   sgsnMTLCSRecord           ( 26 ),
   sgsnMOLCSRecord           ( 27 ),
   sgsnNILCSRecord           ( 28 ),
   mMO1SRecord               ( 30 ),
   mMO4FRqRecord             ( 31 ),
   mMO4FRsRecord             ( 32 ),
   mMO4DRecord               ( 33 ),
   mMO1DRecord               ( 34 ),
   mMO4RRecord               ( 35 ),
   mMO1RRecord               ( 36 ),
   mMOMDRecord               ( 37 ),
   mMR4FRecord               ( 38 ),
   mMR1NRqRecord             ( 39 ),
   mMR1NRsRecord             ( 40 ),
   mMR1RtRecord              ( 41 ),
   mMR1AFRecord              ( 42 ),
   mMR4DRqRecord             ( 43 ),
   mMR4DRsRecord             ( 44 ),
   mMR1RRRecord              ( 45 ),
   mMR4RRqRecord             ( 46 ),
   mMR4RRsRecord             ( 47 ),
   mMRMDRecord               ( 48 ),
   mMFRecord                 ( 49 ),
   mMBx1SRecord              ( 50 ),
   mMBx1VRecord              ( 51 ),
   mMBx1URecord              ( 52 ),
   mMBx1DRecord              ( 53 ),
   mM7SRecord                ( 54 ),
   mM7DRqRecord              ( 55 ),
   mM7DRsRecord              ( 56 ),
   mM7CRecord                ( 57 ),
   mM7RRecord                ( 58 ),
   mM7DRRqRecord             ( 59 ),
   mM7DRRsRecord             ( 60 ),
   mM7RRqRecord              ( 61 ),
   mM7RRsRecord              ( 62 ),
   sCSCFRecord               ( 63 ),
   pCSCFRecord               ( 64 ),
   iCSCFRecord               ( 65 ),
   mRFCRecord                ( 66 ),
   mGCFRecord                ( 67 ),
   bGCFRecord                ( 68 ),
   aSRecord                  ( 69 ),
   eCSCFRecord               ( 70 ),
   iBCFRecord                ( 82 ),
   tRFRecord                 ( 89 ),
   tFRecord                  ( 90 ),
   aTCFRecord                ( 91 ),
   lCSGMORecord              ( 71 ),
   lCSRGMTRecord             ( 72 ),
   lCSHGMTRecord             ( 73 ),
   lCSVGMTRecord             ( 74 ),
   lCSGNIRecord              ( 75 ),
   sgsnMBMSRecord            ( 76 ),
   ggsnMBMSRecord            ( 77 ),
   gwMBMSRecord              ( 86 ),
   sUBBMSCRecord             ( 78 ),
   cONTENTBMSCRecord         ( 79 ),
   pPFRecord                 ( 80 ),
   cPFRecord                 ( 81 ),
   sGWRecord                 ( 84 ),
   pGWRecord                 ( 85 ),
   tDFRecord                 ( 92 ),
   iPERecord                 ( 95 ),
   ePDGRecord                ( 96 ),
   tWAGRecord                ( 97 ),
   mMTelRecord               ( 83 ),
   mSCsRVCCRecord            ( 87 ),
   mMTRFRecord               ( 88 ),
   iCSRegisterRecord         ( 99 ),
   sCSMORecord               ( 93 ),
   sCSMTRecord               ( 94 ),
   pFDDRecord                ( 100 ),
   pFEDRecord                ( 101 ),
   pFDCRecord                ( 102 ),
   mECORecord                ( 103 ),
   mERERecord                ( 104 ),
   cPDTSCERecord             ( 105 ),
   cPDTSNNRecord             ( 106 ),
   sCDVTT4Record             ( 110 ),
   sCSMOT4Record             ( 111 ),
   iSMSMORecord              ( 112 ),
   iSMSMTRecord              ( 113 ),
   eASCERecord               ( 120 ),
   chargingFunctionRecord    ( 200 )}

SystemType ::= ENUMERATED {
   unknown     ( 0 ),
   iuUTRAN     ( 1 ),
   gERAN       ( 2 ) }

DefaultCallHandling ::= ENUMERATED {
   continueCall    ( 0 ),
   releaseCall     ( 1 ),
   ...  }

LCSClientType ::= ENUMERATED {
   emergencyServices          ( 0 ),
   valueAddedServices         ( 1 ),
   plmnOperatorServices       ( 2 ),
   lawfulInterceptServices    ( 3 ),
   ...  }

IsdnBasicService ::= ENUMERATED {
   allServices                                               ( 0 ),
   speech                                                    ( 1 ),
   unrestrictedDigitalInformation                            ( 2 ),
   audio3k1Hz                                                ( 3 ),
   unrestrictedDigitalInformationWithTonesAndAnouncements    ( 4 ),
   telephony3k1Hz                                            ( 32 ),
   teletex                                                   ( 33 ),
   telefaxGroup4Class1                                       ( 34 ),
   videotexSyntaxBased                                       ( 35 ),
   videotelephony                                            ( 36 ),
   telefaxGroup2-3                                           ( 37 ),
   telephony7kHz                                             ( 38 ) }

PositionMethodFailure-Diagnostic ::= ENUMERATED {
   congestion                                  ( 0 ),
   insufficientResources                       ( 1 ),
   insufficientMeasurementData                 ( 2 ),
   inconsistentMeasurementData                 ( 3 ),
   locationProcedureNotCompleted               ( 4 ),
   locationProcedureNotSupportedByTargetMS     ( 5 ),
   qoSNotAttainable                            ( 6 ),
   positionMethodNotAvailableInNetwork         ( 7 ),
   positionMethodNotAvailableInLocationArea    ( 8 ),
   ...  }

UnauthorizedLCSClient-Diagnostic ::= ENUMERATED {
   noAdditionalInformation                           ( 0 ),
   clientNotInMSPrivacyExceptionList                 ( 1 ),
   callToClientNotSetup                              ( 2 ),
   privacyOverrideNotApplicable                      ( 3 ),
   disallowedByLocalRegulatoryRequirements           ( 4 ),
   ... ,
   unauthorizedPrivacyClass                          ( 5 ),
   unauthorizedCallSessionUnrelatedExternalClient    ( 6 ),
   unauthorizedCallSessionRelatedExternalClient      ( 7 ) }

Molr-Type ::= ENUMERATED {
   locationEstimate                            ( 0 ),
   assistanceData                              ( 1 ),
   deCipheringKeys                             ( 2 ),
   ... ,
   deferredMo-lrTTTPInitiation                 ( 3 ),
   deferredMo-lrSelfLocationInitiation         ( 4 ),
   deferredMt-lrOrmo-lrTTTPLocationEstimate    ( 5 ),
   deferredMt-lrOrmo-lrCancellation            ( 6 ),
   periodicEvent                               ( 7 ),
   enteringAreaEvent                           ( 8 ),
   leavingAreaEvent                            ( 9 ),
   beingInsideAreaEvent                        ( 10 ),
   motionEvent                                 ( 11 ),
   maximumIntervalExpirationEvent              ( 12 ) }

Pcs-Extensions ::= SEQUENCE {
   ... }

Ae-title-form1 ::= CHOICE {
   rdnSequence     SEQUENCE  OF
      SET  OF
         Pcs-Extensions}

OsApplication ::= CHOICE {
   ae-title-form1     Ae-title-form1,
   ae-title-form2     OBJECT IDENTIFIER,
   ...}

IdValue ::= SEQUENCE {
   id         CMIP-AVA.&id ({AvaSet}) ,
   value      CMIP-AVA.&Value ({AvaSet}{@.id}) }

IPBinV6AddressWithPrefixLength ::= SEQUENCE {
   iPBinV6Address           OCTET STRING ( SIZE( 16 ) ),
   pDPAddressPrefixLength   INTEGER ( 1 .. 64 ) DEFAULT 64}

InterOperatorIdentifiers ::= SEQUENCE {
   originatingIOI   [0] IMPLICIT GraphicString OPTIONAL,
   terminatingIOI   [1] IMPLICIT GraphicString OPTIONAL}

BasicService ::= CHOICE {
   bearerService     [2] IMPLICIT OCTET STRING ( SIZE( 1 ) ),
   teleservice       [3] IMPLICIT OCTET STRING ( SIZE( 1 ) )}

IPTextRepresentedAddress ::= CHOICE {
   iPTextV4Address     [2] IMPLICIT IA5String  ( SIZE( 7 .. 15 ) ),
   iPTextV6Address     [3] IMPLICIT IA5String  ( SIZE( 15 .. 45 ) )}

IPBinV6AddressWithOrWithoutPrefixLength ::= CHOICE {
   iPBinV6Address               [1] IMPLICIT OCTET STRING ( SIZE( 16 ) ),
   iPBinV6AddressWithPrefix     [4] IMPLICIT IPBinV6AddressWithPrefixLength}

IPBinaryAddress ::= CHOICE {
   iPBinV4Address     [0] IMPLICIT OCTET STRING ( SIZE( 4 ) ),
   iPBinV6Address     IPBinV6AddressWithOrWithoutPrefixLength}

IPAddress ::= CHOICE {
   iPBinaryAddress              IPBinaryAddress,
   iPTextRepresentedAddress     IPTextRepresentedAddress}

NodeAddress ::= CHOICE {
   iPAddress      [0] IPAddress,
   domainName     [1] IMPLICIT GraphicString}

PrivateExtension ::= SEQUENCE {
   extId      MAP-EXTENSION.&extensionId ({ExtensionSet}) ,
   extType    MAP-EXTENSION.&ExtensionType ({ExtensionSet}{@extId})  OPTIONAL}

ExtensionContainer ::= SEQUENCE {
   privateExtensionList   [0] IMPLICIT SEQUENCE  ( SIZE( 1 .. 10 ) ) OF
      PrivateExtension OPTIONAL,
   pcs-Extensions         [1] IMPLICIT Pcs-Extensions OPTIONAL,
   ... }

LCSClientExternalID ::= SEQUENCE {
   externalAddress      [0] IMPLICIT OCTET STRING ( SIZE( 1 .. 20 ) ) ( SIZE( 1 .. 9 ) ) OPTIONAL,
   extensionContainer   [1] IMPLICIT ExtensionContainer OPTIONAL,
   ... }

LocationAreaAndCell ::= SEQUENCE {
   locationAreaCode   [0] IMPLICIT OCTET STRING ( SIZE( 2 ) ),
   cellId             [1] IMPLICIT OCTET STRING ( SIZE( 2 ) ),
   mCC-MNC            [2] IMPLICIT OCTET STRING ( SIZE( 3 ) ) OPTIONAL}

ManagementExtension ::= SEQUENCE {
   identifier     DMI-EXTENSION.&id ({ManagementExtensionSet}) ,
   significance   [1] IMPLICIT BOOLEAN DEFAULT FALSE,
   information    [2] DMI-EXTENSION.&Value ({ManagementExtensionSet}{@.identifier}) }

LCSClientIdentity ::= SEQUENCE {
   lcsClientExternalID   [0] IMPLICIT LCSClientExternalID OPTIONAL,
   lcsClientDialedByMS   [1] IMPLICIT OCTET STRING ( SIZE( 1 .. 20 ) ) OPTIONAL,
   lcsClientInternalID   [2] IMPLICIT ENUMERATED {
      broadcastService             ( 0 ),
      o-andM-HPLMN                 ( 1 ),
      o-andM-VPLMN                 ( 2 ),
      anonymousLocation            ( 3 ),
      targetMSsubscribedService    ( 4 ),
      ...  } OPTIONAL}

LocationType ::= SEQUENCE {
   locationEstimateType        [0] IMPLICIT ENUMERATED {
      currentLocation                 ( 0 ),
      currentOrLastKnownLocation      ( 1 ),
      initialLocation                 ( 2 ),
      ... ,
      activateDeferredLocation        ( 3 ),
      cancelDeferredLocation          ( 4 ),
      notificationVerificationOnly    ( 5 ) },
   ... ,
   deferredLocationEventType   [1] IMPLICIT BIT STRING {
      msAvailable  (0 ),
      enteringIntoArea  (1 ),
      leavingFromArea  (2 ),
      beingInsideArea  (3 ),
      periodicLDR  (4 )} ( SIZE( 1 .. 16 ) ) OPTIONAL}

CSRecord   ::= CHOICE {
   moCallRecord           [0] IMPLICIT MOCallRecord,
   mtCallRecord           [1] IMPLICIT MTCallRecord,
   roamingRecord          [2] IMPLICIT RoamingRecord,
   incGatewayRecord       [3] IMPLICIT IncGatewayRecord,
   outGatewayRecord       [4] IMPLICIT OutGatewayRecord,
   transitRecord          [5] IMPLICIT TransitCallRecord,
   moSMSRecord            [6] IMPLICIT MOSMSRecord,
   mtSMSRecord            [7] IMPLICIT MTSMSRecord,
   moSMSIWRecord          [8] IMPLICIT MOSMSIWRecord,
   mtSMSGWRecord          [9] IMPLICIT MTSMSGWRecord,
   ssActionRecord         [10] IMPLICIT SSActionRecord,
   hlrIntRecord           [11] IMPLICIT HLRIntRecord,
   locUpdateHLRRecord     [12] IMPLICIT LocUpdateHLRRecord,
   locUpdateVLRRecord     [13] IMPLICIT LocUpdateVLRRecord,
   commonEquipRecord      [14] IMPLICIT CommonEquipRecord,
   recTypeExtensions      [15] IMPLICIT SET  OF
      ManagementExtension,
   termCAMELRecord        [16] IMPLICIT TermCAMELRecord,
   mtLCSRecord            [17] IMPLICIT MTLCSRecord,
   moLCSRecord            [18] IMPLICIT MOLCSRecord,
   niLCSRecord            [19] IMPLICIT NILCSRecord,
   mSCsRVCCRecord         [20] IMPLICIT MSCsRVCCRecord,
   mMTRFRecord            [21] IMPLICIT MTRFRecord,
   iCSRegisterRecord      [22] IMPLICIT ICSregisterRecord}

MOCallRecord ::= SET {
   recordType                [0] IMPLICIT RecordType,
   servedIMSI                [1] IMPLICIT OCTET STRING ( SIZE( 3 .. 8 ) ) OPTIONAL,
   servedIMEI                [2] IMPLICIT OCTET STRING ( SIZE( 8 ) ) OPTIONAL,
   servedMSISDN              [3] IMPLICIT OCTET STRING ( SIZE( 1 .. 20 ) ) ( SIZE( 1 .. 9 ) ) OPTIONAL,
   callingNumber             [4] IMPLICIT OCTET STRING OPTIONAL,
   calledNumber              [5] IMPLICIT OCTET STRING OPTIONAL,
   translatedNumber          [6] IMPLICIT OCTET STRING OPTIONAL,
   connectedNumber           [7] IMPLICIT OCTET STRING OPTIONAL,
   roamingNumber             [8] IMPLICIT OCTET STRING ( SIZE( 1 .. 20 ) ) ( SIZE( 1 .. 9 ) ) OPTIONAL,
   recordingEntity           [9] IMPLICIT OCTET STRING ( SIZE( 1 .. 20 ) ),
   mscIncomingTKGP           [10] TrunkGroup OPTIONAL,
   mscOutgoingTKGP           [11] TrunkGroup OPTIONAL,
   location                  [12] IMPLICIT LocationAreaAndCell OPTIONAL,
   changeOfLocation          [13] IMPLICIT SEQUENCE  OF
      LocationChange OPTIONAL,
   basicService              [14] BasicService OPTIONAL,
   transparencyIndicator     [15] IMPLICIT TransparencyInd OPTIONAL,
   changeOfService           [16] IMPLICIT SEQUENCE  OF
      ChangeOfService OPTIONAL,
   supplServicesUsed         [17] IMPLICIT SEQUENCE  OF
      SuppServiceUsed OPTIONAL,
   aocParameters             [18] IMPLICIT AOCParameters OPTIONAL,
   changeOfAOCParms          [19] IMPLICIT SEQUENCE  OF
      AOCParmChange OPTIONAL,
   msClassmark               [20] IMPLICIT OCTET STRING OPTIONAL,
   changeOfClassmark         [21] IMPLICIT ChangeOfClassmark OPTIONAL,
   seizureTime               [22] IMPLICIT OCTET STRING ( SIZE( 9 ) ) OPTIONAL,
   answerTime                [23] IMPLICIT OCTET STRING ( SIZE( 9 ) ) OPTIONAL,
   releaseTime               [24] IMPLICIT OCTET STRING ( SIZE( 9 ) ) OPTIONAL,
   callDuration              [25] IMPLICIT INTEGER,
   dataVolume                [26] IMPLICIT INTEGER OPTIONAL,
   radioChanRequested        [27] IMPLICIT RadioChanRequested OPTIONAL,
   radioChanUsed             [28] IMPLICIT TrafficChannel OPTIONAL,
   changeOfRadioChan         [29] IMPLICIT ChangeOfRadioChannel OPTIONAL,
   causeForTerm              [30] IMPLICIT CauseForTerm,
   diagnostics               [31] HLRIntResult OPTIONAL,
   callReference             [32] IMPLICIT OCTET STRING ( SIZE( 1 .. 8 ) ),
   sequenceNumber            [33] IMPLICIT INTEGER OPTIONAL,
   additionalChgInfo         [34] IMPLICIT AdditionalChgInfo OPTIONAL,
   recordExtensions          [35] IMPLICIT SET  OF
      ManagementExtension OPTIONAL,
   gsm-SCFAddress            [36] IMPLICIT OCTET STRING ( SIZE( 1 .. 20 ) ) ( SIZE( 1 .. 9 ) ) OPTIONAL,
   serviceKey                [37] IMPLICIT INTEGER ( 0 .. 2147483647 ) OPTIONAL,
   networkCallReference      [38] IMPLICIT OCTET STRING ( SIZE( 1 .. 8 ) ) OPTIONAL,
   mSCAddress                [39] IMPLICIT OCTET STRING ( SIZE( 1 .. 20 ) ) OPTIONAL,
   cAMELInitCFIndicator      [40] IMPLICIT CAMELInitCFIndicator OPTIONAL,
   defaultCallHandling       [41] IMPLICIT DefaultCallHandling OPTIONAL,
   hSCSDChanRequested        [42] IMPLICIT INTEGER OPTIONAL,
   hSCSDChanAllocated        [43] IMPLICIT INTEGER OPTIONAL,
   changeOfHSCSDParms        [44] IMPLICIT SEQUENCE  OF
      HSCSDParmsChange OPTIONAL,
   fnur                      [45] IMPLICIT Fnur OPTIONAL,
   aiurRequested             [46] IMPLICIT AiurRequested OPTIONAL,
   chanCodingsAcceptable     [47] IMPLICIT SEQUENCE  OF
      ChannelCoding OPTIONAL,
   chanCodingUsed            [48] IMPLICIT ChannelCoding OPTIONAL,
   speechVersionSupported    [49] IMPLICIT OCTET STRING ( SIZE( 1 ) ) OPTIONAL,
   speechVersionUsed         [50] IMPLICIT OCTET STRING ( SIZE( 1 ) ) OPTIONAL,
   numberOfDPEncountered     [51] IMPLICIT INTEGER OPTIONAL,
   levelOfCAMELService       [52] IMPLICIT BIT STRING {
      basic  (0 ),
      callDurationSupervision  (1 ),
      onlineCharging  (2 )} OPTIONAL,
   freeFormatData            [53] IMPLICIT OCTET STRING ( SIZE( 1 .. 160 ) ) OPTIONAL,
   cAMELCallLegInformation   [54] IMPLICIT SEQUENCE  OF
      CAMELInformation OPTIONAL,
   freeFormatDataAppend      [55] IMPLICIT BOOLEAN OPTIONAL,
   defaultCallHandling-2     [56] IMPLICIT DefaultCallHandling OPTIONAL,
   gsm-SCFAddress-2          [57] IMPLICIT OCTET STRING ( SIZE( 1 .. 20 ) ) ( SIZE( 1 .. 9 ) ) OPTIONAL,
   serviceKey-2              [58] IMPLICIT INTEGER ( 0 .. 2147483647 ) OPTIONAL,
   freeFormatData-2          [59] IMPLICIT OCTET STRING ( SIZE( 1 .. 160 ) ) OPTIONAL,
   freeFormatDataAppend-2    [60] IMPLICIT BOOLEAN OPTIONAL,
   systemType                [61] IMPLICIT SystemType OPTIONAL,
   rateIndication            [62] IMPLICIT OCTET STRING ( SIZE( 1 ) ) OPTIONAL,
   locationRoutNum           [63] IMPLICIT OCTET STRING ( SIZE( 5 ) ) OPTIONAL,
   lrnSoInd                  [64] IMPLICIT INTEGER {
      lRN-NP-Database        ( 1 ),
      switchingSystemData    ( 2 ),
      incomingsignaling      ( 3 ),
      unknown                ( 9 )} OPTIONAL,
   lrnQuryStatus             [65] IMPLICIT INTEGER {
      successfulQuery         ( 1 ),
      noQueryResponseMsg      ( 2 ),
      queryProtocolErr        ( 4 ),
      queryResponseDataErr    ( 5 ),
      queryRejected           ( 6 ),
      queryNotPerformed       ( 9 ),
      queryUnsuccessful       ( 99 )} OPTIONAL,
   jIPPara                   [66] IMPLICIT OCTET STRING ( SIZE( 5 ) ) OPTIONAL,
   jIPSoInd                  [67] IMPLICIT INTEGER {
      lRN-NP-Database        ( 1 ),
      switchingSystemData    ( 2 ),
      incomingsignaling      ( 3 ),
      unknown                ( 9 )} OPTIONAL,
   jIPQuryStatus             [68] IMPLICIT INTEGER {
      successfulQuery         ( 1 ),
      noQueryResponseMsg      ( 2 ),
      queryProtocolErr        ( 4 ),
      queryResponseDataErr    ( 5 ),
      queryRejected           ( 6 ),
      queryNotPerformed       ( 9 ),
      queryUnsuccessful       ( 99 )} OPTIONAL,
   partialRecordType         [69] IMPLICIT PartialRecordType OPTIONAL,
   guaranteedBitRate         [70] IMPLICIT GuaranteedBitRate OPTIONAL,
   maximumBitRate            [71] IMPLICIT MaximumBitRate OPTIONAL,
   redial                    [72] IMPLICIT BOOLEAN OPTIONAL,
   reasonForServiceChange    [73] IMPLICIT ReasonForServiceChange OPTIONAL,
   serviceChangeInitiator    [74] IMPLICIT BOOLEAN OPTIONAL,
   iCSI2ActiveFlag           [75] IMPLICIT NULL OPTIONAL,
   iMS-Charging-Identifier   [76] IMPLICIT OCTET STRING OPTIONAL,
   privateUserID             [77] IMPLICIT GraphicString OPTIONAL}

MTCallRecord ::= SET {
   recordType                [0] IMPLICIT RecordType,
   servedIMSI                [1] IMPLICIT OCTET STRING ( SIZE( 3 .. 8 ) ),
   servedIMEI                [2] IMPLICIT OCTET STRING ( SIZE( 8 ) ) OPTIONAL,
   servedMSISDN              [3] IMPLICIT OCTET STRING OPTIONAL,
   callingNumber             [4] IMPLICIT OCTET STRING OPTIONAL,
   connectedNumber           [5] IMPLICIT OCTET STRING OPTIONAL,
   recordingEntity           [6] IMPLICIT OCTET STRING ( SIZE( 1 .. 20 ) ),
   mscIncomingTKGP           [7] TrunkGroup OPTIONAL,
   mscOutgoingTKGP           [8] TrunkGroup OPTIONAL,
   location                  [9] IMPLICIT LocationAreaAndCell OPTIONAL,
   changeOfLocation          [10] IMPLICIT SEQUENCE  OF
      LocationChange OPTIONAL,
   basicService              [11] BasicService OPTIONAL,
   transparencyIndicator     [12] IMPLICIT TransparencyInd OPTIONAL,
   changeOfService           [13] IMPLICIT SEQUENCE  OF
      ChangeOfService OPTIONAL,
   supplServicesUsed         [14] IMPLICIT SEQUENCE  OF
      SuppServiceUsed OPTIONAL,
   aocParameters             [15] IMPLICIT AOCParameters OPTIONAL,
   changeOfAOCParms          [16] IMPLICIT SEQUENCE  OF
      AOCParmChange OPTIONAL,
   msClassmark               [17] IMPLICIT OCTET STRING OPTIONAL,
   changeOfClassmark         [18] IMPLICIT ChangeOfClassmark OPTIONAL,
   seizureTime               [19] IMPLICIT OCTET STRING ( SIZE( 9 ) ) OPTIONAL,
   answerTime                [20] IMPLICIT OCTET STRING ( SIZE( 9 ) ) OPTIONAL,
   releaseTime               [21] IMPLICIT OCTET STRING ( SIZE( 9 ) ) OPTIONAL,
   callDuration              [22] IMPLICIT INTEGER,
   dataVolume                [23] IMPLICIT INTEGER OPTIONAL,
   radioChanRequested        [24] IMPLICIT RadioChanRequested OPTIONAL,
   radioChanUsed             [25] IMPLICIT TrafficChannel OPTIONAL,
   changeOfRadioChan         [26] IMPLICIT ChangeOfRadioChannel OPTIONAL,
   causeForTerm              [27] IMPLICIT CauseForTerm,
   diagnostics               [28] HLRIntResult OPTIONAL,
   callReference             [29] IMPLICIT OCTET STRING ( SIZE( 1 .. 8 ) ),
   sequenceNumber            [30] IMPLICIT INTEGER OPTIONAL,
   additionalChgInfo         [31] IMPLICIT AdditionalChgInfo OPTIONAL,
   recordExtensions          [32] IMPLICIT SET  OF
      ManagementExtension OPTIONAL,
   networkCallReference      [33] IMPLICIT OCTET STRING ( SIZE( 1 .. 8 ) ) OPTIONAL,
   mSCAddress                [34] IMPLICIT OCTET STRING ( SIZE( 1 .. 20 ) ) OPTIONAL,
   hSCSDChanRequested        [35] IMPLICIT INTEGER OPTIONAL,
   hSCSDChanAllocated        [36] IMPLICIT INTEGER OPTIONAL,
   changeOfHSCSDParms        [37] IMPLICIT SEQUENCE  OF
      HSCSDParmsChange OPTIONAL,
   fnur                      [38] IMPLICIT Fnur OPTIONAL,
   aiurRequested             [39] IMPLICIT AiurRequested OPTIONAL,
   chanCodingsAcceptable     [40] IMPLICIT SEQUENCE  OF
      ChannelCoding OPTIONAL,
   chanCodingUsed            [41] IMPLICIT ChannelCoding OPTIONAL,
   speechVersionSupported    [42] IMPLICIT OCTET STRING ( SIZE( 1 ) ) OPTIONAL,
   speechVersionUsed         [43] IMPLICIT OCTET STRING ( SIZE( 1 ) ) OPTIONAL,
   gsm-SCFAddress            [44] IMPLICIT OCTET STRING ( SIZE( 1 .. 20 ) ) ( SIZE( 1 .. 9 ) ) OPTIONAL,
   serviceKey                [45] IMPLICIT INTEGER ( 0 .. 2147483647 ) OPTIONAL,
   systemType                [46] IMPLICIT SystemType OPTIONAL,
   rateIndication            [47] IMPLICIT OCTET STRING ( SIZE( 1 ) ) OPTIONAL,
   locationRoutNum           [48] IMPLICIT OCTET STRING ( SIZE( 5 ) ) OPTIONAL,
   lrnSoInd                  [49] IMPLICIT INTEGER {
      lRN-NP-Database        ( 1 ),
      switchingSystemData    ( 2 ),
      incomingsignaling      ( 3 ),
      unknown                ( 9 )} OPTIONAL,
   lrnQuryStatus             [50] IMPLICIT INTEGER {
      successfulQuery         ( 1 ),
      noQueryResponseMsg      ( 2 ),
      queryProtocolErr        ( 4 ),
      queryResponseDataErr    ( 5 ),
      queryRejected           ( 6 ),
      queryNotPerformed       ( 9 ),
      queryUnsuccessful       ( 99 )} OPTIONAL,
   jIPPara                   [51] IMPLICIT OCTET STRING ( SIZE( 5 ) ) OPTIONAL,
   jIPSoInd                  [52] IMPLICIT INTEGER {
      lRN-NP-Database        ( 1 ),
      switchingSystemData    ( 2 ),
      incomingsignaling      ( 3 ),
      unknown                ( 9 )} OPTIONAL,
   jIPQuryStatus             [53] IMPLICIT INTEGER {
      successfulQuery         ( 1 ),
      noQueryResponseMsg      ( 2 ),
      queryProtocolErr        ( 4 ),
      queryResponseDataErr    ( 5 ),
      queryRejected           ( 6 ),
      queryNotPerformed       ( 9 ),
      queryUnsuccessful       ( 99 )} OPTIONAL,
   partialRecordType         [54] IMPLICIT PartialRecordType OPTIONAL,
   guaranteedBitRate         [55] IMPLICIT GuaranteedBitRate OPTIONAL,
   maximumBitRate            [56] IMPLICIT MaximumBitRate OPTIONAL,
   reasonForServiceChange    [57] IMPLICIT ReasonForServiceChange OPTIONAL,
   serviceChangeInitiator    [58] IMPLICIT BOOLEAN OPTIONAL,
   iCSI2ActiveFlag           [59] IMPLICIT NULL OPTIONAL,
   iMS-Charging-Identifier   [60] IMPLICIT OCTET STRING OPTIONAL,
   privateUserID             [61] IMPLICIT GraphicString OPTIONAL}

RoamingRecord ::= SET {
   recordType              [0] IMPLICIT RecordType,
   servedIMSI              [1] IMPLICIT OCTET STRING ( SIZE( 3 .. 8 ) ),
   servedMSISDN            [2] IMPLICIT OCTET STRING ( SIZE( 1 .. 20 ) ) ( SIZE( 1 .. 9 ) ) OPTIONAL,
   callingNumber           [3] IMPLICIT OCTET STRING OPTIONAL,
   roamingNumber           [4] IMPLICIT OCTET STRING ( SIZE( 1 .. 20 ) ) ( SIZE( 1 .. 9 ) ) OPTIONAL,
   recordingEntity         [5] IMPLICIT OCTET STRING ( SIZE( 1 .. 20 ) ),
   mscIncomingTKGP         [6] TrunkGroup OPTIONAL,
   mscOutgoingTKGP         [7] TrunkGroup OPTIONAL,
   basicService            [8] BasicService OPTIONAL,
   transparencyIndicator   [9] IMPLICIT TransparencyInd OPTIONAL,
   changeOfService         [10] IMPLICIT SEQUENCE  OF
      ChangeOfService OPTIONAL,
   supplServicesUsed       [11] IMPLICIT SEQUENCE  OF
      SuppServiceUsed OPTIONAL,
   seizureTime             [12] IMPLICIT OCTET STRING ( SIZE( 9 ) ) OPTIONAL,
   answerTime              [13] IMPLICIT OCTET STRING ( SIZE( 9 ) ) OPTIONAL,
   releaseTime             [14] IMPLICIT OCTET STRING ( SIZE( 9 ) ) OPTIONAL,
   callDuration            [15] IMPLICIT INTEGER,
   dataVolume              [16] IMPLICIT INTEGER OPTIONAL,
   causeForTerm            [17] IMPLICIT CauseForTerm,
   diagnostics             [18] HLRIntResult OPTIONAL,
   callReference           [19] IMPLICIT OCTET STRING ( SIZE( 1 .. 8 ) ),
   sequenceNumber          [20] IMPLICIT INTEGER OPTIONAL,
   recordExtensions        [21] IMPLICIT SET  OF
      ManagementExtension OPTIONAL,
   networkCallReference    [22] IMPLICIT OCTET STRING ( SIZE( 1 .. 8 ) ) OPTIONAL,
   mSCAddress              [23] IMPLICIT OCTET STRING ( SIZE( 1 .. 20 ) ) OPTIONAL,
   locationRoutNum         [24] IMPLICIT OCTET STRING ( SIZE( 5 ) ) OPTIONAL,
   lrnSoInd                [25] IMPLICIT INTEGER {
      lRN-NP-Database        ( 1 ),
      switchingSystemData    ( 2 ),
      incomingsignaling      ( 3 ),
      unknown                ( 9 )} OPTIONAL,
   lrnQuryStatus           [26] IMPLICIT INTEGER {
      successfulQuery         ( 1 ),
      noQueryResponseMsg      ( 2 ),
      queryProtocolErr        ( 4 ),
      queryResponseDataErr    ( 5 ),
      queryRejected           ( 6 ),
      queryNotPerformed       ( 9 ),
      queryUnsuccessful       ( 99 )} OPTIONAL,
   jIPPara                 [27] IMPLICIT OCTET STRING ( SIZE( 5 ) ) OPTIONAL,
   jIPSoInd                [28] IMPLICIT INTEGER {
      lRN-NP-Database        ( 1 ),
      switchingSystemData    ( 2 ),
      incomingsignaling      ( 3 ),
      unknown                ( 9 )} OPTIONAL,
   jIPQuryStatus           [29] IMPLICIT INTEGER {
      successfulQuery         ( 1 ),
      noQueryResponseMsg      ( 2 ),
      queryProtocolErr        ( 4 ),
      queryResponseDataErr    ( 5 ),
      queryRejected           ( 6 ),
      queryNotPerformed       ( 9 ),
      queryUnsuccessful       ( 99 )} OPTIONAL,
   partialRecordType       [30] IMPLICIT PartialRecordType OPTIONAL}

TermCAMELRecord ::= SET {
   recordtype                  [0] IMPLICIT RecordType,
   servedIMSI                  [1] IMPLICIT OCTET STRING ( SIZE( 3 .. 8 ) ),
   servedMSISDN                [2] IMPLICIT OCTET STRING ( SIZE( 1 .. 20 ) ) ( SIZE( 1 .. 9 ) ) OPTIONAL,
   recordingEntity             [3] IMPLICIT OCTET STRING ( SIZE( 1 .. 20 ) ),
   interrogationTime           [4] IMPLICIT OCTET STRING ( SIZE( 9 ) ),
   destinationRoutingAddress   [5] IMPLICIT SEQUENCE  ( SIZE( 1 ) ) OF
      OCTET STRING ( SIZE( 1 .. 41 ) ),
   gsm-SCFAddress              [6] IMPLICIT OCTET STRING ( SIZE( 1 .. 20 ) ) ( SIZE( 1 .. 9 ) ),
   serviceKey                  [7] IMPLICIT INTEGER ( 0 .. 2147483647 ),
   networkCallReference        [8] IMPLICIT OCTET STRING ( SIZE( 1 .. 8 ) ) OPTIONAL,
   mSCAddress                  [9] IMPLICIT OCTET STRING ( SIZE( 1 .. 20 ) ) OPTIONAL,
   defaultCallHandling         [10] IMPLICIT DefaultCallHandling OPTIONAL,
   recordExtensions            [11] IMPLICIT SET  OF
      ManagementExtension OPTIONAL,
   calledNumber                [12] IMPLICIT OCTET STRING,
   callingNumber               [13] IMPLICIT OCTET STRING OPTIONAL,
   mscIncomingTKGP             [14] TrunkGroup OPTIONAL,
   mscOutgoingTKGP             [15] TrunkGroup OPTIONAL,
   seizureTime                 [16] IMPLICIT OCTET STRING ( SIZE( 9 ) ) OPTIONAL,
   answerTime                  [17] IMPLICIT OCTET STRING ( SIZE( 9 ) ) OPTIONAL,
   releaseTime                 [18] IMPLICIT OCTET STRING ( SIZE( 9 ) ) OPTIONAL,
   callDuration                [19] IMPLICIT INTEGER,
   dataVolume                  [20] IMPLICIT INTEGER OPTIONAL,
   causeForTerm                [21] IMPLICIT CauseForTerm,
   diagnostics                 [22] HLRIntResult OPTIONAL,
   callReference               [23] IMPLICIT OCTET STRING ( SIZE( 1 .. 8 ) ),
   sequenceNumber              [24] IMPLICIT INTEGER OPTIONAL,
   numberOfDPEncountered       [25] IMPLICIT INTEGER OPTIONAL,
   levelOfCAMELService         [26] IMPLICIT BIT STRING {
      basic  (0 ),
      callDurationSupervision  (1 ),
      onlineCharging  (2 )} OPTIONAL,
   freeFormatData              [27] IMPLICIT OCTET STRING ( SIZE( 1 .. 160 ) ) OPTIONAL,
   cAMELCallLegInformation     [28] IMPLICIT SEQUENCE  OF
      CAMELInformation OPTIONAL,
   freeFormatDataAppend        [29] IMPLICIT BOOLEAN OPTIONAL,
   defaultCallHandling-2       [30] IMPLICIT DefaultCallHandling OPTIONAL,
   gsm-SCFAddress-2            [31] IMPLICIT OCTET STRING ( SIZE( 1 .. 20 ) ) ( SIZE( 1 .. 9 ) ) OPTIONAL,
   serviceKey-2                [32] IMPLICIT INTEGER ( 0 .. 2147483647 ) OPTIONAL,
   freeFormatData-2            [33] IMPLICIT OCTET STRING ( SIZE( 1 .. 160 ) ) OPTIONAL,
   freeFormatDataAppend-2      [34] IMPLICIT BOOLEAN OPTIONAL,
   mscServerIndication         [35] IMPLICIT BOOLEAN OPTIONAL,
   locationRoutNum             [36] IMPLICIT OCTET STRING ( SIZE( 5 ) ) OPTIONAL,
   lrnSoInd                    [37] IMPLICIT INTEGER {
      lRN-NP-Database        ( 1 ),
      switchingSystemData    ( 2 ),
      incomingsignaling      ( 3 ),
      unknown                ( 9 )} OPTIONAL,
   lrnQuryStatus               [38] IMPLICIT INTEGER {
      successfulQuery         ( 1 ),
      noQueryResponseMsg      ( 2 ),
      queryProtocolErr        ( 4 ),
      queryResponseDataErr    ( 5 ),
      queryRejected           ( 6 ),
      queryNotPerformed       ( 9 ),
      queryUnsuccessful       ( 99 )} OPTIONAL,
   jIPPara                     [39] IMPLICIT OCTET STRING ( SIZE( 5 ) ) OPTIONAL,
   jIPSoInd                    [40] IMPLICIT INTEGER {
      lRN-NP-Database        ( 1 ),
      switchingSystemData    ( 2 ),
      incomingsignaling      ( 3 ),
      unknown                ( 9 )} OPTIONAL,
   jIPQuryStatus               [41] IMPLICIT INTEGER {
      successfulQuery         ( 1 ),
      noQueryResponseMsg      ( 2 ),
      queryProtocolErr        ( 4 ),
      queryResponseDataErr    ( 5 ),
      queryRejected           ( 6 ),
      queryNotPerformed       ( 9 ),
      queryUnsuccessful       ( 99 )} OPTIONAL,
   partialRecordType           [42] IMPLICIT PartialRecordType OPTIONAL}

IncGatewayRecord ::= SET {
   recordType               [0] IMPLICIT RecordType,
   callingNumber            [1] IMPLICIT OCTET STRING OPTIONAL,
   calledNumber             [2] IMPLICIT OCTET STRING,
   recordingEntity          [3] IMPLICIT OCTET STRING ( SIZE( 1 .. 20 ) ),
   mscIncomingTKGP          [4] TrunkGroup OPTIONAL,
   mscOutgoingTKGP          [5] TrunkGroup OPTIONAL,
   seizureTime              [6] IMPLICIT OCTET STRING ( SIZE( 9 ) ) OPTIONAL,
   answerTime               [7] IMPLICIT OCTET STRING ( SIZE( 9 ) ) OPTIONAL,
   releaseTime              [8] IMPLICIT OCTET STRING ( SIZE( 9 ) ) OPTIONAL,
   callDuration             [9] IMPLICIT INTEGER,
   dataVolume               [10] IMPLICIT INTEGER OPTIONAL,
   causeForTerm             [11] IMPLICIT CauseForTerm,
   diagnostics              [12] HLRIntResult OPTIONAL,
   callReference            [13] IMPLICIT OCTET STRING ( SIZE( 1 .. 8 ) ),
   sequenceNumber           [14] IMPLICIT INTEGER OPTIONAL,
   recordExtensions         [15] IMPLICIT SET  OF
      ManagementExtension OPTIONAL,
   locationRoutNum          [16] IMPLICIT OCTET STRING ( SIZE( 5 ) ) OPTIONAL,
   lrnSoInd                 [17] IMPLICIT INTEGER {
      lRN-NP-Database        ( 1 ),
      switchingSystemData    ( 2 ),
      incomingsignaling      ( 3 ),
      unknown                ( 9 )} OPTIONAL,
   lrnQuryStatus            [18] IMPLICIT INTEGER {
      successfulQuery         ( 1 ),
      noQueryResponseMsg      ( 2 ),
      queryProtocolErr        ( 4 ),
      queryResponseDataErr    ( 5 ),
      queryRejected           ( 6 ),
      queryNotPerformed       ( 9 ),
      queryUnsuccessful       ( 99 )} OPTIONAL,
   jIPPara                  [19] IMPLICIT OCTET STRING ( SIZE( 5 ) ) OPTIONAL,
   jIPSoInd                 [20] IMPLICIT INTEGER {
      lRN-NP-Database        ( 1 ),
      switchingSystemData    ( 2 ),
      incomingsignaling      ( 3 ),
      unknown                ( 9 )} OPTIONAL,
   jIPQuryStatus            [21] IMPLICIT INTEGER {
      successfulQuery         ( 1 ),
      noQueryResponseMsg      ( 2 ),
      queryProtocolErr        ( 4 ),
      queryResponseDataErr    ( 5 ),
      queryRejected           ( 6 ),
      queryNotPerformed       ( 9 ),
      queryUnsuccessful       ( 99 )} OPTIONAL,
   reasonForServiceChange   [22] IMPLICIT ReasonForServiceChange OPTIONAL,
   serviceChangeInitiator   [23] IMPLICIT BOOLEAN OPTIONAL}

OutGatewayRecord ::= SET {
   recordType               [0] IMPLICIT RecordType,
   callingNumber            [1] IMPLICIT OCTET STRING OPTIONAL,
   calledNumber             [2] IMPLICIT OCTET STRING,
   recordingEntity          [3] IMPLICIT OCTET STRING ( SIZE( 1 .. 20 ) ),
   mscIncomingTKGP          [4] TrunkGroup OPTIONAL,
   mscOutgoingTKGP          [5] TrunkGroup OPTIONAL,
   seizureTime              [6] IMPLICIT OCTET STRING ( SIZE( 9 ) ) OPTIONAL,
   answerTime               [7] IMPLICIT OCTET STRING ( SIZE( 9 ) ) OPTIONAL,
   releaseTime              [8] IMPLICIT OCTET STRING ( SIZE( 9 ) ) OPTIONAL,
   callDuration             [9] IMPLICIT INTEGER,
   dataVolume               [10] IMPLICIT INTEGER OPTIONAL,
   causeForTerm             [11] IMPLICIT CauseForTerm,
   diagnostics              [12] HLRIntResult OPTIONAL,
   callReference            [13] IMPLICIT OCTET STRING ( SIZE( 1 .. 8 ) ),
   sequenceNumber           [14] IMPLICIT INTEGER OPTIONAL,
   recordExtensions         [15] IMPLICIT SET  OF
      ManagementExtension OPTIONAL,
   locationRoutNum          [16] IMPLICIT OCTET STRING ( SIZE( 5 ) ) OPTIONAL,
   lrnSoInd                 [17] IMPLICIT INTEGER {
      lRN-NP-Database        ( 1 ),
      switchingSystemData    ( 2 ),
      incomingsignaling      ( 3 ),
      unknown                ( 9 )} OPTIONAL,
   lrnQuryStatus            [18] IMPLICIT INTEGER {
      successfulQuery         ( 1 ),
      noQueryResponseMsg      ( 2 ),
      queryProtocolErr        ( 4 ),
      queryResponseDataErr    ( 5 ),
      queryRejected           ( 6 ),
      queryNotPerformed       ( 9 ),
      queryUnsuccessful       ( 99 )} OPTIONAL,
   jIPPara                  [19] IMPLICIT OCTET STRING ( SIZE( 5 ) ) OPTIONAL,
   jIPSoInd                 [20] IMPLICIT INTEGER {
      lRN-NP-Database        ( 1 ),
      switchingSystemData    ( 2 ),
      incomingsignaling      ( 3 ),
      unknown                ( 9 )} OPTIONAL,
   jIPQuryStatus            [21] IMPLICIT INTEGER {
      successfulQuery         ( 1 ),
      noQueryResponseMsg      ( 2 ),
      queryProtocolErr        ( 4 ),
      queryResponseDataErr    ( 5 ),
      queryRejected           ( 6 ),
      queryNotPerformed       ( 9 ),
      queryUnsuccessful       ( 99 )} OPTIONAL,
   reasonForServiceChange   [22] IMPLICIT ReasonForServiceChange OPTIONAL,
   serviceChangeInitiator   [23] IMPLICIT BOOLEAN OPTIONAL}

TransitCallRecord ::= SET {
   recordType         [0] IMPLICIT RecordType,
   recordingEntity    [1] IMPLICIT OCTET STRING ( SIZE( 1 .. 20 ) ),
   mscIncomingTKGP    [2] TrunkGroup OPTIONAL,
   mscOutgoingTKGP    [3] TrunkGroup OPTIONAL,
   callingNumber      [4] IMPLICIT OCTET STRING OPTIONAL,
   calledNumber       [5] IMPLICIT OCTET STRING,
   isdnBasicService   [6] IMPLICIT IsdnBasicService OPTIONAL,
   seizureTimestamp   [7] IMPLICIT OCTET STRING ( SIZE( 9 ) ) OPTIONAL,
   answerTimestamp    [8] IMPLICIT OCTET STRING ( SIZE( 9 ) ) OPTIONAL,
   releaseTimestamp   [9] IMPLICIT OCTET STRING ( SIZE( 9 ) ) OPTIONAL,
   callDuration       [10] IMPLICIT INTEGER,
   dataVolume         [11] IMPLICIT INTEGER OPTIONAL,
   causeForTerm       [12] IMPLICIT CauseForTerm,
   diagnostics        [13] HLRIntResult OPTIONAL,
   callReference      [14] IMPLICIT OCTET STRING ( SIZE( 1 .. 8 ) ),
   sequenceNumber     [15] IMPLICIT INTEGER OPTIONAL,
   recordExtensions   [16] IMPLICIT SET  OF
      ManagementExtension OPTIONAL,
   locationRoutNum    [17] IMPLICIT OCTET STRING ( SIZE( 5 ) ) OPTIONAL,
   lrnSoInd           [18] IMPLICIT INTEGER {
      lRN-NP-Database        ( 1 ),
      switchingSystemData    ( 2 ),
      incomingsignaling      ( 3 ),
      unknown                ( 9 )} OPTIONAL,
   lrnQuryStatus      [19] IMPLICIT INTEGER {
      successfulQuery         ( 1 ),
      noQueryResponseMsg      ( 2 ),
      queryProtocolErr        ( 4 ),
      queryResponseDataErr    ( 5 ),
      queryRejected           ( 6 ),
      queryNotPerformed       ( 9 ),
      queryUnsuccessful       ( 99 )} OPTIONAL,
   jIPPara            [20] IMPLICIT OCTET STRING ( SIZE( 5 ) ) OPTIONAL,
   jIPSoInd           [21] IMPLICIT INTEGER {
      lRN-NP-Database        ( 1 ),
      switchingSystemData    ( 2 ),
      incomingsignaling      ( 3 ),
      unknown                ( 9 )} OPTIONAL,
   jIPQuryStatus      [22] IMPLICIT INTEGER {
      successfulQuery         ( 1 ),
      noQueryResponseMsg      ( 2 ),
      queryProtocolErr        ( 4 ),
      queryResponseDataErr    ( 5 ),
      queryRejected           ( 6 ),
      queryNotPerformed       ( 9 ),
      queryUnsuccessful       ( 99 )} OPTIONAL}

MOSMSRecord ::= SET {
   recordType            [0] IMPLICIT RecordType,
   servedIMSI            [1] IMPLICIT OCTET STRING ( SIZE( 3 .. 8 ) ),
   servedIMEI            [2] IMPLICIT OCTET STRING ( SIZE( 8 ) ) OPTIONAL,
   servedMSISDN          [3] IMPLICIT OCTET STRING ( SIZE( 1 .. 20 ) ) ( SIZE( 1 .. 9 ) ) OPTIONAL,
   msClassmark           [4] IMPLICIT OCTET STRING,
   serviceCentre         [5] IMPLICIT OCTET STRING ( SIZE( 1 .. 20 ) ),
   recordingEntity       [6] IMPLICIT OCTET STRING ( SIZE( 1 .. 20 ) ),
   location              [7] IMPLICIT LocationAreaAndCell OPTIONAL,
   messageReference      [8] IMPLICIT OCTET STRING,
   originationTime       [9] IMPLICIT OCTET STRING ( SIZE( 9 ) ),
   smsResult             [10] HLRIntResult OPTIONAL,
   recordExtensions      [11] IMPLICIT SET  OF
      ManagementExtension OPTIONAL,
   destinationNumber     [12] IMPLICIT OCTET STRING OPTIONAL,
   cAMELSMSInformation   [13] IMPLICIT CAMELSMSInformation OPTIONAL,
   systemType            [14] IMPLICIT SystemType OPTIONAL,
   locationExtension     [15] IMPLICIT BIT STRING ( SIZE( 12 ) ) OPTIONAL}

MTSMSRecord ::= SET {
   recordType            [0] IMPLICIT RecordType,
   serviceCentre         [1] IMPLICIT OCTET STRING ( SIZE( 1 .. 20 ) ),
   servedIMSI            [2] IMPLICIT OCTET STRING ( SIZE( 3 .. 8 ) ),
   servedIMEI            [3] IMPLICIT OCTET STRING ( SIZE( 8 ) ) OPTIONAL,
   servedMSISDN          [4] IMPLICIT OCTET STRING ( SIZE( 1 .. 20 ) ) ( SIZE( 1 .. 9 ) ) OPTIONAL,
   msClassmark           [5] IMPLICIT OCTET STRING,
   recordingEntity       [6] IMPLICIT OCTET STRING ( SIZE( 1 .. 20 ) ),
   location              [7] IMPLICIT LocationAreaAndCell OPTIONAL,
   deliveryTime          [8] IMPLICIT OCTET STRING ( SIZE( 9 ) ),
   smsResult             [9] HLRIntResult OPTIONAL,
   recordExtensions      [10] IMPLICIT SET  OF
      ManagementExtension OPTIONAL,
   systemType            [11] IMPLICIT SystemType OPTIONAL,
   cAMELSMSInformation   [12] IMPLICIT CAMELSMSInformation OPTIONAL,
   locationExtension     [13] IMPLICIT BIT STRING ( SIZE( 12 ) ) OPTIONAL}

MOSMSIWRecord ::= SET {
   recordType         [0] IMPLICIT RecordType,
   serviceCentre      [1] IMPLICIT OCTET STRING ( SIZE( 1 .. 20 ) ),
   servedIMSI         [2] IMPLICIT OCTET STRING ( SIZE( 3 .. 8 ) ),
   recordingEntity    [3] IMPLICIT OCTET STRING ( SIZE( 1 .. 20 ) ),
   eventTime          [4] IMPLICIT OCTET STRING ( SIZE( 9 ) ),
   smsResult          [5] HLRIntResult OPTIONAL,
   recordExtensions   [6] IMPLICIT SET  OF
      ManagementExtension OPTIONAL}

MTSMSGWRecord ::= SET {
   recordType         [0] IMPLICIT RecordType,
   serviceCentre      [1] IMPLICIT OCTET STRING ( SIZE( 1 .. 20 ) ),
   servedIMSI         [2] IMPLICIT OCTET STRING ( SIZE( 3 .. 8 ) ),
   servedMSISDN       [3] IMPLICIT OCTET STRING ( SIZE( 1 .. 20 ) ) ( SIZE( 1 .. 9 ) ) OPTIONAL,
   recordingEntity    [4] IMPLICIT OCTET STRING ( SIZE( 1 .. 20 ) ),
   eventTime          [5] IMPLICIT OCTET STRING ( SIZE( 9 ) ),
   smsResult          [6] HLRIntResult OPTIONAL,
   recordExtensions   [7] IMPLICIT SET  OF
      ManagementExtension OPTIONAL}

SSActionRecord ::= SET {
   recordType         [0] IMPLICIT RecordType,
   servedIMSI         [1] IMPLICIT OCTET STRING ( SIZE( 3 .. 8 ) ),
   servedIMEI         [2] IMPLICIT OCTET STRING ( SIZE( 8 ) ) OPTIONAL,
   servedMSISDN       [3] IMPLICIT OCTET STRING ( SIZE( 1 .. 20 ) ) ( SIZE( 1 .. 9 ) ) OPTIONAL,
   msClassmark        [4] IMPLICIT OCTET STRING,
   recordingEntity    [5] IMPLICIT OCTET STRING ( SIZE( 1 .. 20 ) ),
   location           [6] IMPLICIT LocationAreaAndCell OPTIONAL,
   basicServices      [7] IMPLICIT SET  OF
      BasicService OPTIONAL,
   supplService       [8] IMPLICIT OCTET STRING ( SIZE( 1 ) ) OPTIONAL,
   ssAction           [9] IMPLICIT SSActionType OPTIONAL,
   ssActionTime       [10] IMPLICIT OCTET STRING ( SIZE( 9 ) ),
   ssParameters       [11] SSParameters OPTIONAL,
   ssActionResult     [12] HLRIntResult OPTIONAL,
   callReference      [13] IMPLICIT OCTET STRING ( SIZE( 1 .. 8 ) ),
   recordExtensions   [14] IMPLICIT SET  OF
      ManagementExtension OPTIONAL,
   systemType         [15] IMPLICIT SystemType OPTIONAL}

HLRIntRecord ::= SET {
   recordType            [0] IMPLICIT RecordType,
   servedIMSI            [1] IMPLICIT OCTET STRING ( SIZE( 3 .. 8 ) ),
   servedMSISDN          [2] IMPLICIT OCTET STRING ( SIZE( 1 .. 20 ) ) ( SIZE( 1 .. 9 ) ),
   recordingEntity       [3] IMPLICIT OCTET STRING ( SIZE( 1 .. 20 ) ),
   basicService          [4] BasicService OPTIONAL,
   routingNumber         [5] RoutingNumber,
   interrogationTime     [6] IMPLICIT OCTET STRING ( SIZE( 9 ) ),
   numberOfForwarding    [7] IMPLICIT INTEGER ( 1 .. 5 ) OPTIONAL,
   interrogationResult   [8] HLRIntResult OPTIONAL,
   recordExtensions      [9] IMPLICIT SET  OF
      ManagementExtension OPTIONAL}

LocUpdateHLRRecord ::= SET {
   recordType         [0] IMPLICIT RecordType,
   servedIMSI         [1] IMPLICIT OCTET STRING ( SIZE( 3 .. 8 ) ),
   recordingEntity    [2] IMPLICIT OCTET STRING ( SIZE( 1 .. 20 ) ),
   oldLocation        [3] IMPLICIT Visited-Location-info OPTIONAL,
   newLocation        [4] IMPLICIT Visited-Location-info,
   updateTime         [5] IMPLICIT OCTET STRING ( SIZE( 9 ) ),
   updateResult       [6] HLRIntResult OPTIONAL,
   recordExtensions   [7] IMPLICIT SET  OF
      ManagementExtension OPTIONAL}

LocUpdateVLRRecord ::= SET {
   recordType          [0] IMPLICIT RecordType,
   servedIMSI          [1] IMPLICIT OCTET STRING ( SIZE( 3 .. 8 ) ),
   servedMSISDN        [2] IMPLICIT OCTET STRING ( SIZE( 1 .. 20 ) ) ( SIZE( 1 .. 9 ) ) OPTIONAL,
   recordingEntity     [3] IMPLICIT OCTET STRING ( SIZE( 1 .. 20 ) ),
   oldLocation         [4] IMPLICIT Location-info OPTIONAL,
   newLocation         [5] IMPLICIT Location-info,
   msClassmark         [6] IMPLICIT OCTET STRING,
   updateTime          [7] IMPLICIT OCTET STRING ( SIZE( 9 ) ),
   updateResult        [8] HLRIntResult OPTIONAL,
   recordExtensions    [9] IMPLICIT SET  OF
      ManagementExtension OPTIONAL,
   locationExtension   [10] IMPLICIT BIT STRING ( SIZE( 12 ) ) OPTIONAL}

CommonEquipRecord ::= SET {
   recordType          [0] IMPLICIT RecordType,
   equipmentType       [1] IMPLICIT INTEGER {
      conferenceBridge    ( 0 )},
   equipmentId         [2] IMPLICIT INTEGER,
   servedIMSI          [3] IMPLICIT OCTET STRING ( SIZE( 3 .. 8 ) ),
   servedMSISDN        [4] IMPLICIT OCTET STRING ( SIZE( 1 .. 20 ) ) ( SIZE( 1 .. 9 ) ) OPTIONAL,
   recordingEntity     [5] IMPLICIT OCTET STRING ( SIZE( 1 .. 20 ) ),
   basicService        [6] BasicService OPTIONAL,
   changeOfService     [7] IMPLICIT SEQUENCE  OF
      ChangeOfService OPTIONAL,
   supplServicesUsed   [8] IMPLICIT SEQUENCE  OF
      SuppServiceUsed OPTIONAL,
   seizureTime         [9] IMPLICIT OCTET STRING ( SIZE( 9 ) ),
   releaseTime         [10] IMPLICIT OCTET STRING ( SIZE( 9 ) ) OPTIONAL,
   callDuration        [11] IMPLICIT INTEGER,
   callReference       [12] IMPLICIT OCTET STRING ( SIZE( 1 .. 8 ) ),
   sequenceNumber      [13] IMPLICIT INTEGER OPTIONAL,
   recordExtensions    [14] IMPLICIT SET  OF
      ManagementExtension OPTIONAL,
   systemType          [15] IMPLICIT SystemType OPTIONAL,
   rateIndication      [16] IMPLICIT OCTET STRING ( SIZE( 1 ) ) OPTIONAL,
   fnur                [17] IMPLICIT Fnur OPTIONAL}

ObservedIMEITicket ::= SET {
   servedIMEI         [0] IMPLICIT OCTET STRING ( SIZE( 8 ) ),
   imeiStatus         [1] IMPLICIT IMEIStatus,
   servedIMSI         [2] IMPLICIT OCTET STRING ( SIZE( 3 .. 8 ) ),
   servedMSISDN       [3] IMPLICIT OCTET STRING ( SIZE( 1 .. 20 ) ) ( SIZE( 1 .. 9 ) ) OPTIONAL,
   recordingEntity    [4] IMPLICIT OCTET STRING ( SIZE( 1 .. 20 ) ),
   eventTime          [5] IMPLICIT OCTET STRING ( SIZE( 9 ) ),
   location           [6] IMPLICIT LocationAreaAndCell,
   imeiCheckEvent     [7] IMPLICIT INTEGER {
      mobileOriginatedCall    ( 0 ),
      mobileTerminatedCall    ( 1 ),
      smsMobileOriginating    ( 2 ),
      smsMobileTerminating    ( 3 ),
      ssAction                ( 4 ),
      locationUpdate          ( 5 )} OPTIONAL,
   callReference      [8] IMPLICIT OCTET STRING ( SIZE( 1 .. 8 ) ) OPTIONAL,
   recordExtensions   [9] IMPLICIT SET  OF
      ManagementExtension OPTIONAL}

MTLCSRecord ::= SET {
   recordType             [0] IMPLICIT RecordType,
   recordingEntity        [1] IMPLICIT OCTET STRING ( SIZE( 1 .. 20 ) ),
   lcsClientType          [2] IMPLICIT LCSClientType,
   lcsClientIdentity      [3] IMPLICIT LCSClientIdentity,
   servedIMSI             [4] IMPLICIT OCTET STRING ( SIZE( 3 .. 8 ) ) OPTIONAL,
   servedMSISDN           [5] IMPLICIT OCTET STRING ( SIZE( 1 .. 20 ) ) ( SIZE( 1 .. 9 ) ) OPTIONAL,
   locationType           [6] IMPLICIT LocationType,
   lcsQos                 [7] IMPLICIT OCTET STRING ( SIZE( 4 ) ) OPTIONAL,
   lcsPriority            [8] IMPLICIT OCTET STRING ( SIZE( 1 ) ) OPTIONAL,
   mlc-Number             [9] IMPLICIT OCTET STRING ( SIZE( 1 .. 20 ) ) ( SIZE( 1 .. 9 ) ),
   eventTimeStamp         [10] IMPLICIT OCTET STRING ( SIZE( 9 ) ),
   measureDuration        [11] IMPLICIT INTEGER OPTIONAL,
   notificationToMSUser   [12] IMPLICIT ENUMERATED {
      notifyLocationAllowed                             ( 0 ),
      notifyAndVerify-LocationAllowedIfNoResponse       ( 1 ),
      notifyAndVerify-LocationNotAllowedIfNoResponse    ( 2 ),
      ... ,
      locationNotAllowed                                ( 3 ) } OPTIONAL,
   privacyOverride        [13] IMPLICIT NULL OPTIONAL,
   location               [14] IMPLICIT LocationAreaAndCell OPTIONAL,
   locationEstimate       [15] IMPLICIT OCTET STRING ( SIZE( 1 .. 20 ) ) OPTIONAL,
   positioningData        [16] IMPLICIT OCTET STRING ( SIZE( 1 .. 33 ) ) OPTIONAL,
   lcsCause               [17] IMPLICIT OCTET STRING ( SIZE( 1 ) ) OPTIONAL,
   diagnostics            [18] HLRIntResult OPTIONAL,
   systemType             [19] IMPLICIT SystemType OPTIONAL,
   recordExtensions       [20] IMPLICIT SET  OF
      ManagementExtension OPTIONAL,
   causeForTerm           [21] IMPLICIT CauseForTerm,
   servedIMEI             [22] IMPLICIT OCTET STRING ( SIZE( 8 ) ) OPTIONAL}

MOLCSRecord ::= SET {
   recordType          [0] IMPLICIT RecordType,
   recordingEntity     [1] IMPLICIT OCTET STRING ( SIZE( 1 .. 20 ) ),
   lcsClientType       [2] IMPLICIT LCSClientType OPTIONAL,
   lcsClientIdentity   [3] IMPLICIT LCSClientIdentity OPTIONAL,
   servedIMSI          [4] IMPLICIT OCTET STRING ( SIZE( 3 .. 8 ) ),
   servedMSISDN        [5] IMPLICIT OCTET STRING ( SIZE( 1 .. 20 ) ) ( SIZE( 1 .. 9 ) ) OPTIONAL,
   molr-Type           [6] IMPLICIT Molr-Type,
   lcsQos              [7] IMPLICIT OCTET STRING ( SIZE( 4 ) ) OPTIONAL,
   lcsPriority         [8] IMPLICIT OCTET STRING ( SIZE( 1 ) ) OPTIONAL,
   mlc-Number          [9] IMPLICIT OCTET STRING ( SIZE( 1 .. 20 ) ) ( SIZE( 1 .. 9 ) ) OPTIONAL,
   eventTimeStamp      [10] IMPLICIT OCTET STRING ( SIZE( 9 ) ),
   measureDuration     [11] IMPLICIT INTEGER OPTIONAL,
   location            [12] IMPLICIT LocationAreaAndCell OPTIONAL,
   locationEstimate    [13] IMPLICIT OCTET STRING ( SIZE( 1 .. 20 ) ) OPTIONAL,
   positioningData     [14] IMPLICIT OCTET STRING ( SIZE( 1 .. 33 ) ) OPTIONAL,
   lcsCause            [15] IMPLICIT OCTET STRING ( SIZE( 1 ) ) OPTIONAL,
   diagnostics         [16] HLRIntResult OPTIONAL,
   systemType          [17] IMPLICIT SystemType OPTIONAL,
   recordExtensions    [18] IMPLICIT SET  OF
      ManagementExtension OPTIONAL,
   causeForTerm        [19] IMPLICIT CauseForTerm}

NILCSRecord ::= SET {
   recordType          [0] IMPLICIT RecordType,
   recordingEntity     [1] IMPLICIT OCTET STRING ( SIZE( 1 .. 20 ) ),
   lcsClientType       [2] IMPLICIT LCSClientType OPTIONAL,
   lcsClientIdentity   [3] IMPLICIT LCSClientIdentity OPTIONAL,
   servedIMSI          [4] IMPLICIT OCTET STRING ( SIZE( 3 .. 8 ) ) OPTIONAL,
   servedMSISDN        [5] IMPLICIT OCTET STRING ( SIZE( 1 .. 20 ) ) ( SIZE( 1 .. 9 ) ) OPTIONAL,
   servedIMEI          [6] IMPLICIT OCTET STRING ( SIZE( 8 ) ) OPTIONAL,
   emsDigits           [7] IMPLICIT OCTET STRING ( SIZE( 1 .. 20 ) ) ( SIZE( 1 .. 9 ) ) OPTIONAL,
   emsKey              [8] IMPLICIT OCTET STRING ( SIZE( 1 .. 20 ) ) ( SIZE( 1 .. 9 ) ) OPTIONAL,
   lcsQos              [9] IMPLICIT OCTET STRING ( SIZE( 4 ) ) OPTIONAL,
   lcsPriority         [10] IMPLICIT OCTET STRING ( SIZE( 1 ) ) OPTIONAL,
   mlc-Number          [11] IMPLICIT OCTET STRING ( SIZE( 1 .. 20 ) ) ( SIZE( 1 .. 9 ) ) OPTIONAL,
   eventTimeStamp      [12] IMPLICIT OCTET STRING ( SIZE( 9 ) ),
   measureDuration     [13] IMPLICIT INTEGER OPTIONAL,
   location            [14] IMPLICIT LocationAreaAndCell OPTIONAL,
   locationEstimate    [15] IMPLICIT OCTET STRING ( SIZE( 1 .. 20 ) ) OPTIONAL,
   positioningData     [16] IMPLICIT OCTET STRING ( SIZE( 1 .. 33 ) ) OPTIONAL,
   lcsCause            [17] IMPLICIT OCTET STRING ( SIZE( 1 ) ) OPTIONAL,
   diagnostics         [18] HLRIntResult OPTIONAL,
   systemType          [19] IMPLICIT SystemType OPTIONAL,
   recordExtensions    [20] IMPLICIT SET  OF
      ManagementExtension OPTIONAL,
   causeForTerm        [21] IMPLICIT CauseForTerm}

MSCsRVCCRecord ::= SET {
   recordType                  [0] IMPLICIT RecordType,
   servedIMSI                  [1] IMPLICIT OCTET STRING ( SIZE( 3 .. 8 ) ) OPTIONAL,
   servedIMEI                  [2] IMPLICIT OCTET STRING ( SIZE( 8 ) ) OPTIONAL,
   servedMSISDN                [3] IMPLICIT OCTET STRING ( SIZE( 1 .. 20 ) ) ( SIZE( 1 .. 9 ) ) OPTIONAL,
   calledNumber                [5] IMPLICIT OCTET STRING,
   recordingEntity             [9] IMPLICIT OCTET STRING ( SIZE( 1 .. 20 ) ),
   mscOutgoingTKGP             [11] TrunkGroup OPTIONAL,
   location                    [12] IMPLICIT LocationAreaAndCell,
   changeOfLocation            [13] IMPLICIT SEQUENCE  OF
      LocationChange OPTIONAL,
   basicService                [14] BasicService,
   supplServicesUsed           [17] IMPLICIT SEQUENCE  OF
      SuppServiceUsed OPTIONAL,
   msClassmark                 [20] IMPLICIT OCTET STRING OPTIONAL,
   seizureTime                 [22] IMPLICIT OCTET STRING ( SIZE( 9 ) ) OPTIONAL,
   answerTime                  [23] IMPLICIT OCTET STRING ( SIZE( 9 ) ) OPTIONAL,
   releaseTime                 [24] IMPLICIT OCTET STRING ( SIZE( 9 ) ) OPTIONAL,
   callDuration                [25] IMPLICIT INTEGER,
   causeForTerm                [30] IMPLICIT CauseForTerm,
   diagnostics                 [31] HLRIntResult OPTIONAL,
   callReference               [32] IMPLICIT OCTET STRING ( SIZE( 1 .. 8 ) ),
   sequenceNumber              [33] IMPLICIT INTEGER OPTIONAL,
   recordExtensions            [35] IMPLICIT SET  OF
      ManagementExtension OPTIONAL,
   partialRecordType           [69] IMPLICIT PartialRecordType OPTIONAL,
   iMS-Charging-Identifier     [75] IMPLICIT OCTET STRING OPTIONAL,
   iCSI2ActiveFlag             [76] IMPLICIT NULL OPTIONAL,
   relatedICID                 [77] IMPLICIT OCTET STRING OPTIONAL,
   relatedICIDGenerationNode   [78] NodeAddress OPTIONAL}

MTRFRecord ::= SET {
   recordType          [0] IMPLICIT RecordType,
   servedIMSI          [1] IMPLICIT OCTET STRING ( SIZE( 3 .. 8 ) ),
   servedIMEI          [2] IMPLICIT OCTET STRING ( SIZE( 8 ) ) OPTIONAL,
   servedMSISDN        [3] IMPLICIT OCTET STRING OPTIONAL,
   callingNumber       [4] IMPLICIT OCTET STRING OPTIONAL,
   roamingNumber       [5] IMPLICIT OCTET STRING ( SIZE( 1 .. 20 ) ) ( SIZE( 1 .. 9 ) ) OPTIONAL,
   recordingEntity     [6] IMPLICIT OCTET STRING ( SIZE( 1 .. 20 ) ),
   mscIncomingTKGP     [7] TrunkGroup OPTIONAL,
   mscOutgoingTKGP     [8] TrunkGroup OPTIONAL,
   basicService        [9] BasicService OPTIONAL,
   seizureTime         [10] IMPLICIT OCTET STRING ( SIZE( 9 ) ) OPTIONAL,
   answerTime          [11] IMPLICIT OCTET STRING ( SIZE( 9 ) ) OPTIONAL,
   releaseTime         [12] IMPLICIT OCTET STRING ( SIZE( 9 ) ) OPTIONAL,
   callDuration        [13] IMPLICIT INTEGER,
   causeForTerm        [14] IMPLICIT CauseForTerm,
   diagnostics         [15] HLRIntResult OPTIONAL,
   callReference       [16] IMPLICIT OCTET STRING ( SIZE( 1 .. 8 ) ),
   sequenceNumber      [17] IMPLICIT INTEGER OPTIONAL,
   recordExtensions    [18] IMPLICIT SET  OF
      ManagementExtension OPTIONAL,
   partialRecordType   [19] IMPLICIT PartialRecordType OPTIONAL}

ICSregisterRecord ::= SET {
   recordType                 [0] IMPLICIT RecordType,
   servedIMSI                 [1] IMPLICIT OCTET STRING ( SIZE( 3 .. 8 ) ),
   servedMSISDN               [2] IMPLICIT OCTET STRING ( SIZE( 1 .. 20 ) ) ( SIZE( 1 .. 9 ) ),
   privateUserID              [3] IMPLICIT GraphicString OPTIONAL,
   recordingEntity            [4] IMPLICIT OCTET STRING ( SIZE( 1 .. 20 ) ),
   newLocation                [5] IMPLICIT Location-info,
   locationExtension          [6] IMPLICIT BIT STRING ( SIZE( 12 ) ) OPTIONAL,
   updateTime                 [7] IMPLICIT OCTET STRING ( SIZE( 9 ) ) OPTIONAL,
   iMS-Charging-Identifier    [8] IMPLICIT OCTET STRING OPTIONAL,
   interOperatorIdentifiers   [9] IMPLICIT SEQUENCE  OF
      InterOperatorIdentifiers OPTIONAL,
   transit-IOI-Lists          [10] IMPLICIT SEQUENCE  OF
      GraphicString OPTIONAL,
   updateResult               [11] HLRIntResult OPTIONAL,
   recordExtensions           [12] IMPLICIT SET  OF
      ManagementExtension OPTIONAL}

LocationRoutingNumber ::= OCTET STRING ( SIZE( 5 ) )

LocationRoutingNumberSourceIndicator ::= INTEGER {
   lRN-NP-Database        ( 1 ),
   switchingSystemData    ( 2 ),
   incomingsignaling      ( 3 ),
   unknown                ( 9 )}

LocationRoutingNumberQueryStatus ::= INTEGER {
   successfulQuery         ( 1 ),
   noQueryResponseMsg      ( 2 ),
   queryProtocolErr        ( 4 ),
   queryResponseDataErr    ( 5 ),
   queryRejected           ( 6 ),
   queryNotPerformed       ( 9 ),
   queryUnsuccessful       ( 99 )}

JurisdictionInformationParameter ::= OCTET STRING ( SIZE( 5 ) )

JurisdictionInformationParameterSourceIndicator ::= INTEGER {
   lRN-NP-Database        ( 1 ),
   switchingSystemData    ( 2 ),
   incomingsignaling      ( 3 ),
   unknown                ( 9 )}

JurisdictionInformationParameterQueryStatus ::= INTEGER {
   successfulQuery         ( 1 ),
   noQueryResponseMsg      ( 2 ),
   queryProtocolErr        ( 4 ),
   queryResponseDataErr    ( 5 ),
   queryRejected           ( 6 ),
   queryNotPerformed       ( 9 ),
   queryUnsuccessful       ( 99 )}

AdditionalChgInfo ::= SEQUENCE {
   chargeIndicator    [0] IMPLICIT INTEGER {
      noCharge    ( 0 ),
      charge      ( 1 )} OPTIONAL,
   chargeParameters   [1] IMPLICIT OCTET STRING OPTIONAL}

AiurRequested ::= ENUMERATED {
   aiur09600BitsPerSecond     ( 1 ),
   aiur14400BitsPerSecond     ( 2 ),
   aiur19200BitsPerSecond     ( 3 ),
   aiur28800BitsPerSecond     ( 5 ),
   aiur38400BitsPerSecond     ( 6 ),
   aiur43200BitsPerSecond     ( 7 ),
   aiur57600BitsPerSecond     ( 8 ),
   aiur38400BitsPerSecond1    ( 9 ),
   aiur38400BitsPerSecond2    ( 10 ),
   aiur38400BitsPerSecond3    ( 11 ),
   aiur38400BitsPerSecond4    ( 12 ) }

AOCParameters ::= SEQUENCE {
   e1         [1] IMPLICIT INTEGER OPTIONAL,
   e2         [2] IMPLICIT INTEGER OPTIONAL,
   e3         [3] IMPLICIT INTEGER OPTIONAL,
   e4         [4] IMPLICIT INTEGER OPTIONAL,
   e5         [5] IMPLICIT INTEGER OPTIONAL,
   e6         [6] IMPLICIT INTEGER OPTIONAL,
   e7         [7] IMPLICIT INTEGER OPTIONAL}

AOCParmChange ::= SEQUENCE {
   changeTime      [0] IMPLICIT OCTET STRING ( SIZE( 9 ) ),
   newParameters   [1] IMPLICIT AOCParameters}

BasicServices ::= SET  OF
   BasicService

CallingPartyCategory ::= OCTET STRING ( SIZE( 1 ) )

CallType   ::= INTEGER {
   mobileOriginated    ( 0 ),
   mobileTerminated    ( 1 )}

CallTypes  ::= SET  OF
   INTEGER {
      mobileOriginated    ( 0 ),
      mobileTerminated    ( 1 )}

CAMELDestinationNumber ::= SEQUENCE  ( SIZE( 1 ) ) OF
   OCTET STRING ( SIZE( 1 .. 41 ) )

CAMELInformation ::= SET {
   cAMELDestinationNumber   [1] IMPLICIT SEQUENCE  ( SIZE( 1 ) ) OF
      OCTET STRING ( SIZE( 1 .. 41 ) ) OPTIONAL,
   connectedNumber          [2] IMPLICIT OCTET STRING OPTIONAL,
   roamingNumber            [3] IMPLICIT OCTET STRING ( SIZE( 1 .. 20 ) ) ( SIZE( 1 .. 9 ) ) OPTIONAL,
   mscOutgoingTKGP          [4] TrunkGroup OPTIONAL,
   seizureTime              [5] IMPLICIT OCTET STRING ( SIZE( 9 ) ) OPTIONAL,
   answerTime               [6] IMPLICIT OCTET STRING ( SIZE( 9 ) ) OPTIONAL,
   releaseTime              [7] IMPLICIT OCTET STRING ( SIZE( 9 ) ) OPTIONAL,
   callDuration             [8] IMPLICIT INTEGER OPTIONAL,
   dataVolume               [9] IMPLICIT INTEGER OPTIONAL,
   cAMELInitCFIndicator     [10] IMPLICIT CAMELInitCFIndicator OPTIONAL,
   causeForTerm             [11] IMPLICIT CauseForTerm OPTIONAL,
   cAMELModification        [12] IMPLICIT ChangedParameters OPTIONAL,
   freeFormatData           [13] IMPLICIT OCTET STRING ( SIZE( 1 .. 160 ) ) OPTIONAL,
   diagnostics              [14] HLRIntResult OPTIONAL,
   freeFormatDataAppend     [15] IMPLICIT BOOLEAN OPTIONAL,
   freeFormatData-2         [16] IMPLICIT OCTET STRING ( SIZE( 1 .. 160 ) ) OPTIONAL,
   freeFormatDataAppend-2   [17] IMPLICIT BOOLEAN OPTIONAL}

CAMELInitCFIndicator ::= ENUMERATED {
   noCAMELCallForwarding    ( 0 ),
   cAMELCallForwarding      ( 1 ) }

CAMELModificationParameters ::= SET {
   callingPartyNumber          [0] IMPLICIT OCTET STRING OPTIONAL,
   callingPartyCategory        [1] IMPLICIT OCTET STRING ( SIZE( 1 ) ) OPTIONAL,
   originalCalledPartyNumber   [2] IMPLICIT OCTET STRING OPTIONAL,
   genericNumbers              [3] IMPLICIT SET  OF
      OCTET STRING OPTIONAL,
   redirectingPartyNumber      [4] IMPLICIT OCTET STRING OPTIONAL,
   redirectionCounter          [5] IMPLICIT INTEGER ( 1 .. 5 ) OPTIONAL}

CAMELSMSInformation ::= SET {
   gsm-SCFAddress                [1] IMPLICIT OCTET STRING ( SIZE( 1 .. 20 ) ) ( SIZE( 1 .. 9 ) ) OPTIONAL,
   serviceKey                    [2] IMPLICIT INTEGER ( 0 .. 2147483647 ) OPTIONAL,
   defaultSMSHandling            [3] IMPLICIT ENUMERATED {
      continueTransaction    ( 0 ),
      releaseTransaction     ( 1 ),
      ...  } OPTIONAL,
   freeFormatData                [4] IMPLICIT OCTET STRING ( SIZE( 1 .. 160 ) ) OPTIONAL,
   callingPartyNumber            [5] IMPLICIT OCTET STRING OPTIONAL,
   destinationSubscriberNumber   [6] IMPLICIT OCTET STRING OPTIONAL,
   cAMELSMSCAddress              [7] IMPLICIT OCTET STRING ( SIZE( 1 .. 20 ) ) OPTIONAL,
   smsReferenceNumber            [8] IMPLICIT OCTET STRING ( SIZE( 1 .. 8 ) ) OPTIONAL}

Category   ::= OCTET STRING ( SIZE( 1 ) )

ChangedParameters ::= SET {
   changeFlags   [0] IMPLICIT BIT STRING {
      callingPartyNumberModified  (0 ),
      callingPartyCategoryModified  (1 ),
      originalCalledPartyNumberModified  (2 ),
      genericNumbersModified  (3 ),
      redirectingPartyNumberModified  (4 ),
      redirectionCounterModified  (5 )},
   changeList    [1] IMPLICIT CAMELModificationParameters OPTIONAL}

ChangeFlags ::= BIT STRING {
   callingPartyNumberModified  (0 ),
   callingPartyCategoryModified  (1 ),
   originalCalledPartyNumberModified  (2 ),
   genericNumbersModified  (3 ),
   redirectingPartyNumberModified  (4 ),
   redirectionCounterModified  (5 )}

ChangeOfClassmark ::= SEQUENCE {
   classmark    [0] IMPLICIT OCTET STRING,
   changeTime   [1] IMPLICIT OCTET STRING ( SIZE( 9 ) )}

ChangeOfRadioChannel ::= SEQUENCE {
   radioChannel        [0] IMPLICIT TrafficChannel,
   changeTime          [1] IMPLICIT OCTET STRING ( SIZE( 9 ) ),
   speechVersionUsed   [2] IMPLICIT OCTET STRING ( SIZE( 1 ) ) OPTIONAL}

ChangeOfService ::= SEQUENCE {
   basicService      [0] BasicService,
   transparencyInd   [1] IMPLICIT TransparencyInd OPTIONAL,
   changeTime        [2] IMPLICIT OCTET STRING ( SIZE( 9 ) ),
   rateIndication    [3] IMPLICIT OCTET STRING ( SIZE( 1 ) ) OPTIONAL,
   fnur              [4] IMPLICIT Fnur OPTIONAL}

ChannelCoding ::= ENUMERATED {
   tchF4800     ( 1 ),
   tchF9600     ( 2 ),
   tchF14400    ( 3 ) }

Classmark  ::= OCTET STRING

ConnectedNumber ::= OCTET STRING

DataVolume ::= INTEGER

Day        ::= INTEGER ( 1 .. 31 )

DayClass   ::= CHOICE {
   distinguishedName          [2] IMPLICIT SEQUENCE  OF
      SET  OF
         IdValue,
   nonSpecificForm            [3] IMPLICIT OCTET STRING,
   localDistinguishedName     [4] IMPLICIT SEQUENCE  OF
      SET  OF
         IdValue}

DayClasses ::= SET  OF
   DayClass

DayDefinition ::= SEQUENCE {
   day        [0] IMPLICIT DayOfTheWeek,
   dayClass   [1] DayClass}

DayDefinitions ::= SET  OF
   DayDefinition

DateDefinition ::= SEQUENCE {
   month      [0] IMPLICIT INTEGER ( 1 .. 12 ),
   day        [1] IMPLICIT INTEGER ( 1 .. 31 ),
   dayClass   [2] DayClass}

DateDefinitions ::= SET  OF
   DateDefinition

DayOfTheWeek ::= ENUMERATED {
   allDays      ( 0 ),
   sunday       ( 1 ),
   monday       ( 2 ),
   tuesday      ( 3 ),
   wednesday    ( 4 ),
   thursday     ( 5 ),
   friday       ( 6 ),
   saturday     ( 7 ) }

Destinations ::= SET  OF
   OsApplication

EmergencyCallIndEnable ::= BOOLEAN

EmergencyCallIndication ::= SEQUENCE {
   cellId     [0] IMPLICIT OCTET STRING ( SIZE( 2 ) ),
   callerId   [1] IMSIorIMEI}

EParameter ::= INTEGER

EquipmentId ::= INTEGER

EquipmentType ::= INTEGER {
   conferenceBridge    ( 0 )}

FileType   ::= INTEGER {
   callRecords           ( 1 ),
   traceRecords          ( 9 ),
   observedIMEITicket    ( 14 )}

Fnur       ::= ENUMERATED {
   fnurNotApplicable         ( 0 ),
   fnur9600-BitsPerSecond    ( 1 ),
   fnur14400BitsPerSecond    ( 2 ),
   fnur19200BitsPerSecond    ( 3 ),
   fnur28800BitsPerSecond    ( 4 ),
   fnur38400BitsPerSecond    ( 5 ),
   fnur48000BitsPerSecond    ( 6 ),
   fnur56000BitsPerSecond    ( 7 ),
   fnur64000BitsPerSecond    ( 8 ),
   fnur33600BitsPerSecond    ( 9 ),
   fnur32000BitsPerSecond    ( 10 ),
   fnur31200BitsPerSecond    ( 11 ) }

ForwardToNumber ::= OCTET STRING ( SIZE( 1 .. 20 ) )

FreeFormatData ::= OCTET STRING ( SIZE( 1 .. 160 ) )

GenericNumber ::= OCTET STRING

GenericNumbers ::= SET  OF
   OCTET STRING

Gsm-SCFAddress ::= OCTET STRING ( SIZE( 1 .. 20 ) ) ( SIZE( 1 .. 9 ) )

GuaranteedBitRate ::= ENUMERATED {
   gbr14400BitsPerSecond    ( 1 ),
   gbr28800BitsPerSecond    ( 2 ),
   gbr32000BitsPerSecond    ( 3 ),
   gbr33600BitsPerSecond    ( 4 ),
   gbr56000BitsPerSecond    ( 5 ),
   gbr57600BitsPerSecond    ( 6 ),
   gbr64000BitsPerSecond    ( 7 ) }

HLRIntResult ::= CHOICE {
   gsm0408Cause                                [0] IMPLICIT INTEGER,
   gsm0902MapErrorValue                        [1] IMPLICIT INTEGER,
   itu-tQ767Cause                              [2] IMPLICIT INTEGER,
   networkSpecificCause                        [3] IMPLICIT ManagementExtension,
   manufacturerSpecificCause                   [4] IMPLICIT ManagementExtension,
   positionMethodFailureCause                  [5] IMPLICIT PositionMethodFailure-Diagnostic,
   unauthorizedLCSClientCause                  [6] IMPLICIT UnauthorizedLCSClient-Diagnostic,
   diameterResultCodeAndExperimentalResult     [7] IMPLICIT INTEGER}

HSCSDParmsChange ::= SEQUENCE {
   changeTime           [0] IMPLICIT OCTET STRING ( SIZE( 9 ) ),
   hSCSDChanAllocated   [1] IMPLICIT INTEGER,
   initiatingParty      [2] IMPLICIT InitiatingParty OPTIONAL,
   aiurRequested        [3] IMPLICIT AiurRequested OPTIONAL,
   chanCodingUsed       [4] IMPLICIT ChannelCoding,
   hSCSDChanRequested   [5] IMPLICIT INTEGER OPTIONAL}

IMEICheckEvent ::= INTEGER {
   mobileOriginatedCall    ( 0 ),
   mobileTerminatedCall    ( 1 ),
   smsMobileOriginating    ( 2 ),
   smsMobileTerminating    ( 3 ),
   ssAction                ( 4 ),
   locationUpdate          ( 5 )}

IMEIStatus ::= ENUMERATED {
   greyListedMobileEquipment        ( 0 ),
   blackListedMobileEquipment       ( 1 ),
   nonWhiteListedMobileEquipment    ( 2 ) }

IMSIorIMEI ::= CHOICE {
   imsi         [0] IMPLICIT OCTET STRING ( SIZE( 3 .. 8 ) ),
   imei         [1] IMPLICIT OCTET STRING ( SIZE( 8 ) )}

InitiatingParty ::= ENUMERATED {
   network       ( 0 ),
   subscriber    ( 1 ) }

LocationCellExtension ::= BIT STRING ( SIZE( 12 ) )

LocationChange ::= SEQUENCE {
   location     [0] IMPLICIT LocationAreaAndCell,
   changeTime   [1] IMPLICIT OCTET STRING ( SIZE( 9 ) )}

Location-info ::= SEQUENCE {
   mscNumber             [1] IMPLICIT OCTET STRING ( SIZE( 1 .. 20 ) ) ( SIZE( 1 .. 9 ) ) OPTIONAL,
   location-area         [2] IMPLICIT OCTET STRING ( SIZE( 2 ) ),
   cell-identification   [3] IMPLICIT OCTET STRING ( SIZE( 2 ) ) OPTIONAL,
   mCC-MNC               [4] IMPLICIT OCTET STRING ( SIZE( 3 ) ) OPTIONAL}

LocUpdResult ::= CHOICE {
   gsm0408Cause                                [0] IMPLICIT INTEGER,
   gsm0902MapErrorValue                        [1] IMPLICIT INTEGER,
   itu-tQ767Cause                              [2] IMPLICIT INTEGER,
   networkSpecificCause                        [3] IMPLICIT ManagementExtension,
   manufacturerSpecificCause                   [4] IMPLICIT ManagementExtension,
   positionMethodFailureCause                  [5] IMPLICIT PositionMethodFailure-Diagnostic,
   unauthorizedLCSClientCause                  [6] IMPLICIT UnauthorizedLCSClient-Diagnostic,
   diameterResultCodeAndExperimentalResult     [7] IMPLICIT INTEGER}

MaximumBitRate ::= ENUMERATED {
   mbr14400BitsPerSecond    ( 1 ),
   mbr28800BitsPerSecond    ( 2 ),
   mbr32000BitsPerSecond    ( 3 ),
   mbr33600BitsPerSecond    ( 4 ),
   mbr56000BitsPerSecond    ( 5 ),
   mbr57600BitsPerSecond    ( 6 ) }

Month      ::= INTEGER ( 1 .. 12 )

MSPowerClasses ::= SET  OF
   INTEGER

NetworkCallReference ::= OCTET STRING ( SIZE( 1 .. 8 ) )

NetworkSpecificCode ::= INTEGER

NetworkSpecificServices ::= SET  OF
   INTEGER

NumOfHSCSDChanRequested ::= INTEGER

NumOfHSCSDChanAllocated ::= INTEGER

ObservedIMEITicketEnable ::= BOOLEAN

OriginalCalledNumber ::= OCTET STRING

OriginDestCombinations ::= SET  OF
   OriginDestCombination

OriginDestCombination ::= SEQUENCE {
   origin        [0] IMPLICIT INTEGER OPTIONAL,
   destination   [1] IMPLICIT INTEGER OPTIONAL}

PartialRecordTimer ::= INTEGER

PartialRecordType ::= ENUMERATED {
   timeLimit                   ( 0 ),
   serviceChange               ( 1 ),
   locationChange              ( 2 ),
   classmarkChange             ( 3 ),
   aocParmChange               ( 4 ),
   radioChannelChange          ( 5 ),
   hSCSDParmChange             ( 6 ),
   changeOfCAMELDestination    ( 7 ) }

PartialRecordTypes ::= SET  OF
   PartialRecordType

RadioChannelsRequested ::= SET  OF
   RadioChanRequested

RadioChanRequested ::= ENUMERATED {
   halfRateChannel          ( 0 ),
   fullRateChannel          ( 1 ),
   dualHalfRatePreferred    ( 2 ),
   dualFullRatePreferred    ( 3 ) }

RateIndication ::= OCTET STRING ( SIZE( 1 ) )

ReasonForServiceChange ::= ENUMERATED {
   msubInitiated           ( 0 ),
   mscInitiated            ( 1 ),
   callSetupFallBack       ( 2 ),
   callSetupChangeOrder    ( 3 ) }

RecordClassDestination ::= CHOICE {
   osApplication     [0] OsApplication,
   fileType          [1] IMPLICIT INTEGER {
      callRecords           ( 1 ),
      traceRecords          ( 9 ),
      observedIMEITicket    ( 14 )}}

RecordClassDestinations ::= SET  OF
   RecordClassDestination

RecordingMethod ::= ENUMERATED {
   inCallRecord    ( 0 ),
   inSSRecord      ( 1 ) }

RedirectingNumber ::= OCTET STRING

RFPowerCapability ::= INTEGER

RoamingNumber ::= OCTET STRING ( SIZE( 1 .. 20 ) ) ( SIZE( 1 .. 9 ) )

RoutingNumber ::= CHOICE {
   roaming       [1] IMPLICIT OCTET STRING ( SIZE( 1 .. 20 ) ) ( SIZE( 1 .. 9 ) ),
   forwarded     [2] IMPLICIT OCTET STRING ( SIZE( 1 .. 20 ) )}

Service    ::= CHOICE {
   teleservice                [1] IMPLICIT OCTET STRING ( SIZE( 1 ) ),
   bearerService              [2] IMPLICIT OCTET STRING ( SIZE( 1 ) ),
   supplementaryService       [3] IMPLICIT OCTET STRING ( SIZE( 1 ) ),
   networkSpecificService     [4] IMPLICIT INTEGER}

ServiceDistanceDependencies ::= SET  OF
   ServiceDistanceDependency

ServiceDistanceDependency ::= SEQUENCE {
   aocService     [0] IMPLICIT INTEGER,
   chargingZone   [1] IMPLICIT INTEGER OPTIONAL}

SimpleIntegerName ::= INTEGER

SimpleStringName ::= GraphicString

SpeechVersionIdentifier ::= OCTET STRING ( SIZE( 1 ) )

SSActionResult ::= CHOICE {
   gsm0408Cause                                [0] IMPLICIT INTEGER,
   gsm0902MapErrorValue                        [1] IMPLICIT INTEGER,
   itu-tQ767Cause                              [2] IMPLICIT INTEGER,
   networkSpecificCause                        [3] IMPLICIT ManagementExtension,
   manufacturerSpecificCause                   [4] IMPLICIT ManagementExtension,
   positionMethodFailureCause                  [5] IMPLICIT PositionMethodFailure-Diagnostic,
   unauthorizedLCSClientCause                  [6] IMPLICIT UnauthorizedLCSClient-Diagnostic,
   diameterResultCodeAndExperimentalResult     [7] IMPLICIT INTEGER}

SSActionType ::= ENUMERATED {
   registration            ( 0 ),
   erasure                 ( 1 ),
   activation              ( 2 ),
   deactivation            ( 3 ),
   interrogation           ( 4 ),
   invocation              ( 5 ),
   passwordRegistration    ( 6 ) }

SSParameters ::= CHOICE {
   forwardedToNumber     [0] IMPLICIT OCTET STRING ( SIZE( 1 .. 20 ) ),
   unstructuredData      [1] IMPLICIT OCTET STRING}

SupplServices ::= SET  OF
   OCTET STRING ( SIZE( 1 ) )

SuppServiceUsed ::= SEQUENCE {
   ssCode     [0] IMPLICIT OCTET STRING ( SIZE( 1 ) ),
   ssTime     [1] IMPLICIT OCTET STRING ( SIZE( 9 ) ) OPTIONAL}

SwitchoverTime ::= SEQUENCE {
   hour       INTEGER ( 0 .. 23 ),
   minute     INTEGER ( 0 .. 59 ),
   second     INTEGER ( 0 .. 59 )}

TariffId   ::= INTEGER

TariffPeriod ::= SEQUENCE {
   switchoverTime   [0] IMPLICIT SwitchoverTime,
   tariffId         [1] IMPLICIT INTEGER}

TariffPeriods ::= SET  OF
   TariffPeriod

TariffSystemStatus ::= ENUMERATED {
   available    ( 0 ),
   checked      ( 1 ),
   standby      ( 2 ),
   active       ( 3 ) }

TrafficChannel ::= ENUMERATED {
   fullRate    ( 0 ),
   halfRate    ( 1 ) }

TranslatedNumber ::= OCTET STRING

TransparencyInd ::= ENUMERATED {
   transparent       ( 0 ),
   nonTransparent    ( 1 ) }

TrunkGroup ::= CHOICE {
   tkgpNumber     [0] IMPLICIT INTEGER,
   tkgpName       [1] IMPLICIT GraphicString}

TSChangeover ::= SEQUENCE {
   newActiveTS      [0] IMPLICIT INTEGER,
   newStandbyTS     [1] IMPLICIT INTEGER,
   changeoverTime   [2] IMPLICIT GeneralizedTime OPTIONAL,
   authkey          [3] IMPLICIT OCTET STRING OPTIONAL,
   checksum         [4] IMPLICIT OCTET STRING OPTIONAL,
   versionNumber    [5] IMPLICIT OCTET STRING OPTIONAL}

TSCheckError ::= SEQUENCE {
   errorId    [0] TSCheckErrorId,
   fail       ANY DEFINED BY errorId  OPTIONAL}

TSCheckErrorId ::= CHOICE {
   globalForm     [0] IMPLICIT OBJECT IDENTIFIER,
   localForm      [1] IMPLICIT INTEGER}

TSCheckResult ::= CHOICE {
   success      [0] IMPLICIT NULL,
   fail         [1] IMPLICIT SET  OF
      TSCheckError}

TSCopyTariffSystem ::= SEQUENCE {
   oldTS      [0] IMPLICIT INTEGER,
   newTS      [1] IMPLICIT INTEGER}

TSNextChange ::= CHOICE {
   noChangeover     [0] IMPLICIT NULL,
   tsChangeover     [1] IMPLICIT TSChangeover}

TypeOfSubscribers ::= ENUMERATED {
   home        ( 0 ),
   visiting    ( 1 ),
   all         ( 2 ) }

TypeOfTransaction ::= ENUMERATED {
   successful      ( 0 ),
   unsuccessful    ( 1 ),
   all             ( 2 ) }

Visited-Location-info ::= SEQUENCE {
   mscNumber   [1] IMPLICIT OCTET STRING ( SIZE( 1 .. 20 ) ) ( SIZE( 1 .. 9 ) ),
   vlrNumber   [2] IMPLICIT OCTET STRING ( SIZE( 1 .. 20 ) ) ( SIZE( 1 .. 9 ) )}

VlrNo      ::= OCTET STRING ( SIZE( 1 .. 20 ) ) ( SIZE( 1 .. 9 ) )


-- X.721 DMI-EXTENSION. The set is the standard form of the original
-- extensible empty table constraint ({, ...}) and does not change BER.
DMI-EXTENSION ::= CLASS {
    &id     OBJECT IDENTIFIER UNIQUE,
    &Value
}
WITH SYNTAX {
    TYPE &Value
    ID &id
}

ManagementExtensionSet DMI-EXTENSION ::= {...}


-- 3GPP TS 29.002 MAP-EXTENSION. ExtensionSet is the standard form of
-- the original extensible empty table constraint ({, ...}).
MAP-EXTENSION ::= CLASS {
    &ExtensionType OPTIONAL,
    &extensionId OBJECT IDENTIFIER
}

ExtensionSet MAP-EXTENSION ::= {...}


-- ITU-T X.711 CMIP-AVA. AvaSet is the standard form of the original
-- extensible empty table constraint ({, ...}).
CMIP-AVA ::= CLASS {
    &id OBJECT IDENTIFIER UNIQUE,
    &Value
}

AvaSet CMIP-AVA ::= {...}

END
