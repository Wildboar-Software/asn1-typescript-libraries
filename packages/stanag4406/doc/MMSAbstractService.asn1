MMSAbstractService
{iso(1) identified-organization(3) nato(26) stanags(0) mmhs(4406)
object-identifiers(0) module(0) abstract-service(3)}
DEFINITIONS
IMPLICIT TAGS ::=
BEGIN
IMPORTS
  -- IPMS information objects
  AutoForwardComment, Heading
    FROM IPMSInformationObjects
    {joint-iso-ccitt mhs-motis(6) ipms(1) modules(0) information-objects(2)}
  -- MMS information objects
  MM, MNRN, MRN, MON, InformationObject
    FROM MMSInformationObjects
    {iso(1) identified-organization(3) nato(26) stanags(0) mmhs(4406)
    object-identifiers(0) module(0) mms(1)}
  -- MTS abstract service
  MessageDeliveryEnvelope, MessageSubmissionEnvelope,
  MessageSubmissionIdentifier, MessageSubmissionTime, ORName,
  ProbeSubmissionEnvelope, ProbeSubmissionIdentifier, ProbeSubmissionTime,
  ReportDeliveryEnvelope, SupplementaryInformation,
  recipient-improperly-specified
    FROM MTSAbstractService
    {joint-iso-ccitt mhs-motis(6) mts(3) modules(0) mts-abstract-service(1)}
  -- Remote Operations
  ERROR, OPERATION, OPERATION-PACKAGE
    FROM Remote-Operations-Information-Objects
    {joint-iso-itu-t remote-operations(4) informationObjects(5) version1(0)}

  id-mpt-origination, id-mpt-reception, id-mpt-management
    FROM MMSObjectIdentifiers
    {iso(1) identified-organization(3) nato(26) stanags(0) mmhs(4406)
    object-identifiers(0)}
  ;

ABSTRACT-ERROR ::= ERROR
ABSTRACT-OPERATION ::= OPERATION
PORT ::= OPERATION-PACKAGE

-- Ports
origination PORT ::= {
 CONSUMER INVOKES
   {originate-probe |
     
    --  Although, national implementation may
    -- support probes within their own domain, probes are not
    -- permitted across national boundaries
     originate-mm | originate-mrn}
 ID                id-mpt-origination}

reception PORT ::= {
 CONSUMER INVOKES
   {receive-report | receive-mm | receive-mrn | receive-mnrn | receive-mon}
 ID                id-mpt-reception}

management PORT ::= {
 CONSUMER INVOKES
   {change-auto-discard | change-auto-acknowledgement | change-auto-forwarding}
 ID                id-mpt-management}

-- Origination abstract operations
-- Probes are prohibited across national boundaries.
originate-probe ABSTRACT-OPERATION ::= {
 ARGUMENT  OriginateProbeArgument
 RESULT    OriginateProbeResult
 ERROR     {subscription-error | recipient-improperly-specified}}

OriginateProbeArgument ::= SET {
  envelope  [0]  ProbeSubmissionEnvelope,
  content   [1]  MM}

OriginateProbeResult ::= SET {
  submission-identifier  [0]  ProbeSubmissionIdentifier,
  submission-time        [1]  ProbeSubmissionTime}

originate-mm ABSTRACT-OPERATION ::= {
 ARGUMENT  OriginateMMArgument
 RESULT    OriginateMMResult
 ERROR     {subscription-error | recipient-improperly-specified}}

OriginateMMArgument ::= SET {
  envelope  [0]  MessageSubmissionEnvelope,
  content   [1]  MM}

OriginateMMResult ::= SET {
  submission-identifier  [0]  MessageSubmissionIdentifier,
  submission-time        [1]  MessageSubmissionTime}

originate-mrn ABSTRACT-OPERATION ::= {
 ARGUMENT  OriginateMRNArgument
 RESULT    OriginateMRNResult
 ERROR     {subscription-error | recipient-improperly-specified}}

OriginateMRNArgument ::= SET {
  envelope  [0]  MessageSubmissionEnvelope,
  content   [1]  MRN}

OriginateMRNResult ::= SET {
  submission-identifier  [0]  MessageSubmissionIdentifier,
  submission-time        [1]  MessageSubmissionTime}

-- Reception abstract operations
receive-report ABSTRACT-OPERATION ::= {
 ARGUMENT      ReceiveReportArgument
 RESULT ERROR  {}}

ReceiveReportArgument ::= SET {
  envelope            [0]  ReportDeliveryEnvelope,
  undelivered-object  [1]  InformationObject OPTIONAL}

receive-mm ABSTRACT-OPERATION ::= {
 ARGUMENT      ReceiveMMArgument
 RESULT ERROR  {}}

ReceiveMMArgument ::= SET {
  envelope  [0]  MessageDeliveryEnvelope,
  content   [1]  MM}

receive-mrn ABSTRACT-OPERATION ::= {
 ARGUMENT      ReceiveMRNArgument
 RESULT ERROR  {}}

ReceiveMRNArgument ::= SET {
  envelope  [0]  MessageDeliveryEnvelope,
  content   [1]  MRN}

receive-mnrn ABSTRACT-OPERATION ::= {
 ARGUMENT      ReceiveMNRNArgument
 RESULT ERROR  {}}

ReceiveMNRNArgument ::= SET {
  envelope  [0]  MessageDeliveryEnvelope,
  content   [1]  MNRN}

receive-mon ABSTRACT-OPERATION ::= {
 ARGUMENT      ReceiveMONArgument
 RESULT ERROR  {}}

ReceiveMONArgument ::= SET {
  envelope  [0]  MessageDeliveryEnvelope,
  content   [1]  MON}

-- Management abstract operations
-- It should be noted that in cases where an implementation has dual 
-- IPM and MM functionality, the management abstract operations may be used 
-- for support of both types of messaging.
change-auto-discard ABSTRACT-OPERATION ::= {
 ARGUMENT       ChangeAutoDiscardArgument
 RESULT ERRORS  {}}

ChangeAutoDiscardArgument ::= SET {
  auto-discard-expired-MMs   [0]  BOOLEAN,
  auto-discard-obsolete-MMs  [1]  BOOLEAN}

change-auto-acknowledgement ABSTRACT-OPERATION ::= {
 ARGUMENT       ChangeAutoAcknowledgementArgument
 RESULT ERRORS  {subscription-error}}

ChangeAutoAcknowledgementArgument ::= SET {
  auto-acknowledge-MMs                 [0]  BOOLEAN,
  auto-acknowledge-suppl-receipt-info  [1]  SupplementaryInformation}

change-auto-forwarding ABSTRACT-OPERATION ::= {
 ARGUMENT       ChangeAutoForwardingArgument
 RESULT ERRORS  {subscription-error | recipient-improperly-specified}}

ChangeAutoForwardingArgument ::= SET {
  autoforward-MMs          [0]  BOOLEAN,
  auto-forward-recipients  [1]  SEQUENCE OF ORName OPTIONAL,
  auto-forward-heading     [2]  Heading OPTIONAL,
  auto-forward-comment     [3]  AutoForwardComment OPTIONAL}

-- Abstract errors
subscription-error ABSTRACT-ERROR ::= {
  PARAMETER  SubscriptionErrorParameter
}

SubscriptionErrorParameter ::= SET {
  problem  [0]  SubscriptionProblem
}

SubscriptionProblem ::= ENUMERATED {
  mms-eos-not-subcribed(0),
  mts-eos-not-subcribed(1)
}

END --of MMSAbstractService
