-- This is not a real module, but these assignments are defined in STANAG 4406.
-- I obtained this from Wireshark's dissector in cdt.asn.
-- I noticed that Wireshark's ASN.1 adds "IMPLICIT" to the tags.
-- It is unclear from the specification whether this is correct,
-- but I think it is a safe guess, since all the other modules use
-- IMPLICIT tags.
CompressedDataType
{iso(1) identified-organization(3) nato(26) stanags(0) mmhs(4406)
object-identifiers(0) id-mcont(4) 2}
DEFINITIONS ::=
BEGIN

id-mmhs-CDT OBJECT IDENTIFIER ::= {
    iso(1)
    identified-organization(3)
    nato(26)
    stanags(0)
    mmhs(4406)
    object-identifiers(0)
    id-mcont(4)
    2
}

id-alg-zlibCompress OBJECT IDENTIFIER ::= {
    iso(1)
    member-body(2)
    us(840)
    rsadsi(113549)
    pkcs(1)
    pkcs-9(9)
    smime(16)
    alg(3)
    8
}

CompressedData ::= SEQUENCE {
    compressionAlgorithm    CompressionAlgorithmIdentifier,
    compressedContentInfo   CompressedContentInfo
}

CompressionAlgorithmIdentifier ::= CHOICE {
    algorithmID-ShortForm   [0] IMPLICIT AlgorithmID-ShortForm,
    algorithmID-OID         [1] IMPLICIT OBJECT IDENTIFIER
}

AlgorithmID-ShortForm ::= INTEGER  {
    zlibCompress (0)
}

CompressedContentInfo ::= SEQUENCE {
    contentType CHOICE { 
        contentType-ShortForm   [0] IMPLICIT ContentType-ShortForm,
        contentType-OID         [1] IMPLICIT OBJECT IDENTIFIER
    },
    compressedContent       [0] EXPLICIT CompressedContent
}

CompressedContent ::= OCTET STRING

ContentType-ShortForm ::= INTEGER  {
    unidentified (0),
    external (1), -- identified by the object-identifier of the EXTERNAL content 
    p1 (2),
    p3 (3),
    p7 (4)
}

END
