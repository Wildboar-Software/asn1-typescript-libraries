-- Derived from data/ldap-schema/glue/01-Group.schema
-- Upstream: http://redmine.ogf.org/projects/glue-wg
-- This module is a container for LDAP schema. It has no module identifier.
-- X- extension fields from the LDAP schema are comments. USAGE userApplications and structural KIND are omitted because they are the defaults.
-- Object classes with no SUP were subclassed from top, the LDAP default (RFC 4512).
LdapGlue01Group DEFINITIONS ::=
BEGIN

IMPORTS

  ATTRIBUTE, OBJECT-CLASS, top
    FROM InformationFramework
      {joint-iso-itu-t ds(5) module(1) informationFramework(1) 9} WITH SUCCESSORS

  caseExactMatch, caseExactSubstringsMatch, directoryString,
    UnboundedDirectoryString
    FROM SelectedAttributeTypes
      {joint-iso-itu-t ds(5) module(1) selectedAttributeTypes(5) 9} WITH SUCCESSORS ;

-- Object identifiers

id-at-gLUE2GroupID OBJECT IDENTIFIER ::= { 1 3 6 1 4 1 6757 100 1 1 36 1 }
id-oc-gLUE2Group OBJECT IDENTIFIER ::= { 1 3 6 1 4 1 6757 100 1 1 36 }

-- Attribute types

-- initial capital of "GLUE2GroupID" lowercased so the assignment is a valuereference.
gLUE2GroupID ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2GroupID", "GLUE2GroupName", "GLUE2GroupLocalID"}
  LDAP-DESC                 "Local ID, not unique"
  ID                        id-at-gLUE2GroupID }

-- Object classes

-- initial capital of "GLUE2Group" lowercased so the assignment is a valuereference.
-- SUP was absent. RFC 4512 treats that as a subclass of top, so SUBCLASS OF { top } was added.
gLUE2Group OBJECT-CLASS ::= {
  SUBCLASS OF               { top }
  MUST CONTAIN              { gLUE2GroupID }
  LDAP-NAME                 {"GLUE2Group"}
  LDAP-DESC                 "Group object"
  ID                        id-oc-gLUE2Group }
END
