-- Derived from data/ldap-schema/ejbca.ldif
-- Upstream: https://github.com/ISBlocksltd/isblocks-java-pki/blob/356b3728fa2e120a8af2e77cf91ae3a037e4182f/doc/ldapschema/85ejbca.ldif#L28
-- This module is a container for LDAP schema. It has no module identifier.
-- X- extension fields from the LDAP schema are comments. USAGE userApplications and structural KIND are omitted because they are the defaults.
LdapEjbca DEFINITIONS ::=
BEGIN

IMPORTS

  ATTRIBUTE, OBJECT-CLASS
    FROM InformationFramework
      {joint-iso-itu-t ds(5) module(1) informationFramework(1) 9} WITH SUCCESSORS

  description
    FROM SelectedAttributeTypes
      {joint-iso-itu-t ds(5) module(1) selectedAttributeTypes(5) 9} WITH SUCCESSORS

  device
    FROM SelectedObjectClasses
      {joint-iso-itu-t ds(5) module(1) selectedObjectClasses(6) 9} WITH SUCCESSORS ;

-- Object identifiers

id-at-ejbcaDeviceCertificate OBJECT IDENTIFIER ::= { 1 3 6 1 4 1 22408 1 1 1 1 }
id-oc-ejbcaDevice OBJECT IDENTIFIER ::= { 1 3 6 1 4 1 22408 1 1 2 1 }

-- Attribute types

-- X-ORIGIN: "EJBCA"
-- LDAP binary syntax has no X.500 directory type here. Represented as OCTET STRING.
ejbcaDeviceCertificate ATTRIBUTE ::= {
  WITH SYNTAX               OCTET STRING
  LDAP-SYNTAX               { 1 3 6 1 4 1 1466 115 121 1 5 }
  LDAP-NAME                 {"ejbcaDeviceCertificate"}
  LDAP-DESC                 "Cerfificate for devices"
  ID                        id-at-ejbcaDeviceCertificate }

-- Object classes

-- X-ORIGIN: "EJBCA"
ejbcaDevice OBJECT-CLASS ::= {
  SUBCLASS OF               { device }
  KIND                      auxiliary
  MUST CONTAIN              { ejbcaDeviceCertificate }
  MAY CONTAIN               { description }
  LDAP-NAME                 {"ejbcaDevice"}
  LDAP-DESC                 "subclass for adding certificates to devices"
  ID                        id-oc-ejbcaDevice }
END
