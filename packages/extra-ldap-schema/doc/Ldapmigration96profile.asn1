-- Derived from data/ldap-schema/ldapmigration/96profile.ldif
-- This module is a container for LDAP schema. It has no module identifier.
-- X- extension fields from the LDAP schema are comments. USAGE userApplications and structural KIND are omitted because they are the defaults.
-- 15 elements were omitted because their OIDs are already defined. See CONVERSION-REPORT.txt.
Ldapmigration96profile DEFINITIONS ::=
BEGIN

IMPORTS

  OBJECT-CLASS, top
    FROM InformationFramework
      {joint-iso-itu-t ds(5) module(1) informationFramework(1) 9} WITH SUCCESSORS

  commonName
    FROM SelectedAttributeTypes
      {joint-iso-itu-t ds(5) module(1) selectedAttributeTypes(5) 9} WITH SUCCESSORS

  attributeMap, authenticationMethod, bindTimeLimit, credentialLevel,
    defaultSearchBase, defaultSearchScope, defaultServerList, followReferrals,
    objectclassMap, preferredServerList, profileTTL, searchTimeLimit,
    serviceAuthenticationMethod, serviceCredentialLevel,
    serviceSearchDescriptor
    FROM DUAConf
      {iso(1) identified-organization(3) dod(6) internet(1) private(4) enterprise(1) wildboar(56490) module(1) duaconf(4)} WITH SUCCESSORS ;

-- Object identifiers

-- Thought to be invalid. Several LDAP schemas publish 1.3.6.1.4.1.11.1.3.1.2.4 for DUAConfigProfile, but that number does not appear on oid-base.com.
-- RFC 4876 defines DUAConfigProfile with the same name and an OID that ends in 5 instead of 4. That class is already duaConfigProfile in DUAConf.
-- The valuereference and this OID identifier were renamed to show the invalid status. The numeric arcs are the ones this source published and were not rewritten. LDAP-NAME keeps the original string.
id-oc-invalid-dUAConfigProfile OBJECT IDENTIFIER ::= { 1 3 6 1 4 1 11 1 3 1 2 4 }

-- Object classes

-- X-ORIGIN: "user defined"
-- Thought to be invalid. Several LDAP schemas publish 1.3.6.1.4.1.11.1.3.1.2.4 for DUAConfigProfile, but that number does not appear on oid-base.com.
-- RFC 4876 defines DUAConfigProfile with the same name and an OID that ends in 5 instead of 4. That class is already duaConfigProfile in DUAConf.
-- The valuereference and this OID identifier were renamed to show the invalid status. The numeric arcs are the ones this source published and were not rewritten. LDAP-NAME keeps the original string.
invalid-dUAConfigProfile OBJECT-CLASS ::= {
  SUBCLASS OF               { top }
  MUST CONTAIN              { commonName }
  MAY CONTAIN               { attributeMap
                              | authenticationMethod
                              | bindTimeLimit
                              | credentialLevel
                              | defaultSearchBase
                              | defaultSearchScope
                              | defaultServerList
                              | followReferrals
                              | objectclassMap
                              | preferredServerList
                              | profileTTL
                              | searchTimeLimit
                              | serviceAuthenticationMethod
                              | serviceCredentialLevel
                              | serviceSearchDescriptor }
  LDAP-NAME                 {"DUAConfigProfile"}
  ID                        id-oc-invalid-dUAConfigProfile }
END
