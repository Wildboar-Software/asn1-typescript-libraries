-- Derived from data/ldap-schema/trust-fabric.ldif
-- This module is a container for LDAP schema. It has no module identifier.
-- X- extension fields from the LDAP schema are comments. USAGE userApplications and structural KIND are omitted because they are the defaults.
LdapTrustFabric DEFINITIONS ::=
BEGIN

IMPORTS

  ATTRIBUTE, OBJECT-CLASS, top
    FROM InformationFramework
      {joint-iso-itu-t ds(5) module(1) informationFramework(1) 9} WITH SUCCESSORS

  caseExactMatch, caseExactSubstringsMatch, caseIgnoreMatch,
    caseIgnoreSubstringsMatch, commonName, description, directoryString,
    localityName, organizationalUnitName, organizationName, seeAlso,
    UnboundedDirectoryString
    FROM SelectedAttributeTypes
      {joint-iso-itu-t ds(5) module(1) selectedAttributeTypes(5) 9} WITH SUCCESSORS

  displayName
    FROM InetOrgPerson
      {iso(1) identified-organization(3) dod(6) internet(1) private(4) enterprise(1) wildboar(56490) module(1) inetorgperson(5)} WITH SUCCESSORS ;

-- Object identifiers

id-at-tf-workspace-id OBJECT IDENTIFIER ::= { 1 3 6 1 4 1 55988 1 2 3 601 }
id-at-tf-application-id OBJECT IDENTIFIER ::= { 1 3 6 1 4 1 55988 1 2 3 602 }
id-at-tf-app-instance-id OBJECT IDENTIFIER ::= { 1 3 6 1 4 1 55988 1 2 3 603 }
id-at-tf-source-repository OBJECT IDENTIFIER ::= { 1 3 6 1 4 1 55988 1 2 3 611 }
id-at-tf-issue-repository OBJECT IDENTIFIER ::= { 1 3 6 1 4 1 55988 1 2 3 612 }
id-at-tf-software-repository OBJECT IDENTIFIER ::= { 1 3 6 1 4 1 55988 1 2 3 613 }
id-at-tf-software-image OBJECT IDENTIFIER ::= { 1 3 6 1 4 1 55988 1 2 3 614 }
id-at-tf-version OBJECT IDENTIFIER ::= { 1 3 6 1 4 1 55988 1 2 3 615 }
id-at-tf-creator OBJECT IDENTIFIER ::= { 1 3 6 1 4 1 55988 1 2 3 621 }
id-at-tf-maintainers OBJECT IDENTIFIER ::= { 1 3 6 1 4 1 55988 1 2 3 622 }
id-at-tf-approvers OBJECT IDENTIFIER ::= { 1 3 6 1 4 1 55988 1 2 3 623 }
id-at-tf-owners OBJECT IDENTIFIER ::= { 1 3 6 1 4 1 55988 1 2 3 624 }
id-at-tf-rel-mangers OBJECT IDENTIFIER ::= { 1 3 6 1 4 1 55988 1 2 3 625 }
id-at-tf-developers OBJECT IDENTIFIER ::= { 1 3 6 1 4 1 55988 1 2 3 626 }
id-oc-tf-workspace OBJECT IDENTIFIER ::= { 1 3 6 1 4 1 55988 1 2 4 101 }
id-oc-tf-application OBJECT IDENTIFIER ::= { 1 3 6 1 4 1 55988 1 2 4 102 }
id-oc-tf-app-instance OBJECT IDENTIFIER ::= { 1 3 6 1 4 1 55988 1 2 4 103 }
id-oc-tf-am-baseroles OBJECT IDENTIFIER ::= { 1 3 6 1 4 1 55988 1 2 4 201 }
id-oc-tf-am-devops OBJECT IDENTIFIER ::= { 1 3 6 1 4 1 55988 1 2 4 202 }

-- Attribute types

tf-workspace-id ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"tf-workspace-id"}
  LDAP-DESC                 "Identifier for the Business Function/workspace"
  ID                        id-at-tf-workspace-id }

tf-application-id ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"tf-application-id"}
  LDAP-DESC                 "Application Identifier"
  ID                        id-at-tf-application-id }

tf-app-instance-id ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"tf-app-instance-id"}
  LDAP-DESC                 "Application Deployment (instance) Identifier"
  ID                        id-at-tf-app-instance-id }

-- Active Directory syntax 2.5.5.3 (String(Case)), from MS-ADTS. This is not an LDAP syntax OID.
-- EQUALITY caseExactString was taken as caseExactMatch from SelectedAttributeTypes.
tf-source-repository ATTRIBUTE ::= {
  WITH SYNTAX               UnboundedDirectoryString
  EQUALITY MATCHING RULE    caseExactMatch
  SUBSTRINGS MATCHING RULE  caseExactSubstringsMatch
  LDAP-SYNTAX               { 2 5 5 3 }
  LDAP-NAME                 {"tf-source-repository"}
  LDAP-DESC                 "Source code repository URI"
  ID                        id-at-tf-source-repository }

-- Active Directory syntax 2.5.5.3 (String(Case)), from MS-ADTS. This is not an LDAP syntax OID.
-- EQUALITY caseExactString was taken as caseExactMatch from SelectedAttributeTypes.
tf-issue-repository ATTRIBUTE ::= {
  WITH SYNTAX               UnboundedDirectoryString
  EQUALITY MATCHING RULE    caseExactMatch
  SUBSTRINGS MATCHING RULE  caseExactSubstringsMatch
  LDAP-SYNTAX               { 2 5 5 3 }
  LDAP-NAME                 {"tf-issue-repository"}
  LDAP-DESC                 "Issue tracking system/repository URI"
  ID                        id-at-tf-issue-repository }

-- Active Directory syntax 2.5.5.3 (String(Case)), from MS-ADTS. This is not an LDAP syntax OID.
-- EQUALITY caseExactString was taken as caseExactMatch from SelectedAttributeTypes.
tf-software-repository ATTRIBUTE ::= {
  WITH SYNTAX               UnboundedDirectoryString
  EQUALITY MATCHING RULE    caseExactMatch
  SUBSTRINGS MATCHING RULE  caseExactSubstringsMatch
  LDAP-SYNTAX               { 2 5 5 3 }
  LDAP-NAME                 {"tf-software-repository"}
  LDAP-DESC                 "Software download repository (PKG/Container/ISO repo) URI"
  ID                        id-at-tf-software-repository }

-- Active Directory syntax 2.5.5.3 (String(Case)), from MS-ADTS. This is not an LDAP syntax OID.
-- EQUALITY caseExactString was taken as caseExactMatch from SelectedAttributeTypes.
tf-software-image ATTRIBUTE ::= {
  WITH SYNTAX               UnboundedDirectoryString
  EQUALITY MATCHING RULE    caseExactMatch
  SUBSTRINGS MATCHING RULE  caseExactSubstringsMatch
  LDAP-SYNTAX               { 2 5 5 3 }
  LDAP-NAME                 {"tf-software-image"}
  LDAP-DESC                 "Software Image URI for a specific version"
  ID                        id-at-tf-software-image }

tf-version ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"tf-version"}
  LDAP-DESC                 "Version number string"
  ID                        id-at-tf-version }

tf-creator ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"tf-creator"}
  LDAP-DESC                 "UID of the creator"
  ID                        id-at-tf-creator }

tf-maintainers ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"tf-maintainers"}
  LDAP-DESC                 "Group ID of the maintainers"
  ID                        id-at-tf-maintainers }

tf-approvers ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"tf-approvers"}
  LDAP-DESC                 "Group ID of the approvers"
  ID                        id-at-tf-approvers }

tf-owners ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"tf-owners"}
  LDAP-DESC                 "Group ID of the Funnctional owners"
  ID                        id-at-tf-owners }

tf-rel-mangers ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"tf-rel-mangers"}
  LDAP-DESC                 "Group ID of the release managers"
  ID                        id-at-tf-rel-mangers }

tf-developers ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"tf-developers"}
  LDAP-DESC                 "Group ID of the developers"
  ID                        id-at-tf-developers }

-- Object classes

tf-workspace OBJECT-CLASS ::= {
  SUBCLASS OF               { top }
  MUST CONTAIN              { organizationName
                              | tf-workspace-id }
  MAY CONTAIN               { displayName
                              | seeAlso
                              | description
                              | tf-source-repository
                              | tf-issue-repository
                              | tf-creator }
  LDAP-NAME                 {"tf-workspace"}
  ID                        id-oc-tf-workspace }

tf-application OBJECT-CLASS ::= {
  SUBCLASS OF               { top }
  MUST CONTAIN              { organizationalUnitName
                              | tf-application-id }
  MAY CONTAIN               { displayName
                              | seeAlso
                              | description
                              | tf-source-repository
                              | tf-software-repository
                              | tf-issue-repository
                              | tf-creator }
  LDAP-NAME                 {"tf-application"}
  ID                        id-oc-tf-application }

tf-app-instance OBJECT-CLASS ::= {
  SUBCLASS OF               { top }
  MUST CONTAIN              { commonName
                              | tf-app-instance-id
                              | localityName
                              | tf-version }
  MAY CONTAIN               { displayName
                              | seeAlso
                              | description
                              | tf-software-repository
                              | tf-software-image
                              | tf-issue-repository
                              | tf-creator }
  LDAP-NAME                 {"tf-app-instance"}
  ID                        id-oc-tf-app-instance }

tf-am-baseroles OBJECT-CLASS ::= {
  SUBCLASS OF               { top }
  KIND                      auxiliary
  MAY CONTAIN               { tf-maintainers
                              | tf-approvers
                              | tf-owners }
  LDAP-NAME                 {"tf-am-baseroles"}
  ID                        id-oc-tf-am-baseroles }

tf-am-devops OBJECT-CLASS ::= {
  SUBCLASS OF               { top }
  KIND                      auxiliary
  MAY CONTAIN               { tf-developers
                              | tf-maintainers
                              | tf-rel-mangers
                              | tf-approvers
                              | tf-owners }
  LDAP-NAME                 {"tf-am-devops"}
  ID                        id-oc-tf-am-devops }
END
