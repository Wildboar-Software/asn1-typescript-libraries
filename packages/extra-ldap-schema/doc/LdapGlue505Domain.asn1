-- Derived from data/ldap-schema/glue/5-05-Domain.schema
-- Upstream: http://redmine.ogf.org/projects/glue-wg
-- This module is a container for LDAP schema. It has no module identifier.
-- X- extension fields from the LDAP schema are comments. USAGE userApplications and structural KIND are omitted because they are the defaults.
LdapGlue505Domain DEFINITIONS ::=
BEGIN

IMPORTS

  ATTRIBUTE, OBJECT-CLASS
    FROM InformationFramework
      {joint-iso-itu-t ds(5) module(1) informationFramework(1) 9} WITH SUCCESSORS

  caseExactMatch, caseExactSubstringsMatch, directoryString, integer,
    UnboundedDirectoryString
    FROM SelectedAttributeTypes
      {joint-iso-itu-t ds(5) module(1) selectedAttributeTypes(5) 9} WITH SUCCESSORS

  gLUE2Entity
    FROM LdapGlue501Entity ;

-- Object identifiers

id-at-gLUE2DomainID OBJECT IDENTIFIER ::= { 1 3 6 1 4 1 6757 100 1 1 5 1 }
id-at-gLUE2DomainDescription OBJECT IDENTIFIER ::= { 1 3 6 1 4 1 6757 100 1 1 5 2 }
id-at-gLUE2DomainWWW OBJECT IDENTIFIER ::= { 1 3 6 1 4 1 6757 100 1 1 5 3 }
id-oc-gLUE2Domain OBJECT IDENTIFIER ::= { 1 3 6 1 4 1 6757 100 1 1 5 }
id-at-gLUE2AdminDomainDistributed OBJECT IDENTIFIER ::= { 1 3 6 1 4 1 6757 100 1 1 6 1 }
id-at-gLUE2AdminDomainOwner OBJECT IDENTIFIER ::= { 1 3 6 1 4 1 6757 100 1 1 6 2 }
id-at-gLUE2AdminDomainAdminDomainForeignKey OBJECT IDENTIFIER ::= { 1 3 6 1 4 1 6757 100 1 1 6 4 }
id-oc-gLUE2AdminDomain OBJECT IDENTIFIER ::= { 1 3 6 1 4 1 6757 100 1 1 6 }
id-at-gLUE2UserDomainLevel OBJECT IDENTIFIER ::= { 1 3 6 1 4 1 6757 100 1 1 7 1 }
id-at-gLUE2UserDomainUserManager OBJECT IDENTIFIER ::= { 1 3 6 1 4 1 6757 100 1 1 7 2 }
id-at-gLUE2UserDomainMember OBJECT IDENTIFIER ::= { 1 3 6 1 4 1 6757 100 1 1 7 3 }
id-at-gLUE2UserDomainUserDomainForeignKey OBJECT IDENTIFIER ::= { 1 3 6 1 4 1 6757 100 1 1 7 5 }
id-oc-gLUE2UserDomain OBJECT IDENTIFIER ::= { 1 3 6 1 4 1 6757 100 1 1 7 }

-- Attribute types

-- initial capital of "GLUE2DomainID" lowercased so the assignment is a valuereference.
gLUE2DomainID ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2DomainID"}
  LDAP-DESC                 "A description of the domain"
  ID                        id-at-gLUE2DomainID }

-- initial capital of "GLUE2DomainDescription" lowercased so the assignment is a valuereference.
gLUE2DomainDescription ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2DomainDescription"}
  LDAP-DESC                 "A description of the domain"
  ID                        id-at-gLUE2DomainDescription }

-- initial capital of "GLUE2DomainWWW" lowercased so the assignment is a valuereference.
gLUE2DomainWWW ATTRIBUTE ::= {
  WITH SYNTAX               UnboundedDirectoryString
  EQUALITY MATCHING RULE    caseExactMatch
  SUBSTRINGS MATCHING RULE  caseExactSubstringsMatch
  LDAP-SYNTAX               directoryString.&id
  LDAP-NAME                 {"GLUE2DomainWWW"}
  LDAP-DESC                 "The URL identifying a web page with more information about the domain"
  ID                        id-at-gLUE2DomainWWW }

-- initial capital of "GLUE2AdminDomainDistributed" lowercased so the assignment is a valuereference.
gLUE2AdminDomainDistributed ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2AdminDomainDistributed"}
  LDAP-DESC                 "True if the services managed by the AdminDomain are considered geographically distributed by the administrators themselves"
  ID                        id-at-gLUE2AdminDomainDistributed }

-- initial capital of "GLUE2AdminDomainOwner" lowercased so the assignment is a valuereference.
gLUE2AdminDomainOwner ATTRIBUTE ::= {
  WITH SYNTAX               UnboundedDirectoryString
  EQUALITY MATCHING RULE    caseExactMatch
  SUBSTRINGS MATCHING RULE  caseExactSubstringsMatch
  LDAP-SYNTAX               directoryString.&id
  LDAP-NAME                 {"GLUE2AdminDomainOwner"}
  LDAP-DESC                 "Owner of the managed resources"
  ID                        id-at-gLUE2AdminDomainOwner }

-- initial capital of "GLUE2AdminDomainAdminDomainForeignKey" lowercased so the assignment is a valuereference.
gLUE2AdminDomainAdminDomainForeignKey ATTRIBUTE ::= {
  WITH SYNTAX               UnboundedDirectoryString
  EQUALITY MATCHING RULE    caseExactMatch
  SUBSTRINGS MATCHING RULE  caseExactSubstringsMatch
  LDAP-SYNTAX               directoryString.&id
  LDAP-NAME                 {"GLUE2AdminDomainAdminDomainForeignKey"}
  LDAP-DESC                 "ForeignKey"
  ID                        id-at-gLUE2AdminDomainAdminDomainForeignKey }

-- initial capital of "GLUE2UserDomainLevel" lowercased so the assignment is a valuereference.
gLUE2UserDomainLevel ATTRIBUTE ::= {
  WITH SYNTAX               INTEGER
  SINGLE VALUE              TRUE
  LDAP-SYNTAX               integer.&id
  LDAP-NAME                 {"GLUE2UserDomainLevel"}
  LDAP-DESC                 "The number of hops to reach the root for hierarchically organized domains described by the composed by association (0 is for the root)."
  ID                        id-at-gLUE2UserDomainLevel }

-- initial capital of "GLUE2UserDomainUserManager" lowercased so the assignment is a valuereference.
gLUE2UserDomainUserManager ATTRIBUTE ::= {
  WITH SYNTAX               UnboundedDirectoryString
  EQUALITY MATCHING RULE    caseExactMatch
  SUBSTRINGS MATCHING RULE  caseExactSubstringsMatch
  LDAP-SYNTAX               directoryString.&id
  LDAP-NAME                 {"GLUE2UserDomainUserManager"}
  LDAP-DESC                 "The Endpoint ID managing the users part of the domain and the related attributes such as groups or roles"
  ID                        id-at-gLUE2UserDomainUserManager }

-- initial capital of "GLUE2UserDomainMember" lowercased so the assignment is a valuereference.
gLUE2UserDomainMember ATTRIBUTE ::= {
  WITH SYNTAX               UnboundedDirectoryString
  EQUALITY MATCHING RULE    caseExactMatch
  SUBSTRINGS MATCHING RULE  caseExactSubstringsMatch
  LDAP-SYNTAX               directoryString.&id
  LDAP-NAME                 {"GLUE2UserDomainMember"}
  LDAP-DESC                 "An identifier for a user in this user domain"
  ID                        id-at-gLUE2UserDomainMember }

-- initial capital of "GLUE2UserDomainUserDomainForeignKey" lowercased so the assignment is a valuereference.
gLUE2UserDomainUserDomainForeignKey ATTRIBUTE ::= {
  WITH SYNTAX               UnboundedDirectoryString
  EQUALITY MATCHING RULE    caseExactMatch
  SUBSTRINGS MATCHING RULE  caseExactSubstringsMatch
  LDAP-SYNTAX               directoryString.&id
  LDAP-NAME                 {"GLUE2UserDomainUserDomainForeignKey"}
  LDAP-DESC                 "ForeignKey"
  ID                        id-at-gLUE2UserDomainUserDomainForeignKey }

-- Object classes

-- initial capital of "GLUE2Domain" lowercased so the assignment is a valuereference.
gLUE2Domain OBJECT-CLASS ::= {
  SUBCLASS OF               { gLUE2Entity }
  MUST CONTAIN              { gLUE2DomainID }
  MAY CONTAIN               { gLUE2DomainDescription
                              | gLUE2DomainWWW }
  LDAP-NAME                 {"GLUE2Domain"}
  LDAP-DESC                 "A Domain"
  ID                        id-oc-gLUE2Domain }

-- initial capital of "GLUE2AdminDomain" lowercased so the assignment is a valuereference.
gLUE2AdminDomain OBJECT-CLASS ::= {
  SUBCLASS OF               { gLUE2Domain }
  MAY CONTAIN               { gLUE2AdminDomainDistributed
                              | gLUE2AdminDomainOwner
                              | gLUE2AdminDomainAdminDomainForeignKey }
  LDAP-NAME                 {"GLUE2AdminDomain"}
  LDAP-DESC                 "A collection of actors that can be assigned with administrative roles and privileges to services via policies. An AdminDomain manages services that can be geographically distributed, nevertheless a primary location should be identified."
  ID                        id-oc-gLUE2AdminDomain }

-- initial capital of "GLUE2UserDomain" lowercased so the assignment is a valuereference.
gLUE2UserDomain OBJECT-CLASS ::= {
  SUBCLASS OF               { gLUE2Domain }
  MAY CONTAIN               { gLUE2UserDomainLevel
                              | gLUE2UserDomainUserManager
                              | gLUE2UserDomainMember
                              | gLUE2UserDomainUserDomainForeignKey }
  LDAP-NAME                 {"GLUE2UserDomain"}
  LDAP-DESC                 "A collection of actors that can be assigned with user roles and privileges to services or shares via policies"
  ID                        id-oc-gLUE2UserDomain }
END
