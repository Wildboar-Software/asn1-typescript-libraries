-- Derived from data/ldap-schema/glue/5-08-Share.schema
-- Upstream: http://redmine.ogf.org/projects/glue-wg
-- This module is a container for LDAP schema. It has no module identifier.
-- X- extension fields from the LDAP schema are comments. USAGE userApplications and structural KIND are omitted because they are the defaults.
LdapGlue508Share DEFINITIONS ::=
BEGIN

IMPORTS

  ATTRIBUTE, OBJECT-CLASS
    FROM InformationFramework
      {joint-iso-itu-t ds(5) module(1) informationFramework(1) 9} WITH SUCCESSORS

  caseExactMatch, caseExactSubstringsMatch, directoryString,
    UnboundedDirectoryString
    FROM SelectedAttributeTypes
      {joint-iso-itu-t ds(5) module(1) selectedAttributeTypes(5) 9} WITH SUCCESSORS

  gLUE2Entity
    FROM LdapGlue501Entity ;

-- Object identifiers

id-at-gLUE2ShareID OBJECT IDENTIFIER ::= { 1 3 6 1 4 1 6757 100 1 1 10 1 }
id-at-gLUE2ShareDescription OBJECT IDENTIFIER ::= { 1 3 6 1 4 1 6757 100 1 1 10 2 }
id-at-gLUE2ShareEndpointForeignKey OBJECT IDENTIFIER ::= { 1 3 6 1 4 1 6757 100 1 1 10 3 }
id-at-gLUE2ShareResourceForeignKey OBJECT IDENTIFIER ::= { 1 3 6 1 4 1 6757 100 1 1 10 4 }
id-at-gLUE2ShareServiceForeignKey OBJECT IDENTIFIER ::= { 1 3 6 1 4 1 6757 100 1 1 10 5 }
id-oc-gLUE2Share OBJECT IDENTIFIER ::= { 1 3 6 1 4 1 6757 100 1 1 10 }

-- Attribute types

-- initial capital of "GLUE2ShareID" lowercased so the assignment is a valuereference.
gLUE2ShareID ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2ShareID"}
  LDAP-DESC                 "Globally unique ID"
  ID                        id-at-gLUE2ShareID }

-- initial capital of "GLUE2ShareDescription" lowercased so the assignment is a valuereference.
gLUE2ShareDescription ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2ShareDescription"}
  LDAP-DESC                 "Description of this share"
  ID                        id-at-gLUE2ShareDescription }

-- initial capital of "GLUE2ShareEndpointForeignKey" lowercased so the assignment is a valuereference.
gLUE2ShareEndpointForeignKey ATTRIBUTE ::= {
  WITH SYNTAX               UnboundedDirectoryString
  EQUALITY MATCHING RULE    caseExactMatch
  SUBSTRINGS MATCHING RULE  caseExactSubstringsMatch
  LDAP-SYNTAX               directoryString.&id
  LDAP-NAME                 {"GLUE2ShareEndpointForeignKey"}
  LDAP-DESC                 "ForeignKey"
  ID                        id-at-gLUE2ShareEndpointForeignKey }

-- initial capital of "GLUE2ShareResourceForeignKey" lowercased so the assignment is a valuereference.
gLUE2ShareResourceForeignKey ATTRIBUTE ::= {
  WITH SYNTAX               UnboundedDirectoryString
  EQUALITY MATCHING RULE    caseExactMatch
  SUBSTRINGS MATCHING RULE  caseExactSubstringsMatch
  LDAP-SYNTAX               directoryString.&id
  LDAP-NAME                 {"GLUE2ShareResourceForeignKey"}
  LDAP-DESC                 "ForeignKey"
  ID                        id-at-gLUE2ShareResourceForeignKey }

-- initial capital of "GLUE2ShareServiceForeignKey" lowercased so the assignment is a valuereference.
gLUE2ShareServiceForeignKey ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2ShareServiceForeignKey"}
  LDAP-DESC                 "ForeignKey"
  ID                        id-at-gLUE2ShareServiceForeignKey }

-- Object classes

-- initial capital of "GLUE2Share" lowercased so the assignment is a valuereference.
gLUE2Share OBJECT-CLASS ::= {
  SUBCLASS OF               { gLUE2Entity }
  MUST CONTAIN              { gLUE2ShareID
                              | gLUE2ShareServiceForeignKey }
  MAY CONTAIN               { gLUE2ShareDescription
                              | gLUE2ShareEndpointForeignKey
                              | gLUE2ShareResourceForeignKey }
  LDAP-NAME                 {"GLUE2Share"}
  LDAP-DESC                 "A share"
  ID                        id-oc-gLUE2Share }
END
