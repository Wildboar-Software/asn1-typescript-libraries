-- Derived from data/ldap-schema/glue/6-10-ToStorageService.schema
-- Upstream: http://redmine.ogf.org/projects/glue-wg
-- This module is a container for LDAP schema. It has no module identifier.
-- X- extension fields from the LDAP schema are comments. USAGE userApplications and structural KIND are omitted because they are the defaults.
LdapGlue610ToStorageService DEFINITIONS ::=
BEGIN

IMPORTS

  ATTRIBUTE, OBJECT-CLASS
    FROM InformationFramework
      {joint-iso-itu-t ds(5) module(1) informationFramework(1) 9} WITH SUCCESSORS

  caseExactMatch, caseExactSubstringsMatch, directoryString,
    UnboundedDirectoryString
    FROM SelectedAttributeTypes
      {joint-iso-itu-t ds(5) module(1) selectedAttributeTypes(5) 9} WITH SUCCESSORS

  gLUE2Entity
    FROM LdapGlue501Entity ;

-- Object identifiers

id-at-gLUE2ToStorageServiceID OBJECT IDENTIFIER ::= { 1 3 6 1 4 1 6757 100 1 1 26 1 }
id-at-gLUE2ToStorageServiceLocalPath OBJECT IDENTIFIER ::= { 1 3 6 1 4 1 6757 100 1 1 26 2 }
id-at-gLUE2ToStorageServiceRemotePath OBJECT IDENTIFIER ::= { 1 3 6 1 4 1 6757 100 1 1 26 3 }
id-at-gLUE2ToStorageServiceComputingServiceForeignKey OBJECT IDENTIFIER ::= { 1 3 6 1 4 1 6757 100 1 1 26 4 }
id-at-gLUE2ToStorageServiceStorageServiceForeignKey OBJECT IDENTIFIER ::= { 1 3 6 1 4 1 6757 100 1 1 26 5 }
id-oc-gLUE2ToStorageService OBJECT IDENTIFIER ::= { 1 3 6 1 4 1 6757 100 1 1 26 }

-- Attribute types

-- initial capital of "GLUE2ToStorageServiceID" lowercased so the assignment is a valuereference.
gLUE2ToStorageServiceID ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2ToStorageServiceID"}
  LDAP-DESC                 "Globally unique ID"
  ID                        id-at-gLUE2ToStorageServiceID }

-- initial capital of "GLUE2ToStorageServiceLocalPath" lowercased so the assignment is a valuereference.
gLUE2ToStorageServiceLocalPath ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2ToStorageServiceLocalPath"}
  LDAP-DESC                 "The local path of the computing service enabling to access a remote path in the associated storage service (this is typically an NFS mount point)"
  ID                        id-at-gLUE2ToStorageServiceLocalPath }

-- initial capital of "GLUE2ToStorageServiceRemotePath" lowercased so the assignment is a valuereference.
gLUE2ToStorageServiceRemotePath ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2ToStorageServiceRemotePath"}
  LDAP-DESC                 "The remote path in the storage service which is associated the local path in the computing service (this is typically an NFS exported directory)"
  ID                        id-at-gLUE2ToStorageServiceRemotePath }

-- initial capital of "GLUE2ToStorageServiceComputingServiceForeignKey" lowercased so the assignment is a valuereference.
gLUE2ToStorageServiceComputingServiceForeignKey ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2ToStorageServiceComputingServiceForeignKey"}
  LDAP-DESC                 "ForeignKey"
  ID                        id-at-gLUE2ToStorageServiceComputingServiceForeignKey }

-- initial capital of "GLUE2ToStorageServiceStorageServiceForeignKey" lowercased so the assignment is a valuereference.
gLUE2ToStorageServiceStorageServiceForeignKey ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2ToStorageServiceStorageServiceForeignKey"}
  LDAP-DESC                 "ForeignKey"
  ID                        id-at-gLUE2ToStorageServiceStorageServiceForeignKey }

-- Object classes

-- initial capital of "GLUE2ToStorageService" lowercased so the assignment is a valuereference.
gLUE2ToStorageService OBJECT-CLASS ::= {
  SUBCLASS OF               { gLUE2Entity }
  MUST CONTAIN              { gLUE2ToStorageServiceID
                              | gLUE2ToStorageServiceLocalPath
                              | gLUE2ToStorageServiceRemotePath
                              | gLUE2ToStorageServiceComputingServiceForeignKey
                              | gLUE2ToStorageServiceStorageServiceForeignKey }
  LDAP-NAME                 {"GLUE2ToStorageService"}
  LDAP-DESC                 "Description of a POSIX access via a file system technology enabling the computing service to access the associated storage service"
  ID                        id-oc-gLUE2ToStorageService }
END
