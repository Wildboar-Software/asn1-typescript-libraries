-- Derived from data/ldap-schema/tacacs.schema
-- This module is a container for LDAP schema. It has no module identifier.
-- X- extension fields from the LDAP schema are comments. USAGE userApplications and structural KIND are omitted because they are the defaults.
-- LDAP {length} bounds on directory strings are DirectoryString{n}. Bounds on IA5String, PrintableString, NumericString, and OCTET STRING are SIZE (1..n). Other bounds stay comments because the LDAP figure is an encoded-length hint.
LdapTacacs DEFINITIONS ::=
BEGIN

IMPORTS

  ATTRIBUTE, OBJECT-CLASS, top
    FROM InformationFramework
      {joint-iso-itu-t ds(5) module(1) informationFramework(1) 9} WITH SUCCESSORS

  caseExactIA5Match, commonName, ia5String
    FROM SelectedAttributeTypes
      {joint-iso-itu-t ds(5) module(1) selectedAttributeTypes(5) 9} WITH SUCCESSORS ;

-- Object identifiers

id-at-tacacsClient OBJECT IDENTIFIER ::= { 1 3 6 1 3 1 1 1 1 2 1 }
id-at-tacacsMember OBJECT IDENTIFIER ::= { 1 3 6 1 3 1 1 1 1 2 2 }
id-at-tacacsProfile OBJECT IDENTIFIER ::= { 1 3 6 1 3 1 1 1 1 2 3 }
id-at-tacacsFlag OBJECT IDENTIFIER ::= { 1 3 6 1 3 1 1 1 1 2 8 }
id-oc-tacacsAccount OBJECT IDENTIFIER ::= { 1 3 6 1 3 1 1 1 1 2 }

-- Attribute types

tacacsClient ATTRIBUTE ::= {
  WITH SYNTAX               IA5String(SIZE (1..20))
  EQUALITY MATCHING RULE    caseExactIA5Match
  LDAP-SYNTAX               ia5String.&id
  LDAP-NAME                 {"tacacsClient"}
  LDAP-DESC                 "Valid client address range for this user, in CIDR notation"
  ID                        id-at-tacacsClient }

tacacsMember ATTRIBUTE ::= {
  WITH SYNTAX               IA5String(SIZE (1..40))
  EQUALITY MATCHING RULE    caseExactIA5Match
  LDAP-SYNTAX               ia5String.&id
  LDAP-NAME                 {"tacacsMember"}
  LDAP-DESC                 "Tacacs group membership"
  ID                        id-at-tacacsMember }

tacacsProfile ATTRIBUTE ::= {
  WITH SYNTAX               IA5String(SIZE (1..1024))
  EQUALITY MATCHING RULE    caseExactIA5Match
  SINGLE VALUE              TRUE
  LDAP-SYNTAX               ia5String.&id
  LDAP-NAME                 {"tacacsProfile"}
  LDAP-DESC                 "Tacacs user profile"
  ID                        id-at-tacacsProfile }

tacacsFlag ATTRIBUTE ::= {
  WITH SYNTAX               IA5String(SIZE (1..40))
  EQUALITY MATCHING RULE    caseExactIA5Match
  LDAP-SYNTAX               ia5String.&id
  LDAP-NAME                 {"tacacsFlag"}
  LDAP-DESC                 "Arbitrary text, may be used by LDAP filters"
  ID                        id-at-tacacsFlag }

-- Object classes

tacacsAccount OBJECT-CLASS ::= {
  SUBCLASS OF               { top }
  KIND                      auxiliary
  MUST CONTAIN              { commonName }
  MAY CONTAIN               { tacacsClient
                              | tacacsMember
                              | tacacsProfile
                              | tacacsFlag }
  LDAP-NAME                 {"tacacsAccount"}
  LDAP-DESC                 "Tacacs user object"
  ID                        id-oc-tacacsAccount }
END
