-- Derived from data/ldap-schema/nextcloud.schema
-- Upstream: http://www.gnu.org/licenses/
-- This module is a container for LDAP schema. It has no module identifier.
-- X- extension fields from the LDAP schema are comments. USAGE userApplications and structural KIND are omitted because they are the defaults.
LdapNextcloud DEFINITIONS ::=
BEGIN

IMPORTS

  ATTRIBUTE, OBJECT-CLASS, top
    FROM InformationFramework
      {joint-iso-itu-t ds(5) module(1) informationFramework(1) 9} WITH SUCCESSORS

  caseIgnoreMatch, caseIgnoreSubstringsMatch, commonName, directoryString,
    UnboundedDirectoryString
    FROM SelectedAttributeTypes
      {joint-iso-itu-t ds(5) module(1) selectedAttributeTypes(5) 9} WITH SUCCESSORS ;

-- Object identifiers

id-at-nextcloudEnabled OBJECT IDENTIFIER ::= { 1 3 6 1 4 1 49213 1 1 1 }
id-at-nextcloudQuota OBJECT IDENTIFIER ::= { 1 3 6 1 4 1 49213 1 1 2 }
id-oc-nextcloudUser OBJECT IDENTIFIER ::= { 1 3 6 1 4 1 49213 1 2 1 }
id-oc-nextcloudGroup OBJECT IDENTIFIER ::= { 1 3 6 1 4 1 49213 1 2 2 }

-- Attribute types

nextcloudEnabled ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"nextcloudEnabled"}
  LDAP-DESC                 "whether user or group should be available in Nextcloud"
  ID                        id-at-nextcloudEnabled }

nextcloudQuota ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"nextcloudQuota"}
  LDAP-DESC                 "defines how much disk space is available for the user"
  ID                        id-at-nextcloudQuota }

-- Object classes

nextcloudUser OBJECT-CLASS ::= {
  SUBCLASS OF               { top }
  KIND                      auxiliary
  MUST CONTAIN              { commonName }
  MAY CONTAIN               { nextcloudEnabled
                              | nextcloudQuota }
  LDAP-NAME                 {"nextcloudUser"}
  LDAP-DESC                 "A Nextcloud user"
  ID                        id-oc-nextcloudUser }

nextcloudGroup OBJECT-CLASS ::= {
  SUBCLASS OF               { top }
  KIND                      auxiliary
  MUST CONTAIN              { commonName }
  MAY CONTAIN               { nextcloudEnabled }
  LDAP-NAME                 {"nextcloudGroup"}
  LDAP-DESC                 "A Nextcloud group"
  ID                        id-oc-nextcloudGroup }
END
