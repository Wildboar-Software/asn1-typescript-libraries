-- Derived from data/ldap-schema/glue/6-05-Benchmark.schema
-- Upstream: http://redmine.ogf.org/projects/glue-wg
-- This module is a container for LDAP schema. It has no module identifier.
-- X- extension fields from the LDAP schema are comments. USAGE userApplications and structural KIND are omitted because they are the defaults.
LdapGlue605Benchmark DEFINITIONS ::=
BEGIN

IMPORTS

  ATTRIBUTE, OBJECT-CLASS
    FROM InformationFramework
      {joint-iso-itu-t ds(5) module(1) informationFramework(1) 9} WITH SUCCESSORS

  caseExactMatch, caseExactSubstringsMatch, directoryString,
    UnboundedDirectoryString
    FROM SelectedAttributeTypes
      {joint-iso-itu-t ds(5) module(1) selectedAttributeTypes(5) 9} WITH SUCCESSORS

  gLUE2Entity
    FROM LdapGlue501Entity ;

-- Object identifiers

id-at-gLUE2BenchmarkID OBJECT IDENTIFIER ::= { 1 3 6 1 4 1 6757 100 1 1 21 1 }
id-at-gLUE2BenchmarkType OBJECT IDENTIFIER ::= { 1 3 6 1 4 1 6757 100 1 1 21 2 }
id-at-gLUE2BenchmarkValue OBJECT IDENTIFIER ::= { 1 3 6 1 4 1 6757 100 1 1 21 3 }
id-at-gLUE2BenchmarkExecutionEnvironmentForeignKey OBJECT IDENTIFIER ::= { 1 3 6 1 4 1 6757 100 1 1 21 4 }
id-at-gLUE2BenchmarkComputingManagerForeignKey OBJECT IDENTIFIER ::= { 1 3 6 1 4 1 6757 100 1 1 21 5 }
id-oc-gLUE2Benchmark OBJECT IDENTIFIER ::= { 1 3 6 1 4 1 6757 100 1 1 21 }

-- Attribute types

-- initial capital of "GLUE2BenchmarkID" lowercased so the assignment is a valuereference.
gLUE2BenchmarkID ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2BenchmarkID"}
  LDAP-DESC                 "Globally unique ID"
  ID                        id-at-gLUE2BenchmarkID }

-- initial capital of "GLUE2BenchmarkType" lowercased so the assignment is a valuereference.
gLUE2BenchmarkType ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2BenchmarkType"}
  LDAP-DESC                 "Type of benchmark"
  ID                        id-at-gLUE2BenchmarkType }

-- initial capital of "GLUE2BenchmarkValue" lowercased so the assignment is a valuereference.
gLUE2BenchmarkValue ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2BenchmarkValue"}
  LDAP-DESC                 "Value"
  ID                        id-at-gLUE2BenchmarkValue }

-- initial capital of "GLUE2BenchmarkExecutionEnvironmentForeignKey" lowercased so the assignment is a valuereference.
gLUE2BenchmarkExecutionEnvironmentForeignKey ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2BenchmarkExecutionEnvironmentForeignKey"}
  LDAP-DESC                 "ForeignKey"
  ID                        id-at-gLUE2BenchmarkExecutionEnvironmentForeignKey }

-- initial capital of "GLUE2BenchmarkComputingManagerForeignKey" lowercased so the assignment is a valuereference.
gLUE2BenchmarkComputingManagerForeignKey ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2BenchmarkComputingManagerForeignKey"}
  LDAP-DESC                 "ForeignKey"
  ID                        id-at-gLUE2BenchmarkComputingManagerForeignKey }

-- Object classes

-- initial capital of "GLUE2Benchmark" lowercased so the assignment is a valuereference.
gLUE2Benchmark OBJECT-CLASS ::= {
  SUBCLASS OF               { gLUE2Entity }
  MUST CONTAIN              { gLUE2BenchmarkID
                              | gLUE2BenchmarkType
                              | gLUE2BenchmarkValue }
  MAY CONTAIN               { gLUE2BenchmarkExecutionEnvironmentForeignKey
                              | gLUE2BenchmarkComputingManagerForeignKey }
  LDAP-NAME                 {"GLUE2Benchmark"}
  LDAP-DESC                 "Benchmark information about an entity providing computing capacity"
  ID                        id-oc-gLUE2Benchmark }
END
