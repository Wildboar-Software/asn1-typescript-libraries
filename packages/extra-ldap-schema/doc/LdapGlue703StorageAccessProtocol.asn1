-- Derived from data/ldap-schema/glue/7-03-StorageAccessProtocol.schema
-- Upstream: http://redmine.ogf.org/projects/glue-wg
-- This module is a container for LDAP schema. It has no module identifier.
-- X- extension fields from the LDAP schema are comments. USAGE userApplications and structural KIND are omitted because they are the defaults.
LdapGlue703StorageAccessProtocol DEFINITIONS ::=
BEGIN

IMPORTS

  ATTRIBUTE, OBJECT-CLASS
    FROM InformationFramework
      {joint-iso-itu-t ds(5) module(1) informationFramework(1) 9} WITH SUCCESSORS

  caseExactMatch, caseExactSubstringsMatch, directoryString, integer,
    integerMatch, integerOrderingMatch, UnboundedDirectoryString
    FROM SelectedAttributeTypes
      {joint-iso-itu-t ds(5) module(1) selectedAttributeTypes(5) 9} WITH SUCCESSORS

  gLUE2Entity
    FROM LdapGlue501Entity ;

-- Object identifiers

id-at-gLUE2StorageAccessProtocolID OBJECT IDENTIFIER ::= { 1 3 6 1 4 1 6757 100 1 1 29 1 }
id-at-gLUE2StorageAccessProtocolType OBJECT IDENTIFIER ::= { 1 3 6 1 4 1 6757 100 1 1 29 2 }
id-at-gLUE2StorageAccessProtocolVersion OBJECT IDENTIFIER ::= { 1 3 6 1 4 1 6757 100 1 1 29 3 }
id-at-gLUE2StorageAccessProtocolMaxStreams OBJECT IDENTIFIER ::= { 1 3 6 1 4 1 6757 100 1 1 29 4 }
id-at-gLUE2StorageAccessProtocolStorageServiceForeignKey OBJECT IDENTIFIER ::= { 1 3 6 1 4 1 6757 100 1 1 29 5 }
id-oc-gLUE2StorageAccessProtocol OBJECT IDENTIFIER ::= { 1 3 6 1 4 1 6757 100 1 1 29 }

-- Attribute types

-- initial capital of "GLUE2StorageAccessProtocolID" lowercased so the assignment is a valuereference.
gLUE2StorageAccessProtocolID ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2StorageAccessProtocolID"}
  LDAP-DESC                 "Globally unique ID"
  ID                        id-at-gLUE2StorageAccessProtocolID }

-- initial capital of "GLUE2StorageAccessProtocolType" lowercased so the assignment is a valuereference.
gLUE2StorageAccessProtocolType ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2StorageAccessProtocolType"}
  LDAP-DESC                 "The name of the protocol"
  ID                        id-at-gLUE2StorageAccessProtocolType }

-- initial capital of "GLUE2StorageAccessProtocolVersion" lowercased so the assignment is a valuereference.
gLUE2StorageAccessProtocolVersion ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2StorageAccessProtocolVersion"}
  LDAP-DESC                 "The version of the protocol"
  ID                        id-at-gLUE2StorageAccessProtocolVersion }

-- initial capital of "GLUE2StorageAccessProtocolMaxStreams" lowercased so the assignment is a valuereference.
gLUE2StorageAccessProtocolMaxStreams ATTRIBUTE ::= {
  WITH SYNTAX               INTEGER
  EQUALITY MATCHING RULE    integerMatch
  ORDERING MATCHING RULE    integerOrderingMatch
  SINGLE VALUE              TRUE
  LDAP-SYNTAX               integer.&id
  LDAP-NAME                 {"GLUE2StorageAccessProtocolMaxStreams"}
  LDAP-DESC                 "The number of parallel streams this protocol supports"
  ID                        id-at-gLUE2StorageAccessProtocolMaxStreams }

-- initial capital of "GLUE2StorageAccessProtocolStorageServiceForeignKey" lowercased so the assignment is a valuereference.
gLUE2StorageAccessProtocolStorageServiceForeignKey ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2StorageAccessProtocolStorageServiceForeignKey"}
  LDAP-DESC                 "ForeignKey"
  ID                        id-at-gLUE2StorageAccessProtocolStorageServiceForeignKey }

-- Object classes

-- initial capital of "GLUE2StorageAccessProtocol" lowercased so the assignment is a valuereference.
gLUE2StorageAccessProtocol OBJECT-CLASS ::= {
  SUBCLASS OF               { gLUE2Entity }
  MUST CONTAIN              { gLUE2StorageAccessProtocolID
                              | gLUE2StorageAccessProtocolType
                              | gLUE2StorageAccessProtocolVersion
                              | gLUE2StorageAccessProtocolStorageServiceForeignKey }
  MAY CONTAIN               { gLUE2StorageAccessProtocolMaxStreams }
  LDAP-NAME                 {"GLUE2StorageAccessProtocol"}
  LDAP-DESC                 "A type of protocol available to access the available storage capacities"
  ID                        id-oc-gLUE2StorageAccessProtocol }
END
