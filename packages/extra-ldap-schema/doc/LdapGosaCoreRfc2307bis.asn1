-- Derived from data/ldap-schema/gosa-core/rfc2307bis.schema
-- This module is a container for LDAP schema. It has no module identifier.
-- X- extension fields from the LDAP schema are comments. USAGE userApplications and structural KIND are omitted because they are the defaults.
-- 45 elements were omitted because their OIDs are already defined. See CONVERSION-REPORT.txt.
LdapGosaCoreRfc2307bis DEFINITIONS ::=
BEGIN

IMPORTS

  ATTRIBUTE, OBJECT-CLASS, top
    FROM InformationFramework
      {joint-iso-itu-t ds(5) module(1) informationFramework(1) 9} WITH SUCCESSORS

  caseExactIA5Match, commonName, description, ia5String
    FROM SelectedAttributeTypes
      {joint-iso-itu-t ds(5) module(1) selectedAttributeTypes(5) 9} WITH SUCCESSORS

  caseExactIA5SubstringsMatch
    FROM OpenLDAP
      {iso(1) identified-organization(3) dod(6) internet(1) private(4) enterprise(1) wildboar(56490) module(1) openldap(28)} WITH SUCCESSORS

  automountKey, automountMapName
    FROM RFC2307bis
      {iso(1) identified-organization(3) dod(6) internet(1) private(4) enterprise(1) wildboar(56490) module(1) rfc2307-bis(44)} WITH SUCCESSORS ;

-- Object identifiers

id-at-automountInformation OBJECT IDENTIFIER ::= { 1 3 6 1 1 1 1 33 }
id-oc-automountMap OBJECT IDENTIFIER ::= { 1 3 6 1 1 1 2 16 }
id-oc-automount OBJECT IDENTIFIER ::= { 1 3 6 1 1 1 2 17 }
id-oc-namedObject OBJECT IDENTIFIER ::= { 1 3 6 1 4 1 5322 13 1 1 }

-- Attribute types

automountInformation ATTRIBUTE ::= {
  WITH SYNTAX               IA5String
  EQUALITY MATCHING RULE    caseExactIA5Match
  SUBSTRINGS MATCHING RULE  caseExactIA5SubstringsMatch
  SINGLE VALUE              TRUE
  LDAP-SYNTAX               ia5String.&id
  LDAP-NAME                 {"automountInformation"}
  LDAP-DESC                 "Automount information"
  ID                        id-at-automountInformation }

-- Object classes

automountMap OBJECT-CLASS ::= {
  SUBCLASS OF               { top }
  MUST CONTAIN              { automountMapName }
  MAY CONTAIN               { description }
  LDAP-NAME                 {"automountMap"}
  ID                        id-oc-automountMap }

automount OBJECT-CLASS ::= {
  SUBCLASS OF               { top }
  MUST CONTAIN              { automountKey
                              | automountInformation }
  MAY CONTAIN               { description }
  LDAP-NAME                 {"automount"}
  LDAP-DESC                 "Automount information"
  ID                        id-oc-automount }

namedObject OBJECT-CLASS ::= {
  SUBCLASS OF               { top }
  MAY CONTAIN               { commonName }
  LDAP-NAME                 {"namedObject"}
  ID                        id-oc-namedObject }
END
