-- Derived from data/ldap-schema/kitneduperson.schema
-- Upstream: https://github.com/Internet2/grouper/blob/b00c9899258bd26ccc30f5651772445115ce1fa8/grouper/misc/ldap/kitneduperson.schema
-- This module is a container for LDAP schema. It has no module identifier.
-- X- extension fields from the LDAP schema are comments. USAGE userApplications and structural KIND are omitted because they are the defaults.
LdapKitneduperson DEFINITIONS ::=
BEGIN

IMPORTS

  ATTRIBUTE, OBJECT-CLASS, top
    FROM InformationFramework
      {joint-iso-itu-t ds(5) module(1) informationFramework(1) 9} WITH SUCCESSORS

  caseIgnoreMatch, directoryString, UnboundedDirectoryString
    FROM SelectedAttributeTypes
      {joint-iso-itu-t ds(5) module(1) selectedAttributeTypes(5) 9} WITH SUCCESSORS ;

-- Object identifiers

id-at-kitnEduPersonRegId OBJECT IDENTIFIER ::= { 1 3 6 4 1 9902 99999 1 1 1 }
id-oc-kitnEduPerson OBJECT IDENTIFIER ::= { 1 3 6 4 1 9902 99999 1 1 }

-- Attribute types

-- OID 1.3.6.4.1.9902.99999.1.1.1 contains an all-nines arc (99999). Kept as published.
kitnEduPersonRegId ATTRIBUTE ::= {
  WITH SYNTAX               UnboundedDirectoryString
  EQUALITY MATCHING RULE    caseIgnoreMatch
  LDAP-SYNTAX               directoryString.&id
  LDAP-NAME                 {"kitnEduPersonRegId"}
  LDAP-DESC                 "registry id of the person"
  ID                        id-at-kitnEduPersonRegId }

-- Object classes

-- OID 1.3.6.4.1.9902.99999.1.1 contains an all-nines arc (99999). Kept as published.
kitnEduPerson OBJECT-CLASS ::= {
  SUBCLASS OF               { top }
  KIND                      auxiliary
  MAY CONTAIN               { kitnEduPersonRegId }
  LDAP-NAME                 {"kitnEduPerson"}
  LDAP-DESC                 "KITN Edu Person objectclass"
  ID                        id-oc-kitnEduPerson }
END
