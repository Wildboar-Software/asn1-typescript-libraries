-- Derived from data/ldap-schema/glue/5-03-Location.schema
-- Upstream: http://redmine.ogf.org/projects/glue-wg
-- This module is a container for LDAP schema. It has no module identifier.
-- X- extension fields from the LDAP schema are comments. USAGE userApplications and structural KIND are omitted because they are the defaults.
LdapGlue503Location DEFINITIONS ::=
BEGIN

IMPORTS

  ATTRIBUTE, OBJECT-CLASS
    FROM InformationFramework
      {joint-iso-itu-t ds(5) module(1) informationFramework(1) 9} WITH SUCCESSORS

  caseExactMatch, caseExactSubstringsMatch, directoryString,
    UnboundedDirectoryString
    FROM SelectedAttributeTypes
      {joint-iso-itu-t ds(5) module(1) selectedAttributeTypes(5) 9} WITH SUCCESSORS

  gLUE2Entity
    FROM LdapGlue501Entity ;

-- Object identifiers

id-at-gLUE2LocationID OBJECT IDENTIFIER ::= { 1 3 6 1 4 1 6757 100 1 1 3 1 }
id-at-gLUE2LocationAddress OBJECT IDENTIFIER ::= { 1 3 6 1 4 1 6757 100 1 1 3 2 }
id-at-gLUE2LocationPlace OBJECT IDENTIFIER ::= { 1 3 6 1 4 1 6757 100 1 1 3 3 }
id-at-gLUE2LocationCountry OBJECT IDENTIFIER ::= { 1 3 6 1 4 1 6757 100 1 1 3 4 }
id-at-gLUE2LocationPostCode OBJECT IDENTIFIER ::= { 1 3 6 1 4 1 6757 100 1 1 3 5 }
id-at-gLUE2LocationLatitude OBJECT IDENTIFIER ::= { 1 3 6 1 4 1 6757 100 1 1 3 6 }
id-at-gLUE2LocationLongitude OBJECT IDENTIFIER ::= { 1 3 6 1 4 1 6757 100 1 1 3 7 }
id-at-gLUE2LocationServiceForeignKey OBJECT IDENTIFIER ::= { 1 3 6 1 4 1 6757 100 1 1 3 8 }
id-at-gLUE2LocationDomainForeignKey OBJECT IDENTIFIER ::= { 1 3 6 1 4 1 6757 100 1 1 3 9 }
id-oc-gLUE2Location OBJECT IDENTIFIER ::= { 1 3 6 1 4 1 6757 100 1 1 3 }

-- Attribute types

-- initial capital of "GLUE2LocationID" lowercased so the assignment is a valuereference.
gLUE2LocationID ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2LocationID"}
  LDAP-DESC                 "Globally unique ID"
  ID                        id-at-gLUE2LocationID }

-- initial capital of "GLUE2LocationAddress" lowercased so the assignment is a valuereference.
gLUE2LocationAddress ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2LocationAddress"}
  LDAP-DESC                 "Street address"
  ID                        id-at-gLUE2LocationAddress }

-- initial capital of "GLUE2LocationPlace" lowercased so the assignment is a valuereference.
gLUE2LocationPlace ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2LocationPlace"}
  LDAP-DESC                 "Name of town/city"
  ID                        id-at-gLUE2LocationPlace }

-- initial capital of "GLUE2LocationCountry" lowercased so the assignment is a valuereference.
gLUE2LocationCountry ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2LocationCountry"}
  LDAP-DESC                 "Country name"
  ID                        id-at-gLUE2LocationCountry }

-- initial capital of "GLUE2LocationPostCode" lowercased so the assignment is a valuereference.
gLUE2LocationPostCode ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2LocationPostCode"}
  LDAP-DESC                 "Postal code"
  ID                        id-at-gLUE2LocationPostCode }

-- initial capital of "GLUE2LocationLatitude" lowercased so the assignment is a valuereference.
gLUE2LocationLatitude ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2LocationLatitude"}
  LDAP-DESC                 "The position of a place north or south of the equator measured from -90 degrees to +90 degrees with positive values going north and negative values going south"
  ID                        id-at-gLUE2LocationLatitude }

-- initial capital of "GLUE2LocationLongitude" lowercased so the assignment is a valuereference.
gLUE2LocationLongitude ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2LocationLongitude"}
  LDAP-DESC                 "The position of a place east or west of Greenwich, England measured from -180 degrees to +180 degrees with positive values going east and negative values going west"
  ID                        id-at-gLUE2LocationLongitude }

-- initial capital of "GLUE2LocationServiceForeignKey" lowercased so the assignment is a valuereference.
gLUE2LocationServiceForeignKey ATTRIBUTE ::= {
  WITH SYNTAX               UnboundedDirectoryString
  EQUALITY MATCHING RULE    caseExactMatch
  SUBSTRINGS MATCHING RULE  caseExactSubstringsMatch
  LDAP-SYNTAX               directoryString.&id
  LDAP-NAME                 {"GLUE2LocationServiceForeignKey"}
  LDAP-DESC                 "ForeignKey"
  ID                        id-at-gLUE2LocationServiceForeignKey }

-- initial capital of "GLUE2LocationDomainForeignKey" lowercased so the assignment is a valuereference.
gLUE2LocationDomainForeignKey ATTRIBUTE ::= {
  WITH SYNTAX               UnboundedDirectoryString
  EQUALITY MATCHING RULE    caseExactMatch
  SUBSTRINGS MATCHING RULE  caseExactSubstringsMatch
  LDAP-SYNTAX               directoryString.&id
  LDAP-NAME                 {"GLUE2LocationDomainForeignKey"}
  LDAP-DESC                 "ForeignKey"
  ID                        id-at-gLUE2LocationDomainForeignKey }

-- Object classes

-- initial capital of "GLUE2Location" lowercased so the assignment is a valuereference.
gLUE2Location OBJECT-CLASS ::= {
  SUBCLASS OF               { gLUE2Entity }
  MUST CONTAIN              { gLUE2LocationID }
  MAY CONTAIN               { gLUE2LocationAddress
                              | gLUE2LocationPlace
                              | gLUE2LocationCountry
                              | gLUE2LocationPostCode
                              | gLUE2LocationLatitude
                              | gLUE2LocationLongitude
                              | gLUE2LocationServiceForeignKey
                              | gLUE2LocationDomainForeignKey }
  LDAP-NAME                 {"GLUE2Location"}
  LDAP-DESC                 "A geographical position"
  ID                        id-oc-gLUE2Location }
END
