-- Derived from data/ldap-schema/dna-plugin.ldif
-- This module is a container for LDAP schema. It has no module identifier.
-- X- extension fields from the LDAP schema are comments. USAGE userApplications and structural KIND are omitted because they are the defaults.
LdapDnaPlugin DEFINITIONS ::=
BEGIN

IMPORTS

  ATTRIBUTE, DistinguishedName, OBJECT-CLASS, top
    FROM InformationFramework
      {joint-iso-itu-t ds(5) module(1) informationFramework(1) 9} WITH SUCCESSORS

  commonName, directoryString, dn, integer, UnboundedDirectoryString
    FROM SelectedAttributeTypes
      {joint-iso-itu-t ds(5) module(1) selectedAttributeTypes(5) 9} WITH SUCCESSORS ;

-- Object identifiers

id-at-dnaType OBJECT IDENTIFIER ::= { 2 16 840 1 113730 3 1 2115 }
id-at-dnaPrefix OBJECT IDENTIFIER ::= { 2 16 840 1 113730 3 1 2116 }
id-at-dnaNextValue OBJECT IDENTIFIER ::= { 2 16 840 1 113730 3 1 2117 }
id-at-dnaInterval OBJECT IDENTIFIER ::= { 2 16 840 1 113730 3 1 2118 }
id-at-dnaMagicRegen OBJECT IDENTIFIER ::= { 2 16 840 1 113730 3 1 2119 }
id-at-dnaFilter OBJECT IDENTIFIER ::= { 2 16 840 1 113730 3 1 2120 }
id-at-dnaScope OBJECT IDENTIFIER ::= { 2 16 840 1 113730 3 1 2121 }
id-at-dnaMaxValue OBJECT IDENTIFIER ::= { 2 16 840 1 113730 3 1 2122 }
id-at-dnaSharedCfgDN OBJECT IDENTIFIER ::= { 2 16 840 1 113730 3 1 2123 }
id-at-dnaRemainingValues OBJECT IDENTIFIER ::= { 2 16 840 1 113730 3 1 2124 }
id-at-dnaThreshold OBJECT IDENTIFIER ::= { 2 16 840 1 113730 3 1 2125 }
id-at-dnaHostname OBJECT IDENTIFIER ::= { 2 16 840 1 113730 3 1 2126 }
id-at-dnaPortNum OBJECT IDENTIFIER ::= { 2 16 840 1 113730 3 1 2127 }
id-at-dnaSecurePortNum OBJECT IDENTIFIER ::= { 2 16 840 1 113730 3 1 2128 }
id-at-dnaNextRange OBJECT IDENTIFIER ::= { 2 16 840 1 113730 3 1 2129 }
id-at-dnaRangeRequestTimeout OBJECT IDENTIFIER ::= { 2 16 840 1 113730 3 1 2130 }
id-at-dnaRemoteBindCred OBJECT IDENTIFIER ::= { 2 16 840 1 113730 3 1 2157 }
id-at-dnaRemoteBindDN OBJECT IDENTIFIER ::= { 2 16 840 1 113730 3 1 2158 }
id-at-dnaRemoteConnProtocol OBJECT IDENTIFIER ::= { 2 16 840 1 113730 3 1 2159 }
id-at-dnaRemoteBindMethod OBJECT IDENTIFIER ::= { 2 16 840 1 113730 3 1 2160 }
id-at-dnaExcludeScope OBJECT IDENTIFIER ::= { 2 16 840 1 113730 3 1 2312 }
id-oc-dnaPluginConfig OBJECT IDENTIFIER ::= { 2 16 840 1 113730 3 2 324 }
id-oc-dnaSharedConfig OBJECT IDENTIFIER ::= { 2 16 840 1 113730 3 2 325 }

-- Attribute types

-- X-ORIGIN: "389 Directory Server"
dnaType ATTRIBUTE ::= {
  WITH SYNTAX               UnboundedDirectoryString
  LDAP-SYNTAX               directoryString.&id
  LDAP-NAME                 {"dnaType"}
  LDAP-DESC                 "DNA attribute type to maintain"
  ID                        id-at-dnaType }

-- X-ORIGIN: "389 Directory Server"
dnaPrefix ATTRIBUTE ::= {
  WITH SYNTAX               UnboundedDirectoryString
  SINGLE VALUE              TRUE
  LDAP-SYNTAX               directoryString.&id
  LDAP-NAME                 {"dnaPrefix"}
  LDAP-DESC                 "DNA string prefix for dna value"
  ID                        id-at-dnaPrefix }

-- X-ORIGIN: "389 Directory Server"
dnaNextValue ATTRIBUTE ::= {
  WITH SYNTAX               INTEGER
  SINGLE VALUE              TRUE
  LDAP-SYNTAX               integer.&id
  LDAP-NAME                 {"dnaNextValue"}
  LDAP-DESC                 "DNA next available value for assignment"
  ID                        id-at-dnaNextValue }

-- X-ORIGIN: "389 Directory Server"
dnaInterval ATTRIBUTE ::= {
  WITH SYNTAX               INTEGER
  SINGLE VALUE              TRUE
  LDAP-SYNTAX               integer.&id
  LDAP-NAME                 {"dnaInterval"}
  LDAP-DESC                 "DNA interval between values"
  ID                        id-at-dnaInterval }

-- X-ORIGIN: "389 Directory Server"
dnaMagicRegen ATTRIBUTE ::= {
  WITH SYNTAX               UnboundedDirectoryString
  SINGLE VALUE              TRUE
  LDAP-SYNTAX               directoryString.&id
  LDAP-NAME                 {"dnaMagicRegen"}
  LDAP-DESC                 "DNA value that will trigger regeneration of attribute value"
  ID                        id-at-dnaMagicRegen }

-- X-ORIGIN: "389 Directory Server"
dnaFilter ATTRIBUTE ::= {
  WITH SYNTAX               UnboundedDirectoryString
  SINGLE VALUE              TRUE
  LDAP-SYNTAX               directoryString.&id
  LDAP-NAME                 {"dnaFilter"}
  LDAP-DESC                 "DNA filter for finding entries"
  ID                        id-at-dnaFilter }

-- X-ORIGIN: "389 Directory Server"
dnaScope ATTRIBUTE ::= {
  WITH SYNTAX               DistinguishedName
  SINGLE VALUE              TRUE
  LDAP-SYNTAX               dn.&id
  LDAP-NAME                 {"dnaScope"}
  LDAP-DESC                 "DNA base DN for finding entries"
  ID                        id-at-dnaScope }

-- X-ORIGIN: "389 Directory Server"
dnaMaxValue ATTRIBUTE ::= {
  WITH SYNTAX               INTEGER
  SINGLE VALUE              TRUE
  LDAP-SYNTAX               integer.&id
  LDAP-NAME                 {"dnaMaxValue"}
  LDAP-DESC                 "DNA maximum value to assign"
  ID                        id-at-dnaMaxValue }

-- X-ORIGIN: "389 Directory Server"
dnaSharedCfgDN ATTRIBUTE ::= {
  WITH SYNTAX               DistinguishedName
  SINGLE VALUE              TRUE
  LDAP-SYNTAX               dn.&id
  LDAP-NAME                 {"dnaSharedCfgDN"}
  LDAP-DESC                 "DNA shared configuration entry DN"
  ID                        id-at-dnaSharedCfgDN }

-- X-ORIGIN: "389 Directory Server"
dnaRemainingValues ATTRIBUTE ::= {
  WITH SYNTAX               INTEGER
  SINGLE VALUE              TRUE
  LDAP-SYNTAX               integer.&id
  LDAP-NAME                 {"dnaRemainingValues"}
  LDAP-DESC                 "DNA remaining values left to assign"
  ID                        id-at-dnaRemainingValues }

-- X-ORIGIN: "389 Directory Server"
dnaThreshold ATTRIBUTE ::= {
  WITH SYNTAX               INTEGER
  SINGLE VALUE              TRUE
  LDAP-SYNTAX               integer.&id
  LDAP-NAME                 {"dnaThreshold"}
  LDAP-DESC                 "DNA threshold for getting next range of values"
  ID                        id-at-dnaThreshold }

-- X-ORIGIN: "389 Directory Server"
dnaHostname ATTRIBUTE ::= {
  WITH SYNTAX               UnboundedDirectoryString
  SINGLE VALUE              TRUE
  LDAP-SYNTAX               directoryString.&id
  LDAP-NAME                 {"dnaHostname"}
  LDAP-DESC                 "DNA hostname of replica to get new range of values"
  ID                        id-at-dnaHostname }

-- X-ORIGIN: "389 Directory Server"
dnaPortNum ATTRIBUTE ::= {
  WITH SYNTAX               INTEGER
  SINGLE VALUE              TRUE
  LDAP-SYNTAX               integer.&id
  LDAP-NAME                 {"dnaPortNum"}
  LDAP-DESC                 "DNA port number of replica to get new range of values"
  ID                        id-at-dnaPortNum }

-- X-ORIGIN: "389 Directory Server"
dnaSecurePortNum ATTRIBUTE ::= {
  WITH SYNTAX               INTEGER
  SINGLE VALUE              TRUE
  LDAP-SYNTAX               integer.&id
  LDAP-NAME                 {"dnaSecurePortNum"}
  LDAP-DESC                 "DNA secure port number of replica to get new range of values"
  ID                        id-at-dnaSecurePortNum }

-- X-ORIGIN: "389 Directory Server"
dnaNextRange ATTRIBUTE ::= {
  WITH SYNTAX               UnboundedDirectoryString
  SINGLE VALUE              TRUE
  LDAP-SYNTAX               directoryString.&id
  LDAP-NAME                 {"dnaNextRange"}
  LDAP-DESC                 "DNA range of values to get from replica"
  ID                        id-at-dnaNextRange }

-- X-ORIGIN: "389 Directory Server"
dnaRangeRequestTimeout ATTRIBUTE ::= {
  WITH SYNTAX               INTEGER
  SINGLE VALUE              TRUE
  LDAP-SYNTAX               integer.&id
  LDAP-NAME                 {"dnaRangeRequestTimeout"}
  LDAP-DESC                 "DNA timeout for querying replica for next range of values"
  ID                        id-at-dnaRangeRequestTimeout }

-- X-ORIGIN: "389 Directory Server"
dnaRemoteBindCred ATTRIBUTE ::= {
  WITH SYNTAX               UnboundedDirectoryString
  SINGLE VALUE              TRUE
  LDAP-SYNTAX               directoryString.&id
  LDAP-NAME                 {"dnaRemoteBindCred"}
  LDAP-DESC                 "Remote bind credentials"
  ID                        id-at-dnaRemoteBindCred }

-- X-ORIGIN: "389 Directory Server"
dnaRemoteBindDN ATTRIBUTE ::= {
  WITH SYNTAX               DistinguishedName
  SINGLE VALUE              TRUE
  LDAP-SYNTAX               dn.&id
  LDAP-NAME                 {"dnaRemoteBindDN"}
  LDAP-DESC                 "Remote bind DN"
  ID                        id-at-dnaRemoteBindDN }

-- X-ORIGIN: "389 Directory Server"
dnaRemoteConnProtocol ATTRIBUTE ::= {
  WITH SYNTAX               UnboundedDirectoryString
  SINGLE VALUE              TRUE
  LDAP-SYNTAX               directoryString.&id
  LDAP-NAME                 {"dnaRemoteConnProtocol"}
  LDAP-DESC                 "Connection protocol: LDAP, TLS, or SSL"
  ID                        id-at-dnaRemoteConnProtocol }

-- X-ORIGIN: "389 Directory Server"
dnaRemoteBindMethod ATTRIBUTE ::= {
  WITH SYNTAX               UnboundedDirectoryString
  SINGLE VALUE              TRUE
  LDAP-SYNTAX               directoryString.&id
  LDAP-NAME                 {"dnaRemoteBindMethod"}
  LDAP-DESC                 "Remote bind method: SIMPLE, SSL, SASL/DIGEST-MD5, or SASL/GSSAPI"
  ID                        id-at-dnaRemoteBindMethod }

-- X-ORIGIN: "389 Directory Server"
dnaExcludeScope ATTRIBUTE ::= {
  WITH SYNTAX               DistinguishedName
  LDAP-SYNTAX               dn.&id
  LDAP-NAME                 {"dnaExcludeScope"}
  LDAP-DESC                 "DN of a subtree excluded from DNA plugin scope"
  ID                        id-at-dnaExcludeScope }

-- Object classes

-- X-ORIGIN: "389 Directory Server"
dnaPluginConfig OBJECT-CLASS ::= {
  SUBCLASS OF               { top }
  KIND                      auxiliary
  MAY CONTAIN               { dnaType
                              | dnaPrefix
                              | dnaNextValue
                              | dnaMaxValue
                              | dnaInterval
                              | dnaMagicRegen
                              | dnaFilter
                              | dnaScope
                              | dnaExcludeScope
                              | dnaSharedCfgDN
                              | dnaThreshold
                              | dnaNextRange
                              | dnaRangeRequestTimeout
                              | dnaRemoteBindDN
                              | dnaRemoteBindCred
                              | commonName }
  LDAP-NAME                 {"dnaPluginConfig"}
  LDAP-DESC                 "DNA plugin configuration"
  ID                        id-oc-dnaPluginConfig }

-- X-ORIGIN: "389 Directory Server"
dnaSharedConfig OBJECT-CLASS ::= {
  SUBCLASS OF               { top }
  KIND                      auxiliary
  MAY CONTAIN               { dnaHostname
                              | dnaPortNum
                              | dnaSecurePortNum
                              | dnaRemoteBindMethod
                              | dnaRemoteConnProtocol
                              | dnaRemainingValues }
  LDAP-NAME                 {"dnaSharedConfig"}
  LDAP-DESC                 "DNA Shared Configuration"
  ID                        id-oc-dnaSharedConfig }
END
