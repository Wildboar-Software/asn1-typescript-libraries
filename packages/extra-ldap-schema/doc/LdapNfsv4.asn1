-- Derived from data/ldap-schema/nfsv4.ldif
-- Upstream: http://www.citi.umich.edu/projects/nfsv4/ldap/
-- This module is a container for LDAP schema. It has no module identifier.
-- X- extension fields from the LDAP schema are comments. USAGE userApplications and structural KIND are omitted because they are the defaults.
LdapNfsv4 DEFINITIONS ::=
BEGIN

IMPORTS

  ATTRIBUTE, OBJECT-CLASS, top
    FROM InformationFramework
      {joint-iso-itu-t ds(5) module(1) informationFramework(1) 9} WITH SUCCESSORS

  caseIgnoreIA5Match, commonName, description, ia5String
    FROM SelectedAttributeTypes
      {joint-iso-itu-t ds(5) module(1) selectedAttributeTypes(5) 9} WITH SUCCESSORS

  gidNumber, memberUid, uidNumber
    FROM NIS
      {iso(1) identified-organization(3) dod(6) internet(1) private(4) enterprise(1) wildboar(56490) module(1) nis(7)} WITH SUCCESSORS ;

-- Object identifiers

id-at-nFSv4Name OBJECT IDENTIFIER ::= { 1 3 6 1 4 1 250 1 61 }
id-at-gSSAuthName OBJECT IDENTIFIER ::= { 1 3 6 1 4 1 250 1 62 }
id-oc-nFSv4RemotePerson OBJECT IDENTIFIER ::= { 1 3 6 1 4 1 250 1 64 }
id-oc-nFSv4RemoteGroup OBJECT IDENTIFIER ::= { 1 3 6 1 4 1 250 1 63 }

-- Attribute types

-- initial capital of "NFSv4Name" lowercased so the assignment is a valuereference.
nFSv4Name ATTRIBUTE ::= {
  WITH SYNTAX               IA5String
  EQUALITY MATCHING RULE    caseIgnoreIA5Match
  SINGLE VALUE              TRUE
  LDAP-SYNTAX               ia5String.&id
  LDAP-NAME                 {"NFSv4Name"}
  LDAP-DESC                 "NFS version 4 Name"
  ID                        id-at-nFSv4Name }

-- initial capital of "GSSAuthName" lowercased so the assignment is a valuereference.
gSSAuthName ATTRIBUTE ::= {
  WITH SYNTAX               IA5String
  EQUALITY MATCHING RULE    caseIgnoreIA5Match
  LDAP-SYNTAX               ia5String.&id
  LDAP-NAME                 {"GSSAuthName"}
  LDAP-DESC                 "RPCSEC GSS authenticated user name"
  ID                        id-at-gSSAuthName }

-- Object classes

-- initial capital of "NFSv4RemotePerson" lowercased so the assignment is a valuereference.
nFSv4RemotePerson OBJECT-CLASS ::= {
  SUBCLASS OF               { top }
  MUST CONTAIN              { uidNumber
                              | gidNumber
                              | nFSv4Name }
  MAY CONTAIN               { commonName
                              | gSSAuthName
                              | description }
  LDAP-NAME                 {"NFSv4RemotePerson"}
  LDAP-DESC                 "NFS version4 person from remote NFSv4 Domain"
  ID                        id-oc-nFSv4RemotePerson }

-- initial capital of "NFSv4RemoteGroup" lowercased so the assignment is a valuereference.
nFSv4RemoteGroup OBJECT-CLASS ::= {
  SUBCLASS OF               { top }
  MUST CONTAIN              { gidNumber
                              | nFSv4Name }
  MAY CONTAIN               { commonName
                              | memberUid
                              | description }
  LDAP-NAME                 {"NFSv4RemoteGroup"}
  LDAP-DESC                 "NFS version4 group from remote NFSv4 Domain"
  ID                        id-oc-nFSv4RemoteGroup }
END
