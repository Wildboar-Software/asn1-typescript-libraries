-- Derived from data/ldap-schema/glue/5-04-Contact.schema
-- Upstream: http://redmine.ogf.org/projects/glue-wg
-- This module is a container for LDAP schema. It has no module identifier.
-- X- extension fields from the LDAP schema are comments. USAGE userApplications and structural KIND are omitted because they are the defaults.
LdapGlue504Contact DEFINITIONS ::=
BEGIN

IMPORTS

  ATTRIBUTE, OBJECT-CLASS
    FROM InformationFramework
      {joint-iso-itu-t ds(5) module(1) informationFramework(1) 9} WITH SUCCESSORS

  caseExactMatch, caseExactSubstringsMatch, directoryString,
    UnboundedDirectoryString
    FROM SelectedAttributeTypes
      {joint-iso-itu-t ds(5) module(1) selectedAttributeTypes(5) 9} WITH SUCCESSORS

  gLUE2Entity
    FROM LdapGlue501Entity ;

-- Object identifiers

id-at-gLUE2ContactID OBJECT IDENTIFIER ::= { 1 3 6 1 4 1 6757 100 1 1 4 1 }
id-at-gLUE2ContactDetail OBJECT IDENTIFIER ::= { 1 3 6 1 4 1 6757 100 1 1 4 2 }
id-at-gLUE2ContactType OBJECT IDENTIFIER ::= { 1 3 6 1 4 1 6757 100 1 1 4 3 }
id-at-gLUE2ContactServiceForeignKey OBJECT IDENTIFIER ::= { 1 3 6 1 4 1 6757 100 1 1 4 4 }
id-at-gLUE2ContactDomainForeignKey OBJECT IDENTIFIER ::= { 1 3 6 1 4 1 6757 100 1 1 4 5 }
id-oc-gLUE2Contact OBJECT IDENTIFIER ::= { 1 3 6 1 4 1 6757 100 1 1 4 }

-- Attribute types

-- initial capital of "GLUE2ContactID" lowercased so the assignment is a valuereference.
gLUE2ContactID ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2ContactID"}
  LDAP-DESC                 "Globally unique ID"
  ID                        id-at-gLUE2ContactID }

-- initial capital of "GLUE2ContactDetail" lowercased so the assignment is a valuereference.
gLUE2ContactDetail ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2ContactDetail"}
  LDAP-DESC                 "URL embedding the contact information. The syntax of URI depends on the communication channel"
  ID                        id-at-gLUE2ContactDetail }

-- initial capital of "GLUE2ContactType" lowercased so the assignment is a valuereference.
gLUE2ContactType ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2ContactType"}
  LDAP-DESC                 "Type of contact"
  ID                        id-at-gLUE2ContactType }

-- initial capital of "GLUE2ContactServiceForeignKey" lowercased so the assignment is a valuereference.
gLUE2ContactServiceForeignKey ATTRIBUTE ::= {
  WITH SYNTAX               UnboundedDirectoryString
  EQUALITY MATCHING RULE    caseExactMatch
  SUBSTRINGS MATCHING RULE  caseExactSubstringsMatch
  LDAP-SYNTAX               directoryString.&id
  LDAP-NAME                 {"GLUE2ContactServiceForeignKey"}
  LDAP-DESC                 "ForeignKey"
  ID                        id-at-gLUE2ContactServiceForeignKey }

-- initial capital of "GLUE2ContactDomainForeignKey" lowercased so the assignment is a valuereference.
gLUE2ContactDomainForeignKey ATTRIBUTE ::= {
  WITH SYNTAX               UnboundedDirectoryString
  EQUALITY MATCHING RULE    caseExactMatch
  SUBSTRINGS MATCHING RULE  caseExactSubstringsMatch
  LDAP-SYNTAX               directoryString.&id
  LDAP-NAME                 {"GLUE2ContactDomainForeignKey"}
  LDAP-DESC                 "ForeignKey"
  ID                        id-at-gLUE2ContactDomainForeignKey }

-- Object classes

-- initial capital of "GLUE2Contact" lowercased so the assignment is a valuereference.
gLUE2Contact OBJECT-CLASS ::= {
  SUBCLASS OF               { gLUE2Entity }
  MUST CONTAIN              { gLUE2ContactID
                              | gLUE2ContactDetail
                              | gLUE2ContactType }
  MAY CONTAIN               { gLUE2ContactServiceForeignKey
                              | gLUE2ContactDomainForeignKey }
  LDAP-NAME                 {"GLUE2Contact"}
  LDAP-DESC                 "Information enabling to establish a communication with a person or group of persons part of a domain"
  ID                        id-oc-gLUE2Contact }
END
