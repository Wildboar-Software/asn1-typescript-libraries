-- Derived from data/ldap-schema/user.ldif
-- Upstream: https://github.com/TATRC/ClinicalDecisionSupport/blob/b1c4377507f63421e080c174240b6e6c07828917/LDAP/99-user.ldif#L69
-- This module is a container for LDAP schema. It has no module identifier.
-- X- extension fields from the LDAP schema are comments. USAGE userApplications and structural KIND are omitted because they are the defaults.
-- LDAP {length} bounds on directory strings are DirectoryString{n}. Bounds on IA5String, PrintableString, NumericString, and OCTET STRING are SIZE (1..n). Other bounds stay comments because the LDAP figure is an encoded-length hint.
LdapUser DEFINITIONS ::=
BEGIN

IMPORTS

  ATTRIBUTE, OBJECT-CLASS, top
    FROM InformationFramework
      {joint-iso-itu-t ds(5) module(1) informationFramework(1) 9} WITH SUCCESSORS

  caseIgnoreMatch, caseIgnoreSubstringsMatch, commonName, description,
    directoryString, DirectoryString, generalizedTime, generalizedTimeMatch,
    generalizedTimeOrderingMatch, oid, postalAddr, PostalAddress, uid,
    UnboundedDirectoryString
    FROM SelectedAttributeTypes
      {joint-iso-itu-t ds(5) module(1) selectedAttributeTypes(5) 9} WITH SUCCESSORS

  organizationalRole, organizationalUnit
    FROM SelectedObjectClasses
      {joint-iso-itu-t ds(5) module(1) selectedObjectClasses(6) 9} WITH SUCCESSORS

  userPassword
    FROM AuthenticationFramework
      {joint-iso-itu-t ds(5) module(1) authenticationFramework(7) 9} WITH SUCCESSORS

  inetOrgPerson
    FROM InetOrgPerson
      {iso(1) identified-organization(3) dod(6) internet(1) private(4) enterprise(1) wildboar(56490) module(1) inetorgperson(5)} WITH SUCCESSORS

  uidNumber
    FROM NIS
      {iso(1) identified-organization(3) dod(6) internet(1) private(4) enterprise(1) wildboar(56490) module(1) nis(7)} WITH SUCCESSORS

  document
    FROM LdapSchema2ldifCosine ;

-- Object identifiers

id-at-documentExpirationTime OBJECT IDENTIFIER ::= { 1 3 6 1 4 1 26027 1 1 700 }
id-at-languages OBJECT IDENTIFIER ::= { 1 3 6 1 4 1 26027 1 1 701 }
id-at-gender OBJECT IDENTIFIER ::= { 1 3 6 1 4 1 26027 1 1 702 }
id-at-orgCode OBJECT IDENTIFIER ::= { 1 3 6 1 4 1 26027 1 1 703 }
id-at-documentStatus OBJECT IDENTIFIER ::= { 1 3 6 1 4 1 26027 1 1 704 }
id-at-locationCode OBJECT IDENTIFIER ::= { 1 3 6 1 4 1 26027 1 1 705 }
id-at-preferredContactMethod OBJECT IDENTIFIER ::= { 1 3 6 1 4 1 26027 1 1 706 }
id-at-npi OBJECT IDENTIFIER ::= { 1 3 6 1 4 1 26027 1 1 707 }
id-at-providerTaxonomy OBJECT IDENTIFIER ::= { 1 3 6 1 4 1 26027 1 1 708 }
id-oc-kmr-document OBJECT IDENTIFIER ::= { 1 3 6 1 4 1 26027 1 2 500 }
id-oc-kmr-orgPerson OBJECT IDENTIFIER ::= { 1 3 6 1 4 1 26027 1 2 501 }
id-oc-kmr-account OBJECT IDENTIFIER ::= { 1 3 6 1 4 1 26027 1 2 502 }
id-oc-kmr-orgRole OBJECT IDENTIFIER ::= { 1 3 6 1 4 1 26027 1 2 503 }
id-oc-kmr-orgUnit OBJECT IDENTIFIER ::= { 1 3 6 1 4 1 26027 1 2 504 }

-- Attribute types

documentExpirationTime ATTRIBUTE ::= {
  WITH SYNTAX               GeneralizedTime
  EQUALITY MATCHING RULE    generalizedTimeMatch
  ORDERING MATCHING RULE    generalizedTimeOrderingMatch
  SUBSTRINGS MATCHING RULE  caseIgnoreSubstringsMatch
  SINGLE VALUE              TRUE
  LDAP-SYNTAX               generalizedTime.&id
  LDAP-NAME                 {"documentExpirationTime"}
  ID                        id-at-documentExpirationTime }

languages ATTRIBUTE ::= {
  WITH SYNTAX               PostalAddress
  EQUALITY MATCHING RULE    caseIgnoreMatch
  SUBSTRINGS MATCHING RULE  caseIgnoreSubstringsMatch
  LDAP-SYNTAX               postalAddr.&id
  LDAP-NAME                 {"languages"}
  LDAP-DESC                 "written or spoken language for a person"
  ID                        id-at-languages }

gender ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"gender"}
  LDAP-DESC                 "gender of a person"
  ID                        id-at-gender }

orgCode ATTRIBUTE ::= {
  WITH SYNTAX               OBJECT IDENTIFIER
  SINGLE VALUE              TRUE
  LDAP-SYNTAX               oid.&id
  LDAP-NAME                 {"orgCode"}
  LDAP-DESC                 "identifies an organization"
  ID                        id-at-orgCode }

-- LDAP syntax length {256} rendered as DirectoryString{256}.
documentStatus ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"documentStatus"}
  ID                        id-at-documentStatus }

locationCode ATTRIBUTE ::= {
  WITH SYNTAX               OBJECT IDENTIFIER
  SINGLE VALUE              TRUE
  LDAP-SYNTAX               oid.&id
  LDAP-NAME                 {"locationCode"}
  LDAP-DESC                 "identifies the location within an organization"
  ID                        id-at-locationCode }

preferredContactMethod ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"preferredContactMethod"}
  LDAP-DESC                 "the prefer method of contact"
  ID                        id-at-preferredContactMethod }

-- LDAP syntax length {256} rendered as DirectoryString{256}.
npi ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"npi"}
  LDAP-DESC                 "the national provider identifier"
  ID                        id-at-npi }

providerTaxonomy ATTRIBUTE ::= {
  WITH SYNTAX               PostalAddress
  EQUALITY MATCHING RULE    caseIgnoreMatch
  SUBSTRINGS MATCHING RULE  caseIgnoreSubstringsMatch
  LDAP-SYNTAX               postalAddr.&id
  LDAP-NAME                 {"providerTaxonomy"}
  LDAP-DESC                 "provider taxonomies"
  ID                        id-at-providerTaxonomy }

-- Object classes

kmr-document OBJECT-CLASS ::= {
  SUBCLASS OF               { document }
  MAY CONTAIN               { documentExpirationTime
                              | documentStatus }
  LDAP-NAME                 {"kmr-document"}
  ID                        id-oc-kmr-document }

kmr-orgPerson OBJECT-CLASS ::= {
  SUBCLASS OF               { inetOrgPerson }
  MAY CONTAIN               { languages
                              | gender
                              | orgCode
                              | locationCode
                              | preferredContactMethod
                              | npi
                              | providerTaxonomy }
  LDAP-NAME                 {"kmr-orgPerson"}
  ID                        id-oc-kmr-orgPerson }

-- X-ORIGIN: "draft-howard-rfc2307bis"
kmr-account OBJECT-CLASS ::= {
  SUBCLASS OF               { top }
  MUST CONTAIN              { commonName
                              | uid }
  MAY CONTAIN               { uidNumber
                              | userPassword
                              | description }
  LDAP-NAME                 {"kmr-account"}
  ID                        id-oc-kmr-account }

kmr-orgRole OBJECT-CLASS ::= {
  SUBCLASS OF               { organizationalRole }
  MAY CONTAIN               { orgCode
                              | locationCode }
  LDAP-NAME                 {"kmr-orgRole"}
  ID                        id-oc-kmr-orgRole }

kmr-orgUnit OBJECT-CLASS ::= {
  SUBCLASS OF               { organizationalUnit }
  MAY CONTAIN               { orgCode
                              | locationCode }
  LDAP-NAME                 {"kmr-orgUnit"}
  ID                        id-oc-kmr-orgUnit }
END
