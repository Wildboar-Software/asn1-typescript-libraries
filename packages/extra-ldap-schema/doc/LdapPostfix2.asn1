-- Derived from data/ldap-schema/postfix2.schema
-- Upstream: https://github.com/variablenix/ldap-mail-schema/blob/50fe1f26cf942dc4f41a547dc9f6700561a780f8/postfix2.schema#L3
-- This module is a container for LDAP schema. It has no module identifier.
-- X- extension fields from the LDAP schema are comments. USAGE userApplications and structural KIND are omitted because they are the defaults.
-- LDAP {length} bounds on directory strings are DirectoryString{n}. Bounds on IA5String, PrintableString, NumericString, and OCTET STRING are SIZE (1..n). Other bounds stay comments because the LDAP figure is an encoded-length hint.
LdapPostfix2 DEFINITIONS ::=
BEGIN

IMPORTS

  ATTRIBUTE, OBJECT-CLASS, top
    FROM InformationFramework
      {joint-iso-itu-t ds(5) module(1) informationFramework(1) 9} WITH SUCCESSORS

  caseIgnoreMatch, caseIgnoreSubstringsMatch, directoryString, DirectoryString
    FROM SelectedAttributeTypes
      {joint-iso-itu-t ds(5) module(1) selectedAttributeTypes(5) 9} WITH SUCCESSORS ;

-- Object identifiers

id-at-mailacceptinggeneralid OBJECT IDENTIFIER ::= { 1 3 6 1 4 1 4203 666 1 200 }
id-at-maildrop OBJECT IDENTIFIER ::= { 1 3 6 1 4 1 4203 666 1 201 }
id-oc-postfixUser OBJECT IDENTIFIER ::= { 1 3 6 1 4 1 4203 666 1 100 }

-- Attribute types

-- LDAP syntax length {1024} rendered as DirectoryString{1024}.
mailacceptinggeneralid ATTRIBUTE ::= {
  WITH SYNTAX               DirectoryString{1024}
  EQUALITY MATCHING RULE    caseIgnoreMatch
  SUBSTRINGS MATCHING RULE  caseIgnoreSubstringsMatch
  LDAP-SYNTAX               directoryString.&id
  LDAP-NAME                 {"mailacceptinggeneralid"}
  LDAP-DESC                 "Postfix mail local address alias attribute"
  ID                        id-at-mailacceptinggeneralid }

-- LDAP syntax length {1024} rendered as DirectoryString{1024}.
maildrop ATTRIBUTE ::= {
  WITH SYNTAX               DirectoryString{1024}
  EQUALITY MATCHING RULE    caseIgnoreMatch
  SUBSTRINGS MATCHING RULE  caseIgnoreSubstringsMatch
  LDAP-SYNTAX               directoryString.&id
  LDAP-NAME                 {"maildrop"}
  LDAP-DESC                 "Postfix mail final destination attribute"
  ID                        id-at-maildrop }

-- Object classes

postfixUser OBJECT-CLASS ::= {
  SUBCLASS OF               { top }
  KIND                      auxiliary
  MAY CONTAIN               { mailacceptinggeneralid
                              | maildrop }
  LDAP-NAME                 {"postfixUser"}
  LDAP-DESC                 "Postfix mail user class"
  ID                        id-oc-postfixUser }
END
