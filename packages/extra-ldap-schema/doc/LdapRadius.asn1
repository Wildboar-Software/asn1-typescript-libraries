-- Derived from data/ldap-schema/radius.ldif
-- This module is a container for LDAP schema. It has no module identifier.
-- X- extension fields from the LDAP schema are comments. USAGE userApplications and structural KIND are omitted because they are the defaults.
LdapRadius DEFINITIONS ::=
BEGIN

IMPORTS

  ATTRIBUTE, OBJECT-CLASS, objectClass, top
    FROM InformationFramework
      {joint-iso-itu-t ds(5) module(1) informationFramework(1) 9} WITH SUCCESSORS

  caseIgnoreMatch, caseIgnoreSubstringsMatch, directoryString, integer,
    integerMatch, integerOrderingMatch, organizationalUnitName,
    UnboundedDirectoryString
    FROM SelectedAttributeTypes
      {joint-iso-itu-t ds(5) module(1) selectedAttributeTypes(5) 9} WITH SUCCESSORS

  inum
    FROM LdapOx ;

-- Object identifiers

id-at-oxRadiusListenInterface OBJECT IDENTIFIER ::= { 1 3 6 1 4 48710 1 3 500 }
id-at-oxRadiusAuthenticationPort OBJECT IDENTIFIER ::= { 1 3 6 1 4 48710 1 3 501 }
id-at-oxRadiusAccountingPort OBJECT IDENTIFIER ::= { 1 3 6 1 4 48710 1 3 502 }
id-at-oxRadiusOpenidUsername OBJECT IDENTIFIER ::= { 1 3 6 1 4 48710 1 3 503 }
id-at-oxRadiusOpenidPassword OBJECT IDENTIFIER ::= { 1 3 6 1 4 48710 1 3 504 }
id-at-oxRadiusClientName OBJECT IDENTIFIER ::= { 1 3 6 1 4 48710 1 3 505 }
id-at-oxRadiusClientIpAddress OBJECT IDENTIFIER ::= { 1 3 6 1 4 48710 1 3 506 }
id-at-oxRadiusClientSecret OBJECT IDENTIFIER ::= { 1 3 6 1 4 48710 1 3 507 }
id-at-oxRadiusClientSortPriority OBJECT IDENTIFIER ::= { 1 3 6 1 4 48710 1 3 508 }
id-at-oxRadiusOpenIdBaseUrl OBJECT IDENTIFIER ::= { 1 3 6 1 4 48710 1 3 509 }
id-at-oxRadiusAcrValue OBJECT IDENTIFIER ::= { 1 3 6 1 4 48710 1 3 510 }
id-at-oxRadiusAuthScope OBJECT IDENTIFIER ::= { 1 3 6 1 4 48710 1 3 511 }
id-at-oxRadiusAuthenticationTimeout OBJECT IDENTIFIER ::= { 1 3 6 1 4 48710 1 3 512 }
id-oc-oxRadiusServerConfiguration OBJECT IDENTIFIER ::= { 1 3 6 1 4 1 48710 1 4 90 }
id-oc-oxRadiusClient OBJECT IDENTIFIER ::= { 1 3 6 1 4 1 48710 1 4 91 }

-- Attribute types

-- X-ORIGIN: "Gluu created attribute"
oxRadiusListenInterface ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxRadiusListenInterface"}
  LDAP-DESC                 "Gluu Radius Server Listen Interface(s)"
  ID                        id-at-oxRadiusListenInterface }

-- X-ORIGIN: "Gluu created attribute"
oxRadiusAuthenticationPort ATTRIBUTE ::= {
  WITH SYNTAX               INTEGER
  EQUALITY MATCHING RULE    integerMatch
  SUBSTRINGS MATCHING RULE  integerOrderingMatch
  LDAP-SYNTAX               integer.&id
  LDAP-NAME                 {"oxRadiusAuthenticationPort"}
  LDAP-DESC                 "Gluu Radius Server Authentication Port"
  ID                        id-at-oxRadiusAuthenticationPort }

-- X-ORIGIN: "Gluu created attribute"
oxRadiusAccountingPort ATTRIBUTE ::= {
  WITH SYNTAX               INTEGER
  EQUALITY MATCHING RULE    integerMatch
  SUBSTRINGS MATCHING RULE  integerOrderingMatch
  LDAP-SYNTAX               integer.&id
  LDAP-NAME                 {"oxRadiusAccountingPort"}
  LDAP-DESC                 "Gluu Radius Server Accounting Port"
  ID                        id-at-oxRadiusAccountingPort }

-- X-ORIGIN: "Gluu created attribute"
oxRadiusOpenidUsername ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxRadiusOpenidUsername"}
  LDAP-DESC                 "Gluu Radius Server OpenID Username"
  ID                        id-at-oxRadiusOpenidUsername }

-- X-ORIGIN: "Gluu created attribute"
oxRadiusOpenidPassword ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxRadiusOpenidPassword"}
  LDAP-DESC                 "Gluu Radius Server OpenID Password"
  ID                        id-at-oxRadiusOpenidPassword }

-- X-ORIGIN: "Gluu created attribute"
oxRadiusClientName ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxRadiusClientName"}
  LDAP-DESC                 "Gluu Radius Client Name"
  ID                        id-at-oxRadiusClientName }

-- X-ORIGIN: "Gluu created attribute"
oxRadiusClientIpAddress ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxRadiusClientIpAddress"}
  LDAP-DESC                 "Gluu Radius Client Ip Address"
  ID                        id-at-oxRadiusClientIpAddress }

-- X-ORIGIN: "Gluu created attribute"
oxRadiusClientSecret ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxRadiusClientSecret"}
  LDAP-DESC                 "Gluu Radius Client Secret"
  ID                        id-at-oxRadiusClientSecret }

-- X-ORIGIN: "Gluu created attribute"
oxRadiusClientSortPriority ATTRIBUTE ::= {
  WITH SYNTAX               INTEGER
  EQUALITY MATCHING RULE    integerMatch
  SUBSTRINGS MATCHING RULE  integerOrderingMatch
  LDAP-SYNTAX               integer.&id
  LDAP-NAME                 {"oxRadiusClientSortPriority"}
  LDAP-DESC                 "Gluu Radius Sort Priority"
  ID                        id-at-oxRadiusClientSortPriority }

-- X-ORIGIN: "Gluu created attribute"
oxRadiusOpenIdBaseUrl ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxRadiusOpenIdBaseUrl"}
  LDAP-DESC                 "Gluu Radius Openid client base url"
  ID                        id-at-oxRadiusOpenIdBaseUrl }

-- X-ORIGIN: "Gluu created attribute"
oxRadiusAcrValue ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxRadiusAcrValue"}
  LDAP-DESC                 "Gluu Radius acr_values"
  ID                        id-at-oxRadiusAcrValue }

-- X-ORIGIN: "Gluu created attribute"
oxRadiusAuthScope ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxRadiusAuthScope"}
  LDAP-DESC                 "Gluu Radius scope"
  ID                        id-at-oxRadiusAuthScope }

-- X-ORIGIN: "Gluu created attribute"
oxRadiusAuthenticationTimeout ATTRIBUTE ::= {
  WITH SYNTAX               INTEGER
  EQUALITY MATCHING RULE    integerMatch
  SUBSTRINGS MATCHING RULE  integerOrderingMatch
  LDAP-SYNTAX               integer.&id
  LDAP-NAME                 {"oxRadiusAuthenticationTimeout"}
  LDAP-DESC                 "Gluu Radius authentication timeout"
  ID                        id-at-oxRadiusAuthenticationTimeout }

-- Object classes

-- X-ORIGIN: "Gluu created objectclass"
oxRadiusServerConfiguration OBJECT-CLASS ::= {
  SUBCLASS OF               { top }
  MUST CONTAIN              { objectClass }
  MAY CONTAIN               { organizationalUnitName
                              | oxRadiusListenInterface
                              | oxRadiusAuthenticationPort
                              | oxRadiusAccountingPort
                              | oxRadiusOpenIdBaseUrl
                              | oxRadiusOpenidUsername
                              | oxRadiusOpenidPassword
                              | oxRadiusAcrValue
                              | oxRadiusAuthScope
                              | oxRadiusAuthenticationTimeout }
  LDAP-NAME                 {"oxRadiusServerConfiguration"}
  ID                        id-oc-oxRadiusServerConfiguration }

-- X-ORIGIN: "Gluu created objectclass"
oxRadiusClient OBJECT-CLASS ::= {
  SUBCLASS OF               { top }
  MUST CONTAIN              { objectClass }
  MAY CONTAIN               { inum
                              | oxRadiusClientName
                              | oxRadiusClientIpAddress
                              | oxRadiusClientSecret
                              | oxRadiusClientSortPriority }
  LDAP-NAME                 {"oxRadiusClient"}
  ID                        id-oc-oxRadiusClient }
END
