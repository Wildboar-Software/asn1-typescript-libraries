-- Derived from data/ldap-schema/ldapab.schema
-- Upstream: https://github.com/cosmocode/contagged/blob/bc901793a2cd1b7c72effae2f8ab0503c25601a4/doc/ldapab.schema#L31
-- This module is a container for LDAP schema. It has no module identifier.
-- X- extension fields from the LDAP schema are comments. USAGE userApplications and structural KIND are omitted because they are the defaults.
-- Object classes with no SUP were subclassed from top, the LDAP default (RFC 4512).
-- LDAP {length} bounds on directory strings are DirectoryString{n}. Bounds on IA5String, PrintableString, NumericString, and OCTET STRING are SIZE (1..n). Other bounds stay comments because the LDAP figure is an encoded-length hint.
Ldapab DEFINITIONS ::=
BEGIN

IMPORTS

  ATTRIBUTE, OBJECT-CLASS, top
    FROM InformationFramework
      {joint-iso-itu-t ds(5) module(1) informationFramework(1) 9} WITH SUCCESSORS

  caseIgnoreMatch, caseIgnoreOrderingMatch, caseIgnoreSubstringsMatch,
    countryName, directoryString, DirectoryString, UnboundedDirectoryString
    FROM SelectedAttributeTypes
      {joint-iso-itu-t ds(5) module(1) selectedAttributeTypes(5) 9} WITH SUCCESSORS ;

-- Object identifiers

id-at-anniversary OBJECT IDENTIFIER ::= { 1 3 6 1 4 1 16331 2 2 1 1 }
id-at-marker OBJECT IDENTIFIER ::= { 1 3 6 1 4 1 16331 2 2 1 2 }
id-at-birthday OBJECT IDENTIFIER ::= { 1 3 6 1 4 1 16331 2 2 1 3 }
id-at-custom1 OBJECT IDENTIFIER ::= { 1 3 6 1 4 1 16331 2 2 1 51 }
id-at-custom2 OBJECT IDENTIFIER ::= { 1 3 6 1 4 1 16331 2 2 1 52 }
id-at-custom3 OBJECT IDENTIFIER ::= { 1 3 6 1 4 1 16331 2 2 1 53 }
id-at-custom4 OBJECT IDENTIFIER ::= { 1 3 6 1 4 1 16331 2 2 1 54 }
id-oc-contactPerson OBJECT IDENTIFIER ::= { 1 3 6 1 4 1 16331 2 2 2 1 }

-- Attribute types

anniversary ATTRIBUTE ::= {
  WITH SYNTAX               UnboundedDirectoryString
  EQUALITY MATCHING RULE    caseIgnoreMatch
  ORDERING MATCHING RULE    caseIgnoreOrderingMatch
  SUBSTRINGS MATCHING RULE  caseIgnoreSubstringsMatch
  SINGLE VALUE              TRUE
  LDAP-SYNTAX               directoryString.&id
  LDAP-NAME                 {"anniversary"}
  LDAP-DESC                 "Holds Marriage dates etc."
  ID                        id-at-anniversary }

-- LDAP syntax length {256} rendered as DirectoryString{256}.
marker ATTRIBUTE ::= {
  WITH SYNTAX               DirectoryString{256}
  EQUALITY MATCHING RULE    caseIgnoreMatch
  ORDERING MATCHING RULE    caseIgnoreOrderingMatch
  SUBSTRINGS MATCHING RULE  caseIgnoreSubstringsMatch
  LDAP-SYNTAX               directoryString.&id
  LDAP-NAME                 {"marker"}
  LDAP-DESC                 "For tagging support"
  ID                        id-at-marker }

birthday ATTRIBUTE ::= {
  WITH SYNTAX               UnboundedDirectoryString
  EQUALITY MATCHING RULE    caseIgnoreMatch
  ORDERING MATCHING RULE    caseIgnoreOrderingMatch
  SUBSTRINGS MATCHING RULE  caseIgnoreSubstringsMatch
  SINGLE VALUE              TRUE
  LDAP-SYNTAX               directoryString.&id
  LDAP-NAME                 {"birthday"}
  LDAP-DESC                 "Date of birth"
  ID                        id-at-birthday }

-- LDAP syntax length {256} rendered as DirectoryString{256}.
custom1 ATTRIBUTE ::= {
  WITH SYNTAX               DirectoryString{256}
  EQUALITY MATCHING RULE    caseIgnoreMatch
  ORDERING MATCHING RULE    caseIgnoreOrderingMatch
  SUBSTRINGS MATCHING RULE  caseIgnoreSubstringsMatch
  LDAP-SYNTAX               directoryString.&id
  LDAP-NAME                 {"custom1"}
  LDAP-DESC                 "Thunderbird compatible custom field 1"
  ID                        id-at-custom1 }

-- LDAP syntax length {256} rendered as DirectoryString{256}.
custom2 ATTRIBUTE ::= {
  WITH SYNTAX               DirectoryString{256}
  EQUALITY MATCHING RULE    caseIgnoreMatch
  ORDERING MATCHING RULE    caseIgnoreOrderingMatch
  SUBSTRINGS MATCHING RULE  caseIgnoreSubstringsMatch
  LDAP-SYNTAX               directoryString.&id
  LDAP-NAME                 {"custom2"}
  LDAP-DESC                 "Thunderbird compatible custom field 2"
  ID                        id-at-custom2 }

-- LDAP syntax length {256} rendered as DirectoryString{256}.
custom3 ATTRIBUTE ::= {
  WITH SYNTAX               DirectoryString{256}
  EQUALITY MATCHING RULE    caseIgnoreMatch
  ORDERING MATCHING RULE    caseIgnoreOrderingMatch
  SUBSTRINGS MATCHING RULE  caseIgnoreSubstringsMatch
  LDAP-SYNTAX               directoryString.&id
  LDAP-NAME                 {"custom3"}
  LDAP-DESC                 "Thunderbird compatible custom field 3"
  ID                        id-at-custom3 }

-- LDAP syntax length {256} rendered as DirectoryString{256}.
custom4 ATTRIBUTE ::= {
  WITH SYNTAX               DirectoryString{256}
  EQUALITY MATCHING RULE    caseIgnoreMatch
  ORDERING MATCHING RULE    caseIgnoreOrderingMatch
  SUBSTRINGS MATCHING RULE  caseIgnoreSubstringsMatch
  LDAP-SYNTAX               directoryString.&id
  LDAP-NAME                 {"custom4"}
  LDAP-DESC                 "Thunderbird compatible custom field 4"
  ID                        id-at-custom4 }

-- Object classes

-- SUP was absent. RFC 4512 treats that as a subclass of top, so SUBCLASS OF { top } was added.
contactPerson OBJECT-CLASS ::= {
  SUBCLASS OF               { top }
  KIND                      auxiliary
  MAY CONTAIN               { anniversary
                              | marker
                              | birthday
                              | custom1
                              | custom2
                              | custom3
                              | custom4
                              | countryName }
  LDAP-NAME                 {"contactPerson"}
  LDAP-DESC                 "Contact - Addressbook entry"
  ID                        id-oc-contactPerson }
END
