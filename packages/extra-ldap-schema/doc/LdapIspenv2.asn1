-- Derived from data/ldap-schema/ispenv2.schema
-- Upstream: https://github.com/fln/gnarwl/blob/a4861bea0f40ab54d6f8ba4084e589030f338c43/doc/ISPEnv2.schema#L161
-- This module is a container for LDAP schema. It has no module identifier.
-- X- extension fields from the LDAP schema are comments. USAGE userApplications and structural KIND are omitted because they are the defaults.
-- 31 elements were omitted because another source file in this corpus defines the same OID.
LdapIspenv2 DEFINITIONS ::=
BEGIN

IMPORTS

  ATTRIBUTE, OBJECT-CLASS, top
    FROM InformationFramework
      {joint-iso-itu-t ds(5) module(1) informationFramework(1) 9} WITH SUCCESSORS

  caseExactIA5Match, ia5String
    FROM SelectedAttributeTypes
      {joint-iso-itu-t ds(5) module(1) selectedAttributeTypes(5) 9} WITH SUCCESSORS

  caseExactIA5SubstringsMatch
    FROM OpenLDAP
      {iso(1) identified-organization(3) dod(6) internet(1) private(4) enterprise(1) wildboar(56490) module(1) openldap(28)} WITH SUCCESSORS ;

-- Object identifiers

id-at-filePerm OBJECT IDENTIFIER ::= { 1 3 6 1 4 1 11048 1 1 1 23 }
id-at-fileContent OBJECT IDENTIFIER ::= { 1 3 6 1 4 1 11048 1 1 1 24 }
id-at-fileName OBJECT IDENTIFIER ::= { 1 3 6 1 4 1 11048 1 1 1 25 }
id-at-filePath OBJECT IDENTIFIER ::= { 1 3 6 1 4 1 11048 1 1 1 26 }
id-at-fileType OBJECT IDENTIFIER ::= { 1 3 6 1 4 1 11048 1 1 1 27 }
id-oc-file OBJECT IDENTIFIER ::= { 1 3 6 1 4 1 11048 1 1 2 10 }

-- Attribute types

filePerm ATTRIBUTE ::= {
  WITH SYNTAX               IA5String
  EQUALITY MATCHING RULE    caseExactIA5Match
  SUBSTRINGS MATCHING RULE  caseExactIA5SubstringsMatch
  SINGLE VALUE              TRUE
  LDAP-SYNTAX               ia5String.&id
  LDAP-NAME                 {"filePerm"}
  LDAP-DESC                 "file permission field"
  ID                        id-at-filePerm }

-- LDAP binary syntax has no X.500 directory type here. Represented as OCTET STRING.
fileContent ATTRIBUTE ::= {
  WITH SYNTAX               OCTET STRING
  SINGLE VALUE              TRUE
  LDAP-SYNTAX               { 1 3 6 1 4 1 1466 115 121 1 5 }
  LDAP-NAME                 {"fileContent"}
  LDAP-DESC                 "file content"
  ID                        id-at-fileContent }

fileName ATTRIBUTE ::= {
  WITH SYNTAX               IA5String
  EQUALITY MATCHING RULE    caseExactIA5Match
  SUBSTRINGS MATCHING RULE  caseExactIA5SubstringsMatch
  SINGLE VALUE              TRUE
  LDAP-SYNTAX               ia5String.&id
  LDAP-NAME                 {"fileName"}
  LDAP-DESC                 "relative filename"
  ID                        id-at-fileName }

filePath ATTRIBUTE ::= {
  WITH SYNTAX               IA5String
  EQUALITY MATCHING RULE    caseExactIA5Match
  SUBSTRINGS MATCHING RULE  caseExactIA5SubstringsMatch
  SINGLE VALUE              TRUE
  LDAP-SYNTAX               ia5String.&id
  LDAP-NAME                 {"filePath"}
  LDAP-DESC                 "path to the file"
  ID                        id-at-filePath }

fileType ATTRIBUTE ::= {
  WITH SYNTAX               IA5String
  EQUALITY MATCHING RULE    caseExactIA5Match
  SUBSTRINGS MATCHING RULE  caseExactIA5SubstringsMatch
  LDAP-SYNTAX               ia5String.&id
  LDAP-NAME                 {"fileType"}
  LDAP-DESC                 "type of file"
  ID                        id-at-fileType }

-- Object classes

file OBJECT-CLASS ::= {
  SUBCLASS OF               { top }
  MUST CONTAIN              { fileName }
  MAY CONTAIN               { filePath
                              | filePerm
                              | fileContent
                              | fileType }
  LDAP-NAME                 {"file"}
  LDAP-DESC                 "Used to store files in LDAP"
  ID                        id-oc-file }
END
