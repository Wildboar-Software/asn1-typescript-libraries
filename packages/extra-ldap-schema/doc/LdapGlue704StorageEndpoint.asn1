-- Derived from data/ldap-schema/glue/7-04-StorageEndpoint.schema
-- Upstream: http://redmine.ogf.org/projects/glue-wg
-- This module is a container for LDAP schema. It has no module identifier.
-- X- extension fields from the LDAP schema are comments. USAGE userApplications and structural KIND are omitted because they are the defaults.
LdapGlue704StorageEndpoint DEFINITIONS ::=
BEGIN

IMPORTS

  ATTRIBUTE, OBJECT-CLASS
    FROM InformationFramework
      {joint-iso-itu-t ds(5) module(1) informationFramework(1) 9} WITH SUCCESSORS

  caseExactMatch, caseExactSubstringsMatch, directoryString,
    UnboundedDirectoryString
    FROM SelectedAttributeTypes
      {joint-iso-itu-t ds(5) module(1) selectedAttributeTypes(5) 9} WITH SUCCESSORS

  gLUE2Endpoint
    FROM LdapGlue507Endpoint ;

-- Object identifiers

id-at-gLUE2StorageEndpointStorageServiceForeignKey OBJECT IDENTIFIER ::= { 1 3 6 1 4 1 6757 100 1 1 30 1 }
id-oc-gLUE2StorageEndpoint OBJECT IDENTIFIER ::= { 1 3 6 1 4 1 6757 100 1 1 30 }

-- Attribute types

-- initial capital of "GLUE2StorageEndpointStorageServiceForeignKey" lowercased so the assignment is a valuereference.
gLUE2StorageEndpointStorageServiceForeignKey ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2StorageEndpointStorageServiceForeignKey"}
  LDAP-DESC                 "ForeignKey"
  ID                        id-at-gLUE2StorageEndpointStorageServiceForeignKey }

-- Object classes

-- initial capital of "GLUE2StorageEndpoint" lowercased so the assignment is a valuereference.
gLUE2StorageEndpoint OBJECT-CLASS ::= {
  SUBCLASS OF               { gLUE2Endpoint }
  MAY CONTAIN               { gLUE2StorageEndpointStorageServiceForeignKey }
  LDAP-NAME                 {"GLUE2StorageEndpoint"}
  LDAP-DESC                 "A network location having a well-defined interface and exposing the service functionalities"
  ID                        id-oc-gLUE2StorageEndpoint }
END
