-- Derived from data/ldap-schema/ldapmigration/70sun-schema2.ldif
-- This module is a container for LDAP schema. It has no module identifier.
-- X- extension fields from the LDAP schema are comments. USAGE userApplications and structural KIND are omitted because they are the defaults.
-- Object classes with no SUP were subclassed from top, the LDAP default (RFC 4512).
Ldapmigration70sunSchema2 DEFINITIONS ::=
BEGIN

IMPORTS

  ATTRIBUTE, OBJECT-CLASS, top
    FROM InformationFramework
      {joint-iso-itu-t ds(5) module(1) informationFramework(1) 9} WITH SUCCESSORS

  description, directoryString, ia5String, integer, organizationalUnitName,
    organizationName, UnboundedDirectoryString
    FROM SelectedAttributeTypes
      {joint-iso-itu-t ds(5) module(1) selectedAttributeTypes(5) 9} WITH SUCCESSORS

  associatedDomain
    FROM MIXERAddressMapping
      {iso(1) identified-organization(3) dod(6) internet(1) private(4) enterprise(1) wildboar(56490) module(1) mixer-address-mapping(9)} WITH SUCCESSORS

  inetDomainStatus, parentOrganization
    FROM Ldapmigration20subscriber ;

-- Object identifiers

id-at-sunPreferredDomain OBJECT IDENTIFIER ::= { 2 16 840 1 113730 3 1 1086 }
id-at-sunRegisteredServiceName OBJECT IDENTIFIER ::= { 1 3 6 1 4 1 42 2 27 9 1 593 }
id-at-sunPreferredOrganization OBJECT IDENTIFIER ::= { 1 3 6 1 4 1 42 2 27 9 1 75 }
id-at-sunAdditionalTemplates OBJECT IDENTIFIER ::= { 1 3 6 1 4 1 42 2 27 9 1 76 }
id-at-sunOverrideTemplates OBJECT IDENTIFIER ::= { 1 3 6 1 4 1 42 2 27 9 1 77 }
id-at-sunNameSpaceUniqueAttrs OBJECT IDENTIFIER ::= { 1 3 6 1 4 1 42 2 27 9 1 85 }
id-at-sunserviceid OBJECT IDENTIFIER ::= { 1 3 6 1 4 1 42 2 27 9 1 79 }
id-at-sunkeyvalue OBJECT IDENTIFIER ::= { 1 3 6 1 4 1 42 2 27 9 1 83 }
id-at-sunsmspriority OBJECT IDENTIFIER ::= { 1 3 6 1 4 1 42 2 27 9 1 81 }
id-at-sunxmlkeyvalue OBJECT IDENTIFIER ::= { 1 3 6 1 4 1 42 2 27 9 1 84 }
id-oc-sunManagedOrganization OBJECT IDENTIFIER ::= { 2 16 840 1 113730 3 2 185 }
id-oc-sunManagedSubOrganization OBJECT IDENTIFIER ::= { 1 3 6 1 4 1 42 2 27 9 2 75 }
id-oc-sunNameSpace OBJECT IDENTIFIER ::= { 1 3 6 1 4 1 42 2 27 9 2 29 }
id-oc-sunservicecomponent OBJECT IDENTIFIER ::= { 1 3 6 1 4 1 42 2 27 9 2 27 }

-- Attribute types

-- X-ORIGIN: "Sun Java System Identity Management"
sunPreferredDomain ATTRIBUTE ::= {
  WITH SYNTAX               UnboundedDirectoryString
  SINGLE VALUE              TRUE
  LDAP-SYNTAX               directoryString.&id
  LDAP-NAME                 {"sunPreferredDomain"}
  LDAP-DESC                 "The DNS domain name"
  ID                        id-at-sunPreferredDomain }

-- X-ORIGIN: "Sun Java System Identity Management"
sunRegisteredServiceName ATTRIBUTE ::= {
  WITH SYNTAX               UnboundedDirectoryString
  LDAP-SYNTAX               directoryString.&id
  LDAP-NAME                 {"sunRegisteredServiceName", "iplanet-am-service-status"}
  LDAP-DESC                 "List of services registered with an organization - used by identity server"
  ID                        id-at-sunRegisteredServiceName }

-- X-ORIGIN: "Sun Java System Identity Management"
sunPreferredOrganization ATTRIBUTE ::= {
  WITH SYNTAX               UnboundedDirectoryString
  SINGLE VALUE              TRUE
  LDAP-SYNTAX               directoryString.&id
  LDAP-NAME                 {"sunPreferredOrganization"}
  LDAP-DESC                 "Organization Name"
  ID                        id-at-sunPreferredOrganization }

-- X-ORIGIN: "Sun Java System Identity Management"
sunAdditionalTemplates ATTRIBUTE ::= {
  WITH SYNTAX               UnboundedDirectoryString
  LDAP-SYNTAX               directoryString.&id
  LDAP-NAME                 {"sunAdditionalTemplates"}
  LDAP-DESC                 "Template RDN"
  ID                        id-at-sunAdditionalTemplates }

-- X-ORIGIN: "Sun Java System Identity Management"
sunOverrideTemplates ATTRIBUTE ::= {
  WITH SYNTAX               UnboundedDirectoryString
  LDAP-SYNTAX               directoryString.&id
  LDAP-NAME                 {"sunOverrideTemplates"}
  LDAP-DESC                 "Template RDN Override Global Template"
  ID                        id-at-sunOverrideTemplates }

-- X-ORIGIN: "Sun Java System Identity Management"
sunNameSpaceUniqueAttrs ATTRIBUTE ::= {
  WITH SYNTAX               UnboundedDirectoryString
  LDAP-SYNTAX               directoryString.&id
  LDAP-NAME                 {"sunNameSpaceUniqueAttrs"}
  LDAP-DESC                 "Attribute to store the key values in xml format"
  ID                        id-at-sunNameSpaceUniqueAttrs }

-- X-ORIGIN: "Sun Java System Identity Management"
sunserviceid ATTRIBUTE ::= {
  WITH SYNTAX               UnboundedDirectoryString
  SINGLE VALUE              TRUE
  LDAP-SYNTAX               directoryString.&id
  LDAP-NAME                 {"sunserviceid"}
  LDAP-DESC                 "Attribute to store the reference to the inherited object"
  ID                        id-at-sunserviceid }

-- X-ORIGIN: "Sun Java System Identity Management"
sunkeyvalue ATTRIBUTE ::= {
  WITH SYNTAX               IA5String
  LDAP-SYNTAX               ia5String.&id
  LDAP-NAME                 {"sunkeyvalue"}
  LDAP-DESC                 "Attribute to store the encoded key values of the services"
  ID                        id-at-sunkeyvalue }

-- X-ORIGIN: "Sun Java System Identity Management"
sunsmspriority ATTRIBUTE ::= {
  WITH SYNTAX               INTEGER
  SINGLE VALUE              TRUE
  LDAP-SYNTAX               integer.&id
  LDAP-NAME                 {"sunsmspriority"}
  LDAP-DESC                 "To store the priority of the service with respect to its siblings"
  ID                        id-at-sunsmspriority }

-- X-ORIGIN: "Sun Java System Identity Management"
sunxmlkeyvalue ATTRIBUTE ::= {
  WITH SYNTAX               IA5String
  LDAP-SYNTAX               ia5String.&id
  LDAP-NAME                 {"sunxmlkeyvalue"}
  LDAP-DESC                 "Attribute to store the key values in xml format"
  ID                        id-at-sunxmlkeyvalue }

-- Object classes

-- X-ORIGIN: "Sun Java System Identity Management"
sunManagedOrganization OBJECT-CLASS ::= {
  SUBCLASS OF               { top }
  KIND                      auxiliary
  MAY CONTAIN               { inetDomainStatus
                              | sunPreferredDomain
                              | associatedDomain
                              | sunPreferredOrganization
                              | sunAdditionalTemplates
                              | sunOverrideTemplates
                              | sunRegisteredServiceName
                              | organizationName }
  LDAP-NAME                 {"sunManagedOrganization"}
  LDAP-DESC                 "Auxiliary class which must be present in an organization entry"
  ID                        id-oc-sunManagedOrganization }

-- X-ORIGIN: "Sun Java System Identity Management"
sunManagedSubOrganization OBJECT-CLASS ::= {
  SUBCLASS OF               { top }
  KIND                      auxiliary
  MAY CONTAIN               { inetDomainStatus
                              | parentOrganization }
  LDAP-NAME                 {"sunManagedSubOrganization"}
  LDAP-DESC                 "Auxiliary class which must be present in an sub organization entry"
  ID                        id-oc-sunManagedSubOrganization }

-- X-ORIGIN: "Sun Java System Identity Management"
-- SUP was absent. RFC 4512 treats that as a subclass of top, so SUBCLASS OF { top } was added.
sunNameSpace OBJECT-CLASS ::= {
  SUBCLASS OF               { top }
  KIND                      auxiliary
  MAY CONTAIN               { sunNameSpaceUniqueAttrs }
  LDAP-NAME                 {"sunNameSpace"}
  LDAP-DESC                 "Auxiliary class which must be present at the root of a subtree representing a namespace"
  ID                        id-oc-sunNameSpace }

-- X-ORIGIN: "Sun Java System Identity Management"
sunservicecomponent OBJECT-CLASS ::= {
  SUBCLASS OF               { top }
  MUST CONTAIN              { organizationalUnitName }
  MAY CONTAIN               { sunserviceid
                              | sunsmspriority
                              | sunkeyvalue
                              | sunxmlkeyvalue
                              | description }
  LDAP-NAME                 {"sunservicecomponent"}
  LDAP-DESC                 "Sub-components of the service"
  ID                        id-oc-sunservicecomponent }
END
