-- Derived from data/ldap-schema/ldapmigration/92freeradius.ldif
-- This module is a container for LDAP schema. It has no module identifier.
-- X- extension fields from the LDAP schema are comments. USAGE userApplications and structural KIND are omitted because they are the defaults.
-- 65 elements were omitted because their OIDs are already defined. See CONVERSION-REPORT.txt.
Ldapmigration92freeradius DEFINITIONS ::=
BEGIN

IMPORTS

  ATTRIBUTE
    FROM InformationFramework
      {joint-iso-itu-t ds(5) module(1) informationFramework(1) 9} WITH SUCCESSORS

  caseIgnoreIA5Match, ia5String
    FROM SelectedAttributeTypes
      {joint-iso-itu-t ds(5) module(1) selectedAttributeTypes(5) 9} WITH SUCCESSORS ;

-- Object identifiers

id-at-radiusReplicateToRealm OBJECT IDENTIFIER ::= { 1 3 6 1 4 1 3317 4 3 1 51 }
id-at-radiusCheckItem OBJECT IDENTIFIER ::= { 1 3 6 1 4 1 3317 4 3 1 59 }
id-at-radiusReplyItem OBJECT IDENTIFIER ::= { 1 3 6 1 4 1 3317 4 3 1 60 }

-- Attribute types

radiusReplicateToRealm ATTRIBUTE ::= {
  WITH SYNTAX               IA5String
  EQUALITY MATCHING RULE    caseIgnoreIA5Match
  SINGLE VALUE              TRUE
  LDAP-SYNTAX               ia5String.&id
  LDAP-NAME                 {"radiusReplicateToRealm"}
  ID                        id-at-radiusReplicateToRealm }

radiusCheckItem ATTRIBUTE ::= {
  WITH SYNTAX               IA5String
  EQUALITY MATCHING RULE    caseIgnoreIA5Match
  LDAP-SYNTAX               ia5String.&id
  LDAP-NAME                 {"radiusCheckItem"}
  ID                        id-at-radiusCheckItem }

radiusReplyItem ATTRIBUTE ::= {
  WITH SYNTAX               IA5String
  EQUALITY MATCHING RULE    caseIgnoreIA5Match
  LDAP-SYNTAX               ia5String.&id
  LDAP-NAME                 {"radiusReplyItem"}
  ID                        id-at-radiusReplyItem }
END
