-- Derived from data/ldap-schema/dbmail.schema
-- This module is a container for LDAP schema. It has no module identifier.
-- X- extension fields from the LDAP schema are comments. USAGE userApplications and structural KIND are omitted because they are the defaults.
-- LDAP {length} bounds on directory strings are DirectoryString{n}. Bounds on IA5String, PrintableString, NumericString, and OCTET STRING are SIZE (1..n). Other bounds stay comments because the LDAP figure is an encoded-length hint.
LdapDbmail DEFINITIONS ::=
BEGIN

IMPORTS

  ATTRIBUTE, OBJECT-CLASS, top
    FROM InformationFramework
      {joint-iso-itu-t ds(5) module(1) informationFramework(1) 9} WITH SUCCESSORS

  caseIgnoreIA5Match, caseIgnoreIA5SubstringsMatch, caseIgnoreMatch, ia5String,
    printableString, uid
    FROM SelectedAttributeTypes
      {joint-iso-itu-t ds(5) module(1) selectedAttributeTypes(5) 9} WITH SUCCESSORS

  userPassword
    FROM AuthenticationFramework
      {joint-iso-itu-t ds(5) module(1) authenticationFramework(7) 9} WITH SUCCESSORS

  gidNumber, uidNumber
    FROM NIS
      {iso(1) identified-organization(3) dod(6) internet(1) private(4) enterprise(1) wildboar(56490) module(1) nis(7)} WITH SUCCESSORS

  mail
    FROM LdapSchema2ldifCore ;

-- Object identifiers

id-at-mailQuota OBJECT IDENTIFIER ::= { 1 3 6 1 4 1 12340 6 2 1 1 }
id-at-mailForwardingAddress OBJECT IDENTIFIER ::= { 1 3 6 1 4 1 12340 6 2 1 2 }
id-at-mailHost OBJECT IDENTIFIER ::= { 1 3 6 1 4 1 12340 6 2 1 3 }
id-at-dbmailUID OBJECT IDENTIFIER ::= { 1 3 6 1 4 1 12340 6 2 1 4 }
id-at-dbmailGID OBJECT IDENTIFIER ::= { 1 3 6 1 4 1 12340 6 2 1 5 }
id-at-mailAlternateAddress OBJECT IDENTIFIER ::= { 1 3 6 1 4 1 12340 6 2 1 6 }
id-at-deliveryMode OBJECT IDENTIFIER ::= { 1 3 6 1 4 1 12340 6 2 1 7 }
id-at-accountStatus OBJECT IDENTIFIER ::= { 1 3 6 1 4 1 12340 6 2 1 8 }
id-oc-dbmailUser OBJECT IDENTIFIER ::= { 1 3 6 1 4 1 12340 6 2 2 1 }
id-oc-dbmailForwardingAddress OBJECT IDENTIFIER ::= { 1 3 6 1 4 1 12340 6 2 2 2 }

-- Attribute types

mailQuota ATTRIBUTE ::= {
  WITH SYNTAX               PrintableString
  SINGLE VALUE              TRUE
  LDAP-SYNTAX               printableString.&id
  LDAP-NAME                 {"mailQuota"}
  LDAP-DESC                 "The amount of space the user can use until all further messages get bounced."
  ID                        id-at-mailQuota }

mailForwardingAddress ATTRIBUTE ::= {
  WITH SYNTAX               IA5String
  EQUALITY MATCHING RULE    caseIgnoreIA5Match
  LDAP-SYNTAX               ia5String.&id
  LDAP-NAME                 {"mailForwardingAddress"}
  LDAP-DESC                 "Address(es) to forward all incoming messages to."
  ID                        id-at-mailForwardingAddress }

mailHost ATTRIBUTE ::= {
  WITH SYNTAX               IA5String
  EQUALITY MATCHING RULE    caseIgnoreIA5Match
  LDAP-SYNTAX               ia5String.&id
  LDAP-NAME                 {"mailHost"}
  LDAP-DESC                 "Name or address of the MTA host to use for recipient"
  ID                        id-at-mailHost }

dbmailUID ATTRIBUTE ::= {
  WITH SYNTAX               IA5String
  EQUALITY MATCHING RULE    caseIgnoreIA5Match
  SUBSTRINGS MATCHING RULE  caseIgnoreIA5SubstringsMatch
  SINGLE VALUE              TRUE
  LDAP-SYNTAX               ia5String.&id
  LDAP-NAME                 {"dbmailUID"}
  LDAP-DESC                 "UID of the user on the mailsystem"
  ID                        id-at-dbmailUID }

dbmailGID ATTRIBUTE ::= {
  WITH SYNTAX               IA5String
  EQUALITY MATCHING RULE    caseIgnoreIA5Match
  SUBSTRINGS MATCHING RULE  caseIgnoreIA5SubstringsMatch
  SINGLE VALUE              TRUE
  LDAP-SYNTAX               ia5String.&id
  LDAP-NAME                 {"dbmailGID"}
  LDAP-DESC                 "GID of the user on the mailsystem"
  ID                        id-at-dbmailGID }

mailAlternateAddress ATTRIBUTE ::= {
  WITH SYNTAX               IA5String(SIZE (1..256))
  EQUALITY MATCHING RULE    caseIgnoreIA5Match
  LDAP-SYNTAX               ia5String.&id
  LDAP-NAME                 {"mailAlternateAddress"}
  LDAP-DESC                 "Secondary (alias) mailaddresses for the same user"
  ID                        id-at-mailAlternateAddress }

deliveryMode ATTRIBUTE ::= {
  WITH SYNTAX               PrintableString
  EQUALITY MATCHING RULE    caseIgnoreMatch
  SINGLE VALUE              TRUE
  LDAP-SYNTAX               printableString.&id
  LDAP-NAME                 {"deliveryMode"}
  LDAP-DESC                 "multi field entries of: normal, forwardonly"
  ID                        id-at-deliveryMode }

accountStatus ATTRIBUTE ::= {
  WITH SYNTAX               PrintableString
  EQUALITY MATCHING RULE    caseIgnoreMatch
  SINGLE VALUE              TRUE
  LDAP-SYNTAX               printableString.&id
  LDAP-NAME                 {"accountStatus"}
  LDAP-DESC                 "The status of a user account: active, disabled"
  ID                        id-at-accountStatus }

-- Object classes

dbmailUser OBJECT-CLASS ::= {
  SUBCLASS OF               { top }
  KIND                      auxiliary
  MUST CONTAIN              { uid
                              | mail }
  MAY CONTAIN               { userPassword
                              | uidNumber
                              | gidNumber
                              | mailQuota
                              | mailForwardingAddress
                              | mailHost
                              | mailAlternateAddress
                              | dbmailUID
                              | dbmailGID
                              | deliveryMode
                              | accountStatus }
  LDAP-NAME                 {"dbmailUser"}
  LDAP-DESC                 "DBMail-LDAP User"
  ID                        id-oc-dbmailUser }

dbmailForwardingAddress OBJECT-CLASS ::= {
  SUBCLASS OF               { top }
  KIND                      auxiliary
  MUST CONTAIN              { mail
                              | mailForwardingAddress }
  LDAP-NAME                 {"dbmailForwardingAddress"}
  LDAP-DESC                 "DBMail-LDAP Forwarding Address"
  ID                        id-oc-dbmailForwardingAddress }
END
