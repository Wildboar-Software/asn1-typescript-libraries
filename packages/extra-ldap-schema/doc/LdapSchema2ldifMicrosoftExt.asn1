-- Derived from data/ldap-schema/schema2ldif/microsoft.ext.schema
-- This module is a container for LDAP schema. It has no module identifier.
-- X- extension fields from the LDAP schema are comments. USAGE userApplications and structural KIND are omitted because they are the defaults.
LdapSchema2ldifMicrosoftExt DEFINITIONS ::=
BEGIN

IMPORTS

  CONTENT-RULE
    FROM InformationFramework
      {joint-iso-itu-t ds(5) module(1) informationFramework(1) 9} WITH SUCCESSORS

  group, user
    FROM MSUser
      {iso(1) identified-organization(3) dod(6) internet(1) private(4) enterprise(1) wildboar(56490) module(1) msuser(26)} WITH SUCCESSORS

  builtinDomain, contact, domainDNS, mailRecipient, remoteMailRecipient,
    samDomain, samDomainBase, securityPrincipal
    FROM LdapSchema2ldifMicrosoft ;

-- Object identifiers

id-cr-remoteMailRecipient OBJECT IDENTIFIER ::= { 1 2 840 113556 1 5 24 }
id-cr-domainDNS OBJECT IDENTIFIER ::= { 1 2 840 113556 1 5 67 }
id-cr-samDomain OBJECT IDENTIFIER ::= { 1 2 840 113556 1 5 3 }
id-cr-contact OBJECT IDENTIFIER ::= { 1 2 840 113556 1 5 15 }
id-cr-group OBJECT IDENTIFIER ::= { 1 2 840 113556 1 5 8 }
id-cr-user OBJECT IDENTIFIER ::= { 1 2 840 113556 1 5 9 }
id-cr-builtinDomain OBJECT IDENTIFIER ::= { 1 2 840 113556 1 5 4 }

-- DIT content rules

-- valuereference suffixed -rule so it does not hide object class remoteMailRecipient, which this module imports
remoteMailRecipient-rule CONTENT-RULE ::= {
  STRUCTURAL OBJECT-CLASS   remoteMailRecipient.&id
  AUXILIARY OBJECT-CLASSES  { mailRecipient } }

-- valuereference suffixed -rule so it does not hide object class domainDNS, which this module imports
domainDNS-rule CONTENT-RULE ::= {
  STRUCTURAL OBJECT-CLASS   domainDNS.&id
  AUXILIARY OBJECT-CLASSES  { samDomain } }

-- valuereference suffixed -rule so it does not hide object class samDomain, which this module imports
samDomain-rule CONTENT-RULE ::= {
  STRUCTURAL OBJECT-CLASS   samDomain.&id
  AUXILIARY OBJECT-CLASSES  { samDomainBase } }

-- valuereference suffixed -rule so it does not hide object class contact, which this module imports
contact-rule CONTENT-RULE ::= {
  STRUCTURAL OBJECT-CLASS   contact.&id
  AUXILIARY OBJECT-CLASSES  { mailRecipient } }

-- valuereference suffixed -rule so it does not hide object class group, which this module imports
group-rule CONTENT-RULE ::= {
  STRUCTURAL OBJECT-CLASS   group.&id
  AUXILIARY OBJECT-CLASSES  { securityPrincipal
                              | mailRecipient } }

-- valuereference suffixed -rule so it does not hide object class user, which this module imports
user-rule CONTENT-RULE ::= {
  STRUCTURAL OBJECT-CLASS   user.&id
  AUXILIARY OBJECT-CLASSES  { mailRecipient
                              | securityPrincipal } }

-- valuereference suffixed -rule so it does not hide object class builtinDomain, which this module imports
builtinDomain-rule CONTENT-RULE ::= {
  STRUCTURAL OBJECT-CLASS   builtinDomain.&id
  AUXILIARY OBJECT-CLASSES  { samDomainBase } }
END
