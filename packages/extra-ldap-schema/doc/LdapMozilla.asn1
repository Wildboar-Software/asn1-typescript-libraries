-- Derived from data/ldap-schema/mozilla.ldif
-- Upstream: https://github.com/389ds/389-ds-base/blob/main/ldap/schema/60mozilla.ldif
-- This module is a container for LDAP schema. It has no module identifier.
-- X- extension fields from the LDAP schema are comments. USAGE userApplications and structural KIND are omitted because they are the defaults.
-- LDAP {length} bounds on directory strings are DirectoryString{n}. Bounds on IA5String, PrintableString, NumericString, and OCTET STRING are SIZE (1..n). Other bounds stay comments because the LDAP figure is an encoded-length hint.
LdapMozilla DEFINITIONS ::=
BEGIN

IMPORTS

  ATTRIBUTE, OBJECT-CLASS, top
    FROM InformationFramework
      {joint-iso-itu-t ds(5) module(1) informationFramework(1) 9} WITH SUCCESSORS

  boolean, caseIgnoreIA5Match, caseIgnoreIA5SubstringsMatch, caseIgnoreMatch,
    caseIgnoreSubstringsMatch, commonName, countryName, description,
    directoryString, DirectoryString, facsimileTelephoneNumber, givenName,
    ia5String, localityName, organizationalUnitName, organizationName,
    postalCode, postOfficeBox, stateOrProvinceName, streetAddress, surname,
    telephoneNr, telephoneNumber, TelephoneNumber, telephoneNumberMatch,
    telephoneNumberSubstringsMatch, title
    FROM SelectedAttributeTypes
      {joint-iso-itu-t ds(5) module(1) selectedAttributeTypes(5) 9} WITH SUCCESSORS

  displayName
    FROM InetOrgPerson
      {iso(1) identified-organization(3) dod(6) internet(1) private(4) enterprise(1) wildboar(56490) module(1) inetorgperson(5)} WITH SUCCESSORS

  mail
    FROM LdapSchema2ldifCore

  homePhone, mobile, pager
    FROM LdapSchema2ldifCosine ;

-- Object identifiers

id-at-mozillaCustom1 OBJECT IDENTIFIER ::= { 1 3 6 1 4 1 13769 4 1 }
id-at-mozillaCustom2 OBJECT IDENTIFIER ::= { 1 3 6 1 4 1 13769 4 2 }
id-at-mozillaCustom3 OBJECT IDENTIFIER ::= { 1 3 6 1 4 1 13769 4 3 }
id-at-mozillaCustom4 OBJECT IDENTIFIER ::= { 1 3 6 1 4 1 13769 4 4 }
id-at-mozillaHomeStreet OBJECT IDENTIFIER ::= { 1 3 6 1 4 1 13769 3 1 }
id-at-mozillaHomeStreet2 OBJECT IDENTIFIER ::= { 1 3 6 1 4 1 13769 3 2 }
id-at-mozillaHomeLocalityName OBJECT IDENTIFIER ::= { 1 3 6 1 4 1 13769 3 3 }
id-at-mozillaHomeState OBJECT IDENTIFIER ::= { 1 3 6 1 4 1 13769 3 4 }
id-at-mozillaHomePostalCode OBJECT IDENTIFIER ::= { 1 3 6 1 4 1 13769 3 5 }
id-at-mozillaHomeCountryName OBJECT IDENTIFIER ::= { 1 3 6 1 4 1 13769 3 6 }
id-at-mozillaHomeUrl OBJECT IDENTIFIER ::= { 1 3 6 1 4 1 13769 3 7 }
id-at-mozillaWorkStreet2 OBJECT IDENTIFIER ::= { 1 3 6 1 4 1 13769 3 8 }
id-at-mozillaWorkUrl OBJECT IDENTIFIER ::= { 1 3 6 1 4 1 13769 3 9 }
id-at-mozillaNickname OBJECT IDENTIFIER ::= { 1 3 6 1 4 1 13769 2 1 }
id-at-mozillaSecondEmail OBJECT IDENTIFIER ::= { 1 3 6 1 4 1 13769 2 2 }
id-at-mozillaUseHtmlMail OBJECT IDENTIFIER ::= { 1 3 6 1 4 1 13769 2 3 }
id-at-nsAIMid OBJECT IDENTIFIER ::= { 1 3 6 1 4 1 13769 2 4 }
id-oc-mozillaAbPersonAlpha OBJECT IDENTIFIER ::= { 1 3 6 1 4 1 13769 9 1 }

-- Attribute types

-- X-ORIGIN: "Mozilla Address Book"
-- LDAP syntax length {128} rendered as DirectoryString{128}.
mozillaCustom1 ATTRIBUTE ::= {
  WITH SYNTAX               DirectoryString{128}
  EQUALITY MATCHING RULE    caseIgnoreMatch
  SUBSTRINGS MATCHING RULE  caseIgnoreSubstringsMatch
  SINGLE VALUE              TRUE
  LDAP-SYNTAX               directoryString.&id
  LDAP-NAME                 {"mozillaCustom1"}
  ID                        id-at-mozillaCustom1 }

-- X-ORIGIN: "Mozilla Address Book"
-- LDAP syntax length {128} rendered as DirectoryString{128}.
mozillaCustom2 ATTRIBUTE ::= {
  WITH SYNTAX               DirectoryString{128}
  EQUALITY MATCHING RULE    caseIgnoreMatch
  SUBSTRINGS MATCHING RULE  caseIgnoreSubstringsMatch
  SINGLE VALUE              TRUE
  LDAP-SYNTAX               directoryString.&id
  LDAP-NAME                 {"mozillaCustom2"}
  ID                        id-at-mozillaCustom2 }

-- X-ORIGIN: "Mozilla Address Book"
-- LDAP syntax length {128} rendered as DirectoryString{128}.
mozillaCustom3 ATTRIBUTE ::= {
  WITH SYNTAX               DirectoryString{128}
  EQUALITY MATCHING RULE    caseIgnoreMatch
  SUBSTRINGS MATCHING RULE  caseIgnoreSubstringsMatch
  SINGLE VALUE              TRUE
  LDAP-SYNTAX               directoryString.&id
  LDAP-NAME                 {"mozillaCustom3"}
  ID                        id-at-mozillaCustom3 }

-- X-ORIGIN: "Mozilla Address Book"
-- LDAP syntax length {128} rendered as DirectoryString{128}.
mozillaCustom4 ATTRIBUTE ::= {
  WITH SYNTAX               DirectoryString{128}
  EQUALITY MATCHING RULE    caseIgnoreMatch
  SUBSTRINGS MATCHING RULE  caseIgnoreSubstringsMatch
  SINGLE VALUE              TRUE
  LDAP-SYNTAX               directoryString.&id
  LDAP-NAME                 {"mozillaCustom4"}
  ID                        id-at-mozillaCustom4 }

-- X-ORIGIN: "Mozilla Address Book"
-- LDAP syntax length {128} rendered as DirectoryString{128}.
mozillaHomeStreet ATTRIBUTE ::= {
  WITH SYNTAX               DirectoryString{128}
  EQUALITY MATCHING RULE    caseIgnoreMatch
  SUBSTRINGS MATCHING RULE  caseIgnoreSubstringsMatch
  SINGLE VALUE              TRUE
  LDAP-SYNTAX               directoryString.&id
  LDAP-NAME                 {"mozillaHomeStreet"}
  ID                        id-at-mozillaHomeStreet }

-- X-ORIGIN: "Mozilla Address Book"
-- LDAP syntax length {128} rendered as DirectoryString{128}.
mozillaHomeStreet2 ATTRIBUTE ::= {
  WITH SYNTAX               DirectoryString{128}
  EQUALITY MATCHING RULE    caseIgnoreMatch
  SUBSTRINGS MATCHING RULE  caseIgnoreSubstringsMatch
  SINGLE VALUE              TRUE
  LDAP-SYNTAX               directoryString.&id
  LDAP-NAME                 {"mozillaHomeStreet2"}
  ID                        id-at-mozillaHomeStreet2 }

-- X-ORIGIN: "Mozilla Address Book"
-- This attribute declares neither a supertype nor a syntax.
mozillaHomeLocalityName ATTRIBUTE ::= {
  LDAP-NAME                 {"mozillaHomeLocalityName", "SINGLE-VALUE"}
  ID                        id-at-mozillaHomeLocalityName }

-- X-ORIGIN: "Mozilla Address Book"
-- This attribute declares neither a supertype nor a syntax.
mozillaHomeState ATTRIBUTE ::= {
  LDAP-NAME                 {"mozillaHomeState", "SINGLE-VALUE"}
  ID                        id-at-mozillaHomeState }

-- X-ORIGIN: "Mozilla Address Book"
-- LDAP syntax length {40} rendered as DirectoryString{40}.
mozillaHomePostalCode ATTRIBUTE ::= {
  WITH SYNTAX               DirectoryString{40}
  EQUALITY MATCHING RULE    caseIgnoreMatch
  SUBSTRINGS MATCHING RULE  caseIgnoreSubstringsMatch
  SINGLE VALUE              TRUE
  LDAP-SYNTAX               directoryString.&id
  LDAP-NAME                 {"mozillaHomePostalCode"}
  ID                        id-at-mozillaHomePostalCode }

-- X-ORIGIN: "Mozilla Address Book"
-- This attribute declares neither a supertype nor a syntax.
mozillaHomeCountryName ATTRIBUTE ::= {
  LDAP-NAME                 {"mozillaHomeCountryName", "SINGLE-VALUE"}
  ID                        id-at-mozillaHomeCountryName }

-- X-ORIGIN: "Mozilla Address Book"
-- LDAP syntax length {128} rendered as DirectoryString{128}.
mozillaHomeUrl ATTRIBUTE ::= {
  WITH SYNTAX               DirectoryString{128}
  EQUALITY MATCHING RULE    caseIgnoreMatch
  SINGLE VALUE              TRUE
  LDAP-SYNTAX               directoryString.&id
  LDAP-NAME                 {"mozillaHomeUrl"}
  ID                        id-at-mozillaHomeUrl }

-- X-ORIGIN: "Mozilla Address Book"
-- LDAP syntax length {128} rendered as DirectoryString{128}.
mozillaWorkStreet2 ATTRIBUTE ::= {
  WITH SYNTAX               DirectoryString{128}
  EQUALITY MATCHING RULE    caseIgnoreMatch
  SUBSTRINGS MATCHING RULE  caseIgnoreSubstringsMatch
  SINGLE VALUE              TRUE
  LDAP-SYNTAX               directoryString.&id
  LDAP-NAME                 {"mozillaWorkStreet2"}
  ID                        id-at-mozillaWorkStreet2 }

-- X-ORIGIN: "Mozilla Address Book"
-- LDAP syntax length {128} rendered as DirectoryString{128}.
mozillaWorkUrl ATTRIBUTE ::= {
  WITH SYNTAX               DirectoryString{128}
  EQUALITY MATCHING RULE    caseIgnoreMatch
  SINGLE VALUE              TRUE
  LDAP-SYNTAX               directoryString.&id
  LDAP-NAME                 {"mozillaWorkUrl"}
  ID                        id-at-mozillaWorkUrl }

-- This attribute declares neither a supertype nor a syntax.
mozillaNickname ATTRIBUTE ::= {
  LDAP-NAME                 {"mozillaNickname", "xmozillanickname", "X-ORIGIN"}
  ID                        id-at-mozillaNickname }

-- X-ORIGIN: "Mozilla Address Book"
mozillaSecondEmail ATTRIBUTE ::= {
  WITH SYNTAX               IA5String(SIZE (1..256))
  EQUALITY MATCHING RULE    caseIgnoreIA5Match
  SUBSTRINGS MATCHING RULE  caseIgnoreIA5SubstringsMatch
  SINGLE VALUE              TRUE
  LDAP-SYNTAX               ia5String.&id
  LDAP-NAME                 {"mozillaSecondEmail", "xmozillasecondemail"}
  ID                        id-at-mozillaSecondEmail }

-- X-ORIGIN: "Mozilla Address Book"
mozillaUseHtmlMail ATTRIBUTE ::= {
  WITH SYNTAX               BOOLEAN
  SINGLE VALUE              TRUE
  LDAP-SYNTAX               boolean.&id
  LDAP-NAME                 {"mozillaUseHtmlMail", "xmozillausehtmlmail"}
  ID                        id-at-mozillaUseHtmlMail }

-- X-ORIGIN: "Mozilla Address Book"
nsAIMid ATTRIBUTE ::= {
  WITH SYNTAX               TelephoneNumber
  EQUALITY MATCHING RULE    telephoneNumberMatch
  SUBSTRINGS MATCHING RULE  telephoneNumberSubstringsMatch
  LDAP-SYNTAX               telephoneNr.&id
  LDAP-NAME                 {"nsAIMid", "nscpaimscreenname"}
  ID                        id-at-nsAIMid }

-- Object classes

-- X-ORIGIN: "Mozilla Address Book"
mozillaAbPersonAlpha OBJECT-CLASS ::= {
  SUBCLASS OF               { top }
  KIND                      auxiliary
  MUST CONTAIN              { commonName }
  MAY CONTAIN               { countryName
                              | description
                              | displayName
                              | facsimileTelephoneNumber
                              | givenName
                              | homePhone
                              | localityName
                              | mail
                              | mobile
                              | mozillaCustom1
                              | mozillaCustom2
                              | mozillaCustom3
                              | mozillaCustom4
                              | mozillaHomeCountryName
                              | mozillaHomeLocalityName
                              | mozillaHomePostalCode
                              | mozillaHomeState
                              | mozillaHomeStreet
                              | mozillaHomeStreet2
                              | mozillaHomeUrl
                              | mozillaNickname
                              | mozillaSecondEmail
                              | mozillaUseHtmlMail
                              | mozillaWorkStreet2
                              | mozillaWorkUrl
                              | nsAIMid
                              | organizationName
                              | organizationalUnitName
                              | pager
                              | postalCode
                              | postOfficeBox
                              | surname
                              | stateOrProvinceName
                              | streetAddress
                              | telephoneNumber
                              | title }
  LDAP-NAME                 {"mozillaAbPersonAlpha"}
  ID                        id-oc-mozillaAbPersonAlpha }
END
