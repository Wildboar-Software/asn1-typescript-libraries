-- Derived from data/ldap-schema/eregansu.schema
-- Upstream: https://github.com/nexgenta/eregansu/blob/bf7fb05e365e7106fcfdc84376e77f0acc61b467/identity.schema#L13
-- This module is a container for LDAP schema. It has no module identifier.
-- X- extension fields from the LDAP schema are comments. USAGE userApplications and structural KIND are omitted because they are the defaults.
-- Object classes with no SUP were subclassed from top, the LDAP default (RFC 4512).
LdapEregansu DEFINITIONS ::=
BEGIN

IMPORTS

  ATTRIBUTE, OBJECT-CLASS, top
    FROM InformationFramework
      {joint-iso-itu-t ds(5) module(1) informationFramework(1) 9} WITH SUCCESSORS

  caseExactMatch, directoryString, generationQualifier, givenName, initials,
    surname, uid, UnboundedDirectoryString
    FROM SelectedAttributeTypes
      {joint-iso-itu-t ds(5) module(1) selectedAttributeTypes(5) 9} WITH SUCCESSORS

  cACertificate, userCertificate, userPassword
    FROM AuthenticationFramework
      {joint-iso-itu-t ds(5) module(1) authenticationFramework(7) 9} WITH SUCCESSORS

  mail
    FROM LdapSchema2ldifCore

  photo
    FROM LdapSchema2ldifCosine ;

-- Object identifiers

id-at-userIRI OBJECT IDENTIFIER ::= { 1 3 6 1 4 1 27678 2 11 }
id-at-userPermission OBJECT IDENTIFIER ::= { 1 3 6 1 4 1 27678 2 12 }
id-oc-userIdentity OBJECT IDENTIFIER ::= { 1 3 6 1 4 1 27678 3 1 }

-- Attribute types

userIRI ATTRIBUTE ::= {
  WITH SYNTAX               UnboundedDirectoryString
  EQUALITY MATCHING RULE    caseExactMatch
  LDAP-SYNTAX               directoryString.&id
  LDAP-NAME                 {"userIRI"}
  ID                        id-at-userIRI }

userPermission ATTRIBUTE ::= {
  WITH SYNTAX               UnboundedDirectoryString
  EQUALITY MATCHING RULE    caseExactMatch
  LDAP-SYNTAX               directoryString.&id
  LDAP-NAME                 {"userPermission"}
  ID                        id-at-userPermission }

-- Object classes

-- SUP was absent. RFC 4512 treats that as a subclass of top, so SUBCLASS OF { top } was added.
userIdentity OBJECT-CLASS ::= {
  SUBCLASS OF               { top }
  KIND                      auxiliary
  MUST CONTAIN              { uid
                              | userIRI }
  MAY CONTAIN               { userPermission
                              | givenName
                              | surname
                              | initials
                              | generationQualifier
                              | userPassword
                              | userCertificate
                              | cACertificate
                              | mail
                              | photo }
  LDAP-NAME                 {"userIdentity"}
  LDAP-DESC                 "Eregansu user identity"
  ID                        id-oc-userIdentity }
END
