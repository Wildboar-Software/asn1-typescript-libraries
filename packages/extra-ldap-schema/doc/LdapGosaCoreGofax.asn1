-- Derived from data/ldap-schema/gosa-core/gofax.schema
-- This module is a container for LDAP schema. It has no module identifier.
-- X- extension fields from the LDAP schema are comments. USAGE userApplications and structural KIND are omitted because they are the defaults.
-- Object classes with no SUP were subclassed from top, the LDAP default (RFC 4512).
-- LDAP {length} bounds on directory strings are DirectoryString{n}. Bounds on IA5String, PrintableString, NumericString, and OCTET STRING are SIZE (1..n). Other bounds stay comments because the LDAP figure is an encoded-length hint.
LdapGosaCoreGofax DEFINITIONS ::=
BEGIN

IMPORTS

  ATTRIBUTE, OBJECT-CLASS, top
    FROM InformationFramework
      {joint-iso-itu-t ds(5) module(1) informationFramework(1) 9} WITH SUCCESSORS

  caseExactIA5Match, commonName, description, facsimileTelephoneNr,
    facsimileTelephoneNumber, FacsimileTelephoneNumber, ia5String, telephoneNr,
    TelephoneNumber, telephoneNumberMatch, telephoneNumberSubstringsMatch, uid
    FROM SelectedAttributeTypes
      {joint-iso-itu-t ds(5) module(1) selectedAttributeTypes(5) 9} WITH SUCCESSORS

  caseExactIA5SubstringsMatch
    FROM OpenLDAP
      {iso(1) identified-organization(3) dod(6) internet(1) private(4) enterprise(1) wildboar(56490) module(1) openldap(28)} WITH SUCCESSORS

  mail
    FROM LdapSchema2ldifCore ;

-- Object identifiers

id-at-goFaxDeliveryMode OBJECT IDENTIFIER ::= { 1 3 6 1 4 1 10098 1 1 7 1 }
id-at-goFaxPrinter OBJECT IDENTIFIER ::= { 1 3 6 1 4 1 10098 1 1 7 2 }
id-at-goFaxDivertNumber OBJECT IDENTIFIER ::= { 1 3 6 1 4 1 10098 1 1 7 3 }
id-at-goFaxLanguage OBJECT IDENTIFIER ::= { 1 3 6 1 4 1 10098 1 1 7 4 }
id-at-goFaxFormat OBJECT IDENTIFIER ::= { 1 3 6 1 4 1 10098 1 1 7 5 }
id-at-goFaxRBlocklist OBJECT IDENTIFIER ::= { 1 3 6 1 4 1 10098 1 1 7 6 }
id-at-goFaxSBlocklist OBJECT IDENTIFIER ::= { 1 3 6 1 4 1 10098 1 1 7 8 }
id-at-goFaxRBlockgroups OBJECT IDENTIFIER ::= { 1 3 6 1 4 1 10098 1 1 7 7 }
id-at-goFaxSBlockgroups OBJECT IDENTIFIER ::= { 1 3 6 1 4 1 10098 1 1 7 9 }
id-at-goFaxIsEnabled OBJECT IDENTIFIER ::= { 1 3 6 1 4 1 10098 1 1 7 10 }
id-at-facsimileAlternateTelephoneNumber OBJECT IDENTIFIER ::= { 1 3 6 1 4 1 10098 1 1 7 11 }
id-oc-goFaxAccount OBJECT IDENTIFIER ::= { 1 3 6 1 4 1 10098 1 2 1 11 }
id-oc-goFaxSBlock OBJECT IDENTIFIER ::= { 1 3 6 1 4 1 10098 1 2 1 12 }
id-oc-goFaxRBlock OBJECT IDENTIFIER ::= { 1 3 6 1 4 1 10098 1 2 1 13 }

-- Attribute types

goFaxDeliveryMode ATTRIBUTE ::= {
  WITH SYNTAX               IA5String
  EQUALITY MATCHING RULE    caseExactIA5Match
  SUBSTRINGS MATCHING RULE  caseExactIA5SubstringsMatch
  SINGLE VALUE              TRUE
  LDAP-SYNTAX               ia5String.&id
  LDAP-NAME                 {"goFaxDeliveryMode"}
  LDAP-DESC                 "goFax delivery mode is defined here"
  ID                        id-at-goFaxDeliveryMode }

goFaxPrinter ATTRIBUTE ::= {
  WITH SYNTAX               IA5String
  EQUALITY MATCHING RULE    caseExactIA5Match
  SUBSTRINGS MATCHING RULE  caseExactIA5SubstringsMatch
  SINGLE VALUE              TRUE
  LDAP-SYNTAX               ia5String.&id
  LDAP-NAME                 {"goFaxPrinter"}
  LDAP-DESC                 "defines which printer is used to print a fax"
  ID                        id-at-goFaxPrinter }

goFaxDivertNumber ATTRIBUTE ::= {
  WITH SYNTAX               FacsimileTelephoneNumber
  SINGLE VALUE              TRUE
  LDAP-SYNTAX               facsimileTelephoneNr.&id
  LDAP-NAME                 {"goFaxDivertNumber"}
  LDAP-DESC                 "for fax diversion services"
  ID                        id-at-goFaxDivertNumber }

goFaxLanguage ATTRIBUTE ::= {
  WITH SYNTAX               IA5String
  EQUALITY MATCHING RULE    caseExactIA5Match
  SUBSTRINGS MATCHING RULE  caseExactIA5SubstringsMatch
  SINGLE VALUE              TRUE
  LDAP-SYNTAX               ia5String.&id
  LDAP-NAME                 {"goFaxLanguage"}
  LDAP-DESC                 "preferred language for the users goFax entry"
  ID                        id-at-goFaxLanguage }

goFaxFormat ATTRIBUTE ::= {
  WITH SYNTAX               IA5String
  EQUALITY MATCHING RULE    caseExactIA5Match
  SUBSTRINGS MATCHING RULE  caseExactIA5SubstringsMatch
  SINGLE VALUE              TRUE
  LDAP-SYNTAX               ia5String.&id
  LDAP-NAME                 {"goFaxFormat"}
  LDAP-DESC                 "defines the fileformat for mailattachments"
  ID                        id-at-goFaxFormat }

goFaxRBlocklist ATTRIBUTE ::= {
  WITH SYNTAX               IA5String
  EQUALITY MATCHING RULE    caseExactIA5Match
  LDAP-SYNTAX               ia5String.&id
  LDAP-NAME                 {"goFaxRBlocklist"}
  LDAP-DESC                 "defines faxnumbers the user is not allowed to get fax from"
  ID                        id-at-goFaxRBlocklist }

goFaxSBlocklist ATTRIBUTE ::= {
  WITH SYNTAX               IA5String
  EQUALITY MATCHING RULE    caseExactIA5Match
  LDAP-SYNTAX               ia5String.&id
  LDAP-NAME                 {"goFaxSBlocklist"}
  LDAP-DESC                 "defines faxnumbers the user is not allowed to fax to"
  ID                        id-at-goFaxSBlocklist }

goFaxRBlockgroups ATTRIBUTE ::= {
  WITH SYNTAX               IA5String
  EQUALITY MATCHING RULE    caseExactIA5Match
  SUBSTRINGS MATCHING RULE  caseExactIA5SubstringsMatch
  LDAP-SYNTAX               ia5String.&id
  LDAP-NAME                 {"goFaxRBlockgroups"}
  LDAP-DESC                 "defines groups of receive blocklists the user belongs to"
  ID                        id-at-goFaxRBlockgroups }

goFaxSBlockgroups ATTRIBUTE ::= {
  WITH SYNTAX               IA5String
  EQUALITY MATCHING RULE    caseExactIA5Match
  SUBSTRINGS MATCHING RULE  caseExactIA5SubstringsMatch
  LDAP-SYNTAX               ia5String.&id
  LDAP-NAME                 {"goFaxSBlockgroups"}
  LDAP-DESC                 "defines groups of sender blocklists the user belongs to"
  ID                        id-at-goFaxSBlockgroups }

goFaxIsEnabled ATTRIBUTE ::= {
  WITH SYNTAX               IA5String
  EQUALITY MATCHING RULE    caseExactIA5Match
  SUBSTRINGS MATCHING RULE  caseExactIA5SubstringsMatch
  SINGLE VALUE              TRUE
  LDAP-SYNTAX               ia5String.&id
  LDAP-NAME                 {"goFaxIsEnabled"}
  LDAP-DESC                 "This account is enabled or not"
  ID                        id-at-goFaxIsEnabled }

-- LDAP syntax length {32} kept as a comment only; it is an encoded-length hint, not a value constraint.
facsimileAlternateTelephoneNumber ATTRIBUTE ::= {
  WITH SYNTAX               TelephoneNumber
  EQUALITY MATCHING RULE    telephoneNumberMatch
  SUBSTRINGS MATCHING RULE  telephoneNumberSubstringsMatch
  LDAP-SYNTAX               telephoneNr.&id
  LDAP-NAME                 {"facsimileAlternateTelephoneNumber"}
  ID                        id-at-facsimileAlternateTelephoneNumber }

-- Object classes

goFaxAccount OBJECT-CLASS ::= {
  SUBCLASS OF               { top }
  KIND                      auxiliary
  MUST CONTAIN              { goFaxDeliveryMode
                              | facsimileTelephoneNumber
                              | uid
                              | goFaxIsEnabled }
  MAY CONTAIN               { goFaxPrinter
                              | goFaxDivertNumber
                              | goFaxLanguage
                              | goFaxFormat
                              | goFaxRBlocklist
                              | goFaxRBlockgroups
                              | goFaxSBlocklist
                              | goFaxSBlockgroups
                              | mail
                              | facsimileAlternateTelephoneNumber }
  LDAP-NAME                 {"goFaxAccount"}
  LDAP-DESC                 "goFax Account objectclass (v1.0.4)"
  ID                        id-oc-goFaxAccount }

-- SUP was absent. RFC 4512 treats that as a subclass of top, so SUBCLASS OF { top } was added.
goFaxSBlock OBJECT-CLASS ::= {
  SUBCLASS OF               { top }
  MUST CONTAIN              { commonName }
  MAY CONTAIN               { goFaxSBlocklist
                              | description }
  LDAP-NAME                 {"goFaxSBlock"}
  LDAP-DESC                 "goFax send blocklist groups (v1.0.4)"
  ID                        id-oc-goFaxSBlock }

-- SUP was absent. RFC 4512 treats that as a subclass of top, so SUBCLASS OF { top } was added.
goFaxRBlock OBJECT-CLASS ::= {
  SUBCLASS OF               { top }
  MUST CONTAIN              { commonName }
  MAY CONTAIN               { goFaxRBlocklist
                              | description }
  LDAP-NAME                 {"goFaxRBlock"}
  LDAP-DESC                 "goFax receive blocklist groups (v1.0.4)"
  ID                        id-oc-goFaxRBlock }
END
