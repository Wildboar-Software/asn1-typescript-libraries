-- Derived from data/ldap-schema/glue/7-01-StorageService.schema
-- Upstream: http://redmine.ogf.org/projects/glue-wg
-- This module is a container for LDAP schema. It has no module identifier.
-- X- extension fields from the LDAP schema are comments. USAGE userApplications and structural KIND are omitted because they are the defaults.
LdapGlue701StorageService DEFINITIONS ::=
BEGIN

IMPORTS

  OBJECT-CLASS
    FROM InformationFramework
      {joint-iso-itu-t ds(5) module(1) informationFramework(1) 9} WITH SUCCESSORS

  gLUE2Service
    FROM LdapGlue506Service ;

-- Object identifiers

id-oc-gLUE2StorageService OBJECT IDENTIFIER ::= { 1 3 6 1 4 1 6757 100 1 1 27 }

-- Object classes

-- initial capital of "GLUE2StorageService" lowercased so the assignment is a valuereference.
gLUE2StorageService OBJECT-CLASS ::= {
  SUBCLASS OF               { gLUE2Service }
  LDAP-NAME                 {"GLUE2StorageService"}
  LDAP-DESC                 "Description of the size and state of an homogeneous storage extent"
  ID                        id-oc-gLUE2StorageService }
END
