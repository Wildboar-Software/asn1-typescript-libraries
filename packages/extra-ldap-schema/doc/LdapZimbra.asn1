-- Derived from data/ldap-schema/zimbra.schema
-- This module is a container for LDAP schema. It has no module identifier.
-- X- extension fields from the LDAP schema are comments. USAGE userApplications and structural KIND are omitted because they are the defaults.
-- 1 elements were omitted because their OIDs are already defined. See CONVERSION-REPORT.txt.
-- LDAP {length} bounds on directory strings are DirectoryString{n}. Bounds on IA5String, PrintableString, NumericString, and OCTET STRING are SIZE (1..n). Other bounds stay comments because the LDAP figure is an encoded-length hint.
LdapZimbra DEFINITIONS ::=
BEGIN

IMPORTS

  ATTRIBUTE, OBJECT-CLASS, top
    FROM InformationFramework
      {joint-iso-itu-t ds(5) module(1) informationFramework(1) 9} WITH SUCCESSORS

  boolean, booleanMatch, caseExactMatch, caseExactSubstringsMatch,
    caseIgnoreIA5Match, caseIgnoreMatch, caseIgnoreSubstringsMatch, commonName,
    countryName, description, destinationIndicator, directoryString,
    DirectoryString, facsimileTelephoneNumber, generalizedTime,
    generalizedTimeMatch, generalizedTimeOrderingMatch, givenName, ia5String,
    initials, integer, integerMatch, integerOrderingMatch,
    internationalISDNNumber, localityName, octetString, octetStringMatch,
    organizationalUnitName, organizationName, physicalDeliveryOfficeName,
    postalAddress, postalCode, postOfficeBox, preferredDeliveryMethod,
    registeredAddress, stateOrProvinceName, streetAddress, surname,
    telephoneNr, telephoneNumber, TelephoneNumber, telephoneNumberMatch,
    telephoneNumberSubstringsMatch, telexNumber, title, uid,
    UnboundedDirectoryString, x121Address
    FROM SelectedAttributeTypes
      {joint-iso-itu-t ds(5) module(1) selectedAttributeTypes(5) 9} WITH SUCCESSORS

  userCertificate, userPassword
    FROM AuthenticationFramework
      {joint-iso-itu-t ds(5) module(1) authenticationFramework(7) 9} WITH SUCCESSORS

  memberURL
    FROM DynGroup
      {iso(1) identified-organization(3) dod(6) internet(1) private(4) enterprise(1) wildboar(56490) module(1) dyngroup(24)} WITH SUCCESSORS

  userSMIMECertificate
    FROM H323-X500-Schema
      {iso(1) identified-organization(3) dod(6) internet(1) private(4) enterprise(1) wildboar(56490) module(1) h323-x500-schema(1000)} WITH SUCCESSORS

  displayName
    FROM InetOrgPerson
      {iso(1) identified-organization(3) dod(6) internet(1) private(4) enterprise(1) wildboar(56490) module(1) inetorgperson(5)} WITH SUCCESSORS

  company
    FROM MSUser
      {iso(1) identified-organization(3) dod(6) internet(1) private(4) enterprise(1) wildboar(56490) module(1) msuser(26)} WITH SUCCESSORS

  mail, teletexTerminalIdentifier
    FROM LdapSchema2ldifCore

  co, homePhone, mobile, pager
    FROM LdapSchema2ldifCosine ;

-- Object identifiers

id-at-zimbraACE OBJECT IDENTIFIER ::= { 1 3 6 1 4 1 19348 2 1 659 }
id-at-zimbraAccountCalendarUserType OBJECT IDENTIFIER ::= { 1 3 6 1 4 1 19348 2 1 313 }
id-at-zimbraAccountClientAttr OBJECT IDENTIFIER ::= { 1 3 6 1 4 1 19348 2 1 112 }
id-at-zimbraAccountExtraObjectClass OBJECT IDENTIFIER ::= { 1 3 6 1 4 1 19348 2 1 438 }
id-at-zimbraAccountStatus OBJECT IDENTIFIER ::= { 1 3 6 1 4 1 19348 2 1 2 }
id-at-zimbraAdminAccessControlMech OBJECT IDENTIFIER ::= { 1 3 6 1 4 1 19348 2 1 1101 }
id-at-zimbraAdminAuthTokenLifetime OBJECT IDENTIFIER ::= { 1 3 6 1 4 1 19348 2 1 109 }
id-at-zimbraAdminBindAddress OBJECT IDENTIFIER ::= { 1 3 6 1 4 1 19348 2 1 1368 }
id-at-zimbraAdminConsoleCatchAllAddressEnabled OBJECT IDENTIFIER ::= { 1 3 6 1 4 1 19348 2 1 746 }
id-at-zimbraAdminConsoleDNSCheckEnabled OBJECT IDENTIFIER ::= { 1 3 6 1 4 1 19348 2 1 743 }
id-at-zimbraAdminConsoleLDAPAuthEnabled OBJECT IDENTIFIER ::= { 1 3 6 1 4 1 19348 2 1 774 }
id-at-zimbraAdminConsoleLoginMessage OBJECT IDENTIFIER ::= { 1 3 6 1 4 1 19348 2 1 772 }
id-at-zimbraAdminConsoleLoginURL OBJECT IDENTIFIER ::= { 1 3 6 1 4 1 19348 2 1 696 }
id-at-zimbraAdminConsoleLogoutURL OBJECT IDENTIFIER ::= { 1 3 6 1 4 1 19348 2 1 684 }
id-at-zimbraAdminConsoleSkinEnabled OBJECT IDENTIFIER ::= { 1 3 6 1 4 1 19348 2 1 751 }
id-at-zimbraAdminConsoleUIComponents OBJECT IDENTIFIER ::= { 1 3 6 1 4 1 19348 2 1 761 }
id-at-zimbraAdminExtDisableUIUndeploy OBJECT IDENTIFIER ::= { 1 3 6 1 4 1 19348 2 1 803 }
id-at-zimbraAdminImapImportNumThreads OBJECT IDENTIFIER ::= { 1 3 6 1 4 1 19348 2 1 1113 }
id-at-zimbraAdminLocalBind OBJECT IDENTIFIER ::= { 1 3 6 1 4 1 19348 2 1 1377 }
id-at-zimbraAdminPort OBJECT IDENTIFIER ::= { 1 3 6 1 4 1 19348 2 1 155 }
id-at-zimbraAdminProxyPort OBJECT IDENTIFIER ::= { 1 3 6 1 4 1 19348 2 1 1322 }
id-at-zimbraAdminSavedSearches OBJECT IDENTIFIER ::= { 1 3 6 1 4 1 19348 2 1 446 }
id-at-zimbraAdminURL OBJECT IDENTIFIER ::= { 1 3 6 1 4 1 19348 2 1 497 }
id-at-zimbraAggregateQuotaLastUsage OBJECT IDENTIFIER ::= { 1 3 6 1 4 1 19348 2 1 1328 }
id-at-zimbraAliasTargetId OBJECT IDENTIFIER ::= { 1 3 6 1 4 1 19348 2 1 40 }
id-at-zimbraAllowAnyFromAddress OBJECT IDENTIFIER ::= { 1 3 6 1 4 1 19348 2 1 427 }
id-at-zimbraAllowFromAddress OBJECT IDENTIFIER ::= { 1 3 6 1 4 1 19348 2 1 428 }
id-at-zimbraAllowNonLDHCharsInDomain OBJECT IDENTIFIER ::= { 1 3 6 1 4 1 19348 2 1 1052 }
id-at-zimbraAlwaysOnClusterId OBJECT IDENTIFIER ::= { 1 3 6 1 4 1 19348 2 1 1446 }
id-at-zimbraAmavisDSPAMEnabled OBJECT IDENTIFIER ::= { 1 3 6 1 4 1 19348 2 1 1465 }
id-at-zimbraAmavisDomainDisclaimerHTML OBJECT IDENTIFIER ::= { 1 3 6 1 4 1 19348 2 1 1459 }
id-at-zimbraAmavisDomainDisclaimerText OBJECT IDENTIFIER ::= { 1 3 6 1 4 1 19348 2 1 1458 }
id-at-zimbraAmavisEnableDKIMVerification OBJECT IDENTIFIER ::= { 1 3 6 1 4 1 19348 2 1 1463 }
id-at-zimbraAmavisFinalSpamDestiny OBJECT IDENTIFIER ::= { 1 3 6 1 4 1 19348 2 1 1460 }
id-at-zimbraAmavisLogLevel OBJECT IDENTIFIER ::= { 1 3 6 1 4 1 19348 2 1 1488 }
id-at-zimbraAmavisMaxServers OBJECT IDENTIFIER ::= { 1 3 6 1 4 1 19348 2 1 1461 }
id-at-zimbraAmavisOriginatingBypassSA OBJECT IDENTIFIER ::= { 1 3 6 1 4 1 19348 2 1 1464 }
id-at-zimbraAmavisOutboundDisclaimersOnly OBJECT IDENTIFIER ::= { 1 3 6 1 4 1 19348 2 1 1577 }
id-at-zimbraAmavisQuarantineAccount OBJECT IDENTIFIER ::= { 1 3 6 1 4 1 19348 2 1 1100 }
id-at-zimbraAmavisSALogLevel OBJECT IDENTIFIER ::= { 1 3 6 1 4 1 19348 2 1 1578 }
id-at-zimbraAntispamExtractionBatchDelay OBJECT IDENTIFIER ::= { 1 3 6 1 4 1 19348 2 1 1457 }
id-at-zimbraAntispamExtractionBatchSize OBJECT IDENTIFIER ::= { 1 3 6 1 4 1 19348 2 1 1456 }
id-at-zimbraArchiveAccount OBJECT IDENTIFIER ::= { 1 3 6 1 4 1 19348 2 1 429 }
id-at-zimbraArchiveAccountDateTemplate OBJECT IDENTIFIER ::= { 1 3 6 1 4 1 19348 2 1 432 }
id-at-zimbraArchiveAccountNameTemplate OBJECT IDENTIFIER ::= { 1 3 6 1 4 1 19348 2 1 431 }
id-at-zimbraArchiveEnabled OBJECT IDENTIFIER ::= { 1 3 6 1 4 1 19348 2 1 1206 }
id-at-zimbraArchiveMailFrom OBJECT IDENTIFIER ::= { 1 3 6 1 4 1 19348 2 1 430 }
id-at-zimbraAttachmentsBlocked OBJECT IDENTIFIER ::= { 1 3 6 1 4 1 19348 2 1 115 }
id-at-zimbraAttachmentsIndexedTextLimit OBJECT IDENTIFIER ::= { 1 3 6 1 4 1 19348 2 1 582 }
id-at-zimbraAttachmentsIndexingEnabled OBJECT IDENTIFIER ::= { 1 3 6 1 4 1 19348 2 1 173 }
id-at-zimbraAttachmentsScanClass OBJECT IDENTIFIER ::= { 1 3 6 1 4 1 19348 2 1 238 }
id-at-zimbraAttachmentsScanEnabled OBJECT IDENTIFIER ::= { 1 3 6 1 4 1 19348 2 1 237 }
id-at-zimbraAttachmentsScanURL OBJECT IDENTIFIER ::= { 1 3 6 1 4 1 19348 2 1 239 }
id-at-zimbraAttachmentsViewInHtmlOnly OBJECT IDENTIFIER ::= { 1 3 6 1 4 1 19348 2 1 116 }
id-at-zimbraAuthFallbackToLocal OBJECT IDENTIFIER ::= { 1 3 6 1 4 1 19348 2 1 257 }
id-at-zimbraAuthKerberos5Realm OBJECT IDENTIFIER ::= { 1 3 6 1 4 1 19348 2 1 548 }
id-at-zimbraAuthLdapBindDn OBJECT IDENTIFIER ::= { 1 3 6 1 4 1 19348 2 1 44 }
id-at-zimbraAuthLdapExternalDn OBJECT IDENTIFIER ::= { 1 3 6 1 4 1 19348 2 1 256 }
id-at-zimbraAuthLdapSearchBase OBJECT IDENTIFIER ::= { 1 3 6 1 4 1 19348 2 1 252 }
id-at-zimbraAuthLdapSearchBindDn OBJECT IDENTIFIER ::= { 1 3 6 1 4 1 19348 2 1 253 }
id-at-zimbraAuthLdapSearchBindPassword OBJECT IDENTIFIER ::= { 1 3 6 1 4 1 19348 2 1 254 }
id-at-zimbraAuthLdapSearchFilter OBJECT IDENTIFIER ::= { 1 3 6 1 4 1 19348 2 1 255 }
id-at-zimbraAuthLdapStartTlsEnabled OBJECT IDENTIFIER ::= { 1 3 6 1 4 1 19348 2 1 654 }
id-at-zimbraAuthLdapURL OBJECT IDENTIFIER ::= { 1 3 6 1 4 1 19348 2 1 43 }
id-at-zimbraAuthMech OBJECT IDENTIFIER ::= { 1 3 6 1 4 1 19348 2 1 42 }
id-at-zimbraAuthMechAdmin OBJECT IDENTIFIER ::= { 1 3 6 1 4 1 19348 2 1 1252 }
id-at-zimbraAuthTokenKey OBJECT IDENTIFIER ::= { 1 3 6 1 4 1 19348 2 1 100 }
id-at-zimbraAuthTokenLifetime OBJECT IDENTIFIER ::= { 1 3 6 1 4 1 19348 2 1 108 }
id-at-zimbraAuthTokenNotificationInterval OBJECT IDENTIFIER ::= { 1 3 6 1 4 1 19348 2 1 1635 }
id-at-zimbraAuthTokenValidityValue OBJECT IDENTIFIER ::= { 1 3 6 1 4 1 19348 2 1 1044 }
id-at-zimbraAuthTokenValidityValueEnabled OBJECT IDENTIFIER ::= { 1 3 6 1 4 1 19348 2 1 1094 }
id-at-zimbraAuthTokens OBJECT IDENTIFIER ::= { 1 3 6 1 4 1 19348 2 1 1585 }
id-at-zimbraAutoProvAccountNameMap OBJECT IDENTIFIER ::= { 1 3 6 1 4 1 19348 2 1 1230 }
id-at-zimbraAutoProvAttrMap OBJECT IDENTIFIER ::= { 1 3 6 1 4 1 19348 2 1 1231 }
id-at-zimbraAutoProvAuthMech OBJECT IDENTIFIER ::= { 1 3 6 1 4 1 19348 2 1 1222 }
id-at-zimbraAutoProvBatchSize OBJECT IDENTIFIER ::= { 1 3 6 1 4 1 19348 2 1 1234 }
id-at-zimbraAutoProvLastPolledTimestamp OBJECT IDENTIFIER ::= { 1 3 6 1 4 1 19348 2 1 1235 }
id-at-zimbraAutoProvLdapAdminBindDn OBJECT IDENTIFIER ::= { 1 3 6 1 4 1 19348 2 1 1225 }
id-at-zimbraAutoProvLdapAdminBindPassword OBJECT IDENTIFIER ::= { 1 3 6 1 4 1 19348 2 1 1226 }
id-at-zimbraAutoProvLdapBindDn OBJECT IDENTIFIER ::= { 1 3 6 1 4 1 19348 2 1 1229 }
id-at-zimbraAutoProvLdapSearchBase OBJECT IDENTIFIER ::= { 1 3 6 1 4 1 19348 2 1 1227 }
id-at-zimbraAutoProvLdapSearchFilter OBJECT IDENTIFIER ::= { 1 3 6 1 4 1 19348 2 1 1228 }
id-at-zimbraAutoProvLdapStartTlsEnabled OBJECT IDENTIFIER ::= { 1 3 6 1 4 1 19348 2 1 1224 }
id-at-zimbraAutoProvLdapURL OBJECT IDENTIFIER ::= { 1 3 6 1 4 1 19348 2 1 1223 }
id-at-zimbraAutoProvListenerClass OBJECT IDENTIFIER ::= { 1 3 6 1 4 1 19348 2 1 1233 }
id-at-zimbraAutoProvLock OBJECT IDENTIFIER ::= { 1 3 6 1 4 1 19348 2 1 1236 }
id-at-zimbraAutoProvMode OBJECT IDENTIFIER ::= { 1 3 6 1 4 1 19348 2 1 1221 }
id-at-zimbraAutoProvNotificationBody OBJECT IDENTIFIER ::= { 1 3 6 1 4 1 19348 2 1 1357 }
id-at-zimbraAutoProvNotificationFromAddress OBJECT IDENTIFIER ::= { 1 3 6 1 4 1 19348 2 1 1232 }
id-at-zimbraAutoProvNotificationSubject OBJECT IDENTIFIER ::= { 1 3 6 1 4 1 19348 2 1 1356 }
id-at-zimbraAutoProvPollingInterval OBJECT IDENTIFIER ::= { 1 3 6 1 4 1 19348 2 1 1238 }
id-at-zimbraAutoProvScheduledDomains OBJECT IDENTIFIER ::= { 1 3 6 1 4 1 19348 2 1 1237 }
id-at-zimbraAutoSubmittedNullReturnPath OBJECT IDENTIFIER ::= { 1 3 6 1 4 1 19348 2 1 502 }
id-at-zimbraAvailableLocale OBJECT IDENTIFIER ::= { 1 3 6 1 4 1 19348 2 1 487 }
id-at-zimbraAvailableSkin OBJECT IDENTIFIER ::= { 1 3 6 1 4 1 19348 2 1 364 }
id-at-zimbraBackupAutoGroupedInterval OBJECT IDENTIFIER ::= { 1 3 6 1 4 1 19348 2 1 513 }
id-at-zimbraBackupAutoGroupedNumGroups OBJECT IDENTIFIER ::= { 1 3 6 1 4 1 19348 2 1 514 }
id-at-zimbraBackupAutoGroupedThrottled OBJECT IDENTIFIER ::= { 1 3 6 1 4 1 19348 2 1 515 }
id-at-zimbraBackupMinFreeSpace OBJECT IDENTIFIER ::= { 1 3 6 1 4 1 19348 2 1 1111 }
id-at-zimbraBackupMode OBJECT IDENTIFIER ::= { 1 3 6 1 4 1 19348 2 1 512 }
id-at-zimbraBackupReportEmailRecipients OBJECT IDENTIFIER ::= { 1 3 6 1 4 1 19348 2 1 459 }
id-at-zimbraBackupReportEmailSender OBJECT IDENTIFIER ::= { 1 3 6 1 4 1 19348 2 1 460 }
id-at-zimbraBackupReportEmailSubjectPrefix OBJECT IDENTIFIER ::= { 1 3 6 1 4 1 19348 2 1 461 }
id-at-zimbraBackupSkipBlobs OBJECT IDENTIFIER ::= { 1 3 6 1 4 1 19348 2 1 1004 }
id-at-zimbraBackupSkipHsmBlobs OBJECT IDENTIFIER ::= { 1 3 6 1 4 1 19348 2 1 1005 }
id-at-zimbraBackupSkipSearchIndex OBJECT IDENTIFIER ::= { 1 3 6 1 4 1 19348 2 1 1003 }
id-at-zimbraBackupTarget OBJECT IDENTIFIER ::= { 1 3 6 1 4 1 19348 2 1 458 }
id-at-zimbraBasicAuthRealm OBJECT IDENTIFIER ::= { 1 3 6 1 4 1 19348 2 1 1098 }
id-at-zimbraBatchedIndexingSize OBJECT IDENTIFIER ::= { 1 3 6 1 4 1 19348 2 1 619 }
id-at-zimbraCBPolicydAccessControlEnabled OBJECT IDENTIFIER ::= { 1 3 6 1 4 1 19348 2 1 1469 }
id-at-zimbraCBPolicydAccountingEnabled OBJECT IDENTIFIER ::= { 1 3 6 1 4 1 19348 2 1 1470 }
id-at-zimbraCBPolicydAmavisEnabled OBJECT IDENTIFIER ::= { 1 3 6 1 4 1 19348 2 1 1471 }
id-at-zimbraCBPolicydBindPort OBJECT IDENTIFIER ::= { 1 3 6 1 4 1 19348 2 1 1561 }
id-at-zimbraCBPolicydBypassMode OBJECT IDENTIFIER ::= { 1 3 6 1 4 1 19348 2 1 1485 }
id-at-zimbraCBPolicydBypassTimeout OBJECT IDENTIFIER ::= { 1 3 6 1 4 1 19348 2 1 1484 }
id-at-zimbraCBPolicydCheckHeloEnabled OBJECT IDENTIFIER ::= { 1 3 6 1 4 1 19348 2 1 1472 }
id-at-zimbraCBPolicydCheckSPFEnabled OBJECT IDENTIFIER ::= { 1 3 6 1 4 1 19348 2 1 1473 }
id-at-zimbraCBPolicydGreylistingBlacklistMsg OBJECT IDENTIFIER ::= { 1 3 6 1 4 1 19348 2 1 1487 }
id-at-zimbraCBPolicydGreylistingDeferMsg OBJECT IDENTIFIER ::= { 1 3 6 1 4 1 19348 2 1 1486 }
id-at-zimbraCBPolicydGreylistingEnabled OBJECT IDENTIFIER ::= { 1 3 6 1 4 1 19348 2 1 1474 }
id-at-zimbraCBPolicydGreylistingTrainingEnabled OBJECT IDENTIFIER ::= { 1 3 6 1 4 1 19348 2 1 1475 }
id-at-zimbraCBPolicydLogLevel OBJECT IDENTIFIER ::= { 1 3 6 1 4 1 19348 2 1 1562 }
id-at-zimbraCBPolicydMaxRequests OBJECT IDENTIFIER ::= { 1 3 6 1 4 1 19348 2 1 1481 }
id-at-zimbraCBPolicydMaxServers OBJECT IDENTIFIER ::= { 1 3 6 1 4 1 19348 2 1 1480 }
id-at-zimbraCBPolicydMaxSpareServers OBJECT IDENTIFIER ::= { 1 3 6 1 4 1 19348 2 1 1479 }
id-at-zimbraCBPolicydMinServers OBJECT IDENTIFIER ::= { 1 3 6 1 4 1 19348 2 1 1477 }
id-at-zimbraCBPolicydMinSpareServers OBJECT IDENTIFIER ::= { 1 3 6 1 4 1 19348 2 1 1478 }
id-at-zimbraCBPolicydQuotasEnabled OBJECT IDENTIFIER ::= { 1 3 6 1 4 1 19348 2 1 1476 }
id-at-zimbraCBPolicydTimeoutBusy OBJECT IDENTIFIER ::= { 1 3 6 1 4 1 19348 2 1 1483 }
id-at-zimbraCBPolicydTimeoutIdle OBJECT IDENTIFIER ::= { 1 3 6 1 4 1 19348 2 1 1482 }
id-at-zimbraCOSId OBJECT IDENTIFIER ::= { 1 3 6 1 4 1 19348 2 1 14 }
id-at-zimbraCOSInheritedAttr OBJECT IDENTIFIER ::= { 1 3 6 1 4 1 19348 2 1 21 }
id-at-zimbraCalResAutoAcceptDecline OBJECT IDENTIFIER ::= { 1 3 6 1 4 1 19348 2 1 315 }
id-at-zimbraCalResAutoDeclineIfBusy OBJECT IDENTIFIER ::= { 1 3 6 1 4 1 19348 2 1 322 }
id-at-zimbraCalResAutoDeclineRecurring OBJECT IDENTIFIER ::= { 1 3 6 1 4 1 19348 2 1 323 }
id-at-zimbraCalResBuilding OBJECT IDENTIFIER ::= { 1 3 6 1 4 1 19348 2 1 327 }
id-at-zimbraCalResCapacity OBJECT IDENTIFIER ::= { 1 3 6 1 4 1 19348 2 1 330 }
id-at-zimbraCalResContactEmail OBJECT IDENTIFIER ::= { 1 3 6 1 4 1 19348 2 1 332 }
id-at-zimbraCalResContactName OBJECT IDENTIFIER ::= { 1 3 6 1 4 1 19348 2 1 331 }
id-at-zimbraCalResContactPhone OBJECT IDENTIFIER ::= { 1 3 6 1 4 1 19348 2 1 333 }
id-at-zimbraCalResFloor OBJECT IDENTIFIER ::= { 1 3 6 1 4 1 19348 2 1 328 }
id-at-zimbraCalResLocationDisplayName OBJECT IDENTIFIER ::= { 1 3 6 1 4 1 19348 2 1 324 }
id-at-zimbraCalResMaxNumConflictsAllowed OBJECT IDENTIFIER ::= { 1 3 6 1 4 1 19348 2 1 808 }
id-at-zimbraCalResMaxPercentConflictsAllowed OBJECT IDENTIFIER ::= { 1 3 6 1 4 1 19348 2 1 809 }
id-at-zimbraCalResRoom OBJECT IDENTIFIER ::= { 1 3 6 1 4 1 19348 2 1 329 }
id-at-zimbraCalResSite OBJECT IDENTIFIER ::= { 1 3 6 1 4 1 19348 2 1 326 }
id-at-zimbraCalResType OBJECT IDENTIFIER ::= { 1 3 6 1 4 1 19348 2 1 314 }
id-at-zimbraCalendarCalDavAlternateCalendarHomeSet OBJECT IDENTIFIER ::= { 1 3 6 1 4 1 19348 2 1 651 }
id-at-zimbraCalendarCalDavCalendarAutoScheduleEnabled OBJECT IDENTIFIER ::= { 1 3 6 1 4 1 19348 2 1 1655 }
id-at-zimbraCalendarCalDavClearTextPasswordEnabled OBJECT IDENTIFIER ::= { 1 3 6 1 4 1 19348 2 1 820 }
id-at-zimbraCalendarCalDavDefaultCalendarId OBJECT IDENTIFIER ::= { 1 3 6 1 4 1 19348 2 1 1078 }
id-at-zimbraCalendarCalDavDisableFreebusy OBJECT IDENTIFIER ::= { 1 3 6 1 4 1 19348 2 1 690 }
id-at-zimbraCalendarCalDavDisableScheduling OBJECT IDENTIFIER ::= { 1 3 6 1 4 1 19348 2 1 652 }
id-at-zimbraCalendarCalDavSharedFolderCacheDuration OBJECT IDENTIFIER ::= { 1 3 6 1 4 1 19348 2 1 817 }
id-at-zimbraCalendarCalDavSyncEnd OBJECT IDENTIFIER ::= { 1 3 6 1 4 1 19348 2 1 816 }
id-at-zimbraCalendarCalDavSyncStart OBJECT IDENTIFIER ::= { 1 3 6 1 4 1 19348 2 1 815 }
id-at-zimbraCalendarCalDavUseDistinctAppointmentAndToDoCollection OBJECT IDENTIFIER ::= { 1 3 6 1 4 1 19348 2 1 794 }
id-at-zimbraCalendarCompatibilityMode OBJECT IDENTIFIER ::= { 1 3 6 1 4 1 19348 2 1 243 }
id-at-zimbraCalendarKeepExceptionsOnSeriesTimeChange OBJECT IDENTIFIER ::= { 1 3 6 1 4 1 19348 2 1 1240 }
id-at-zimbraCalendarLocationDisabledFields OBJECT IDENTIFIER ::= { 1 3 6 1 4 1 19348 2 1 1218 }
id-at-zimbraCalendarMaxRevisions OBJECT IDENTIFIER ::= { 1 3 6 1 4 1 19348 2 1 709 }
id-at-zimbraCalendarRecurrenceDailyMaxDays OBJECT IDENTIFIER ::= { 1 3 6 1 4 1 19348 2 1 661 }
id-at-zimbraCalendarRecurrenceMaxInstances OBJECT IDENTIFIER ::= { 1 3 6 1 4 1 19348 2 1 660 }
id-at-zimbraCalendarRecurrenceMonthlyMaxMonths OBJECT IDENTIFIER ::= { 1 3 6 1 4 1 19348 2 1 663 }
id-at-zimbraCalendarRecurrenceOtherFrequencyMaxYears OBJECT IDENTIFIER ::= { 1 3 6 1 4 1 19348 2 1 665 }
id-at-zimbraCalendarRecurrenceWeeklyMaxWeeks OBJECT IDENTIFIER ::= { 1 3 6 1 4 1 19348 2 1 662 }
id-at-zimbraCalendarRecurrenceYearlyMaxYears OBJECT IDENTIFIER ::= { 1 3 6 1 4 1 19348 2 1 664 }
id-at-zimbraCalendarReminderDeviceEmail OBJECT IDENTIFIER ::= { 1 3 6 1 4 1 19348 2 1 1140 }
id-at-zimbraCalendarResourceDoubleBookingAllowed OBJECT IDENTIFIER ::= { 1 3 6 1 4 1 19348 2 1 1087 }
id-at-zimbraCalendarResourceExtraObjectClass OBJECT IDENTIFIER ::= { 1 3 6 1 4 1 19348 2 1 753 }
id-at-zimbraCalendarShowResourceTabs OBJECT IDENTIFIER ::= { 1 3 6 1 4 1 19348 2 1 1092 }
id-at-zimbraCertAuthorityCertSelfSigned OBJECT IDENTIFIER ::= { 1 3 6 1 4 1 19348 2 1 280 }
id-at-zimbraCertAuthorityKeySelfSigned OBJECT IDENTIFIER ::= { 1 3 6 1 4 1 19348 2 1 279 }
id-at-zimbraChangePasswordURL OBJECT IDENTIFIER ::= { 1 3 6 1 4 1 19348 2 1 777 }
id-at-zimbraChildAccount OBJECT IDENTIFIER ::= { 1 3 6 1 4 1 19348 2 1 449 }
id-at-zimbraChildVisibleAccount OBJECT IDENTIFIER ::= { 1 3 6 1 4 1 19348 2 1 450 }
id-at-zimbraClamAVBindAddress OBJECT IDENTIFIER ::= { 1 3 6 1 4 1 19348 2 1 1619 }
id-at-zimbraClamAVListenPort OBJECT IDENTIFIER ::= { 1 3 6 1 4 1 19348 2 1 1620 }
id-at-zimbraClamAVMaxThreads OBJECT IDENTIFIER ::= { 1 3 6 1 4 1 19348 2 1 1462 }
id-at-zimbraClientTypeRegex OBJECT IDENTIFIER ::= { 1 3 6 1 4 1 19348 2 1 1416 }
id-at-zimbraClusterType OBJECT IDENTIFIER ::= { 1 3 6 1 4 1 19348 2 1 508 }
id-at-zimbraCommunityAPIClientID OBJECT IDENTIFIER ::= { 1 3 6 1 4 1 19348 2 1 1637 }
id-at-zimbraCommunityAPIClientSecret OBJECT IDENTIFIER ::= { 1 3 6 1 4 1 19348 2 1 1638 }
id-at-zimbraCommunityBaseURL OBJECT IDENTIFIER ::= { 1 3 6 1 4 1 19348 2 1 1640 }
id-at-zimbraCommunityHomeURL OBJECT IDENTIFIER ::= { 1 3 6 1 4 1 19348 2 1 1641 }
id-at-zimbraCommunityID OBJECT IDENTIFIER ::= { 1 3 6 1 4 1 19348 2 1 1644 }
id-at-zimbraCommunityUsernameMapping OBJECT IDENTIFIER ::= { 1 3 6 1 4 1 19348 2 1 1639 }
id-at-zimbraComponentAvailable OBJECT IDENTIFIER ::= { 1 3 6 1 4 1 19348 2 1 242 }
id-at-zimbraConfiguredServerIDForBlobDirEnabled OBJECT IDENTIFIER ::= { 1 3 6 1 4 1 19348 2 1 1551 }
id-at-zimbraConstraint OBJECT IDENTIFIER ::= { 1 3 6 1 4 1 19348 2 1 766 }
id-at-zimbraContactAutoCompleteEmailFields OBJECT IDENTIFIER ::= { 1 3 6 1 4 1 19348 2 1 760 }
id-at-zimbraContactAutoCompleteMaxResults OBJECT IDENTIFIER ::= { 1 3 6 1 4 1 19348 2 1 827 }
id-at-zimbraContactEmailFields OBJECT IDENTIFIER ::= { 1 3 6 1 4 1 19348 2 1 1088 }
id-at-zimbraContactHiddenAttributes OBJECT IDENTIFIER ::= { 1 3 6 1 4 1 19348 2 1 1086 }
id-at-zimbraContactMaxNumEntries OBJECT IDENTIFIER ::= { 1 3 6 1 4 1 19348 2 1 107 }
id-at-zimbraContactRankingTableRefreshInterval OBJECT IDENTIFIER ::= { 1 3 6 1 4 1 19348 2 1 1023 }
id-at-zimbraContactRankingTableSize OBJECT IDENTIFIER ::= { 1 3 6 1 4 1 19348 2 1 758 }
id-at-zimbraConvertdURL OBJECT IDENTIFIER ::= { 1 3 6 1 4 1 19348 2 1 776 }
id-at-zimbraConverterHints OBJECT IDENTIFIER ::= { 1 3 6 1 4 1 19348 2 1 1441 }
id-at-zimbraCosExtraObjectClass OBJECT IDENTIFIER ::= { 1 3 6 1 4 1 19348 2 1 754 }
id-at-zimbraCreateTimestamp OBJECT IDENTIFIER ::= { 1 3 6 1 4 1 19348 2 1 790 }
id-at-zimbraCsrfAllowedRefererHosts OBJECT IDENTIFIER ::= { 1 3 6 1 4 1 19348 2 1 1630 }
id-at-zimbraCsrfRefererCheckEnabled OBJECT IDENTIFIER ::= { 1 3 6 1 4 1 19348 2 1 1631 }
id-at-zimbraCsrfTokenCheckEnabled OBJECT IDENTIFIER ::= { 1 3 6 1 4 1 19348 2 1 1628 }
id-at-zimbraCsrfTokenData OBJECT IDENTIFIER ::= { 1 3 6 1 4 1 19348 2 1 1629 }
id-at-zimbraCsrfTokenKey OBJECT IDENTIFIER ::= { 1 3 6 1 4 1 19348 2 1 1627 }
id-at-zimbraCustomMimeHeaderNameAllowed OBJECT IDENTIFIER ::= { 1 3 6 1 4 1 19348 2 1 1265 }
id-at-zimbraCustomerCareTier OBJECT IDENTIFIER ::= { 1 3 6 1 4 1 19348 2 1 605 }
id-at-zimbraDNSCheckHostname OBJECT IDENTIFIER ::= { 1 3 6 1 4 1 19348 2 1 744 }
id-at-zimbraDNSMasterIP OBJECT IDENTIFIER ::= { 1 3 6 1 4 1 19348 2 1 1569 }
id-at-zimbraDNSTCPUpstream OBJECT IDENTIFIER ::= { 1 3 6 1 4 1 19348 2 1 1597 }
id-at-zimbraDNSUseTCP OBJECT IDENTIFIER ::= { 1 3 6 1 4 1 19348 2 1 1584 }
id-at-zimbraDNSUseUDP OBJECT IDENTIFIER ::= { 1 3 6 1 4 1 19348 2 1 1586 }
id-at-zimbraDataSourceAttribute OBJECT IDENTIFIER ::= { 1 3 6 1 4 1 19348 2 1 718 }
id-at-zimbraDataSourceAuthMechanism OBJECT IDENTIFIER ::= { 1 3 6 1 4 1 19348 2 1 1107 }
id-at-zimbraDataSourceAuthorizationId OBJECT IDENTIFIER ::= { 1 3 6 1 4 1 19348 2 1 1108 }
id-at-zimbraDataSourceCaldavPollingInterval OBJECT IDENTIFIER ::= { 1 3 6 1 4 1 19348 2 1 788 }
id-at-zimbraDataSourceCalendarPollingInterval OBJECT IDENTIFIER ::= { 1 3 6 1 4 1 19348 2 1 819 }
id-at-zimbraDataSourceConnectTimeout OBJECT IDENTIFIER ::= { 1 3 6 1 4 1 19348 2 1 1083 }
id-at-zimbraDataSourceConnectionType OBJECT IDENTIFIER ::= { 1 3 6 1 4 1 19348 2 1 425 }
id-at-zimbraDataSourceDomain OBJECT IDENTIFIER ::= { 1 3 6 1 4 1 19348 2 1 1037 }
id-at-zimbraDataSourceEmailAddress OBJECT IDENTIFIER ::= { 1 3 6 1 4 1 19348 2 1 495 }
id-at-zimbraDataSourceEnableTrace OBJECT IDENTIFIER ::= { 1 3 6 1 4 1 19348 2 1 683 }
id-at-zimbraDataSourceEnabled OBJECT IDENTIFIER ::= { 1 3 6 1 4 1 19348 2 1 419 }
id-at-zimbraDataSourceFailingSince OBJECT IDENTIFIER ::= { 1 3 6 1 4 1 19348 2 1 1030 }
id-at-zimbraDataSourceFolderId OBJECT IDENTIFIER ::= { 1 3 6 1 4 1 19348 2 1 424 }
id-at-zimbraDataSourceGalPollingInterval OBJECT IDENTIFIER ::= { 1 3 6 1 4 1 19348 2 1 826 }
id-at-zimbraDataSourceHost OBJECT IDENTIFIER ::= { 1 3 6 1 4 1 19348 2 1 420 }
id-at-zimbraDataSourceId OBJECT IDENTIFIER ::= { 1 3 6 1 4 1 19348 2 1 417 }
id-at-zimbraDataSourceImapPollingInterval OBJECT IDENTIFIER ::= { 1 3 6 1 4 1 19348 2 1 768 }
id-at-zimbraDataSourceImportClassName OBJECT IDENTIFIER ::= { 1 3 6 1 4 1 19348 2 1 717 }
id-at-zimbraDataSourceImportOnLogin OBJECT IDENTIFIER ::= { 1 3 6 1 4 1 19348 2 1 1418 }
id-at-zimbraDataSourceImportOnly OBJECT IDENTIFIER ::= { 1 3 6 1 4 1 19348 2 1 1106 }
id-at-zimbraDataSourceIsInternal OBJECT IDENTIFIER ::= { 1 3 6 1 4 1 19348 2 1 1126 }
id-at-zimbraDataSourceLastError OBJECT IDENTIFIER ::= { 1 3 6 1 4 1 19348 2 1 1029 }
id-at-zimbraDataSourceLeaveOnServer OBJECT IDENTIFIER ::= { 1 3 6 1 4 1 19348 2 1 434 }
id-at-zimbraDataSourceLivePollingInterval OBJECT IDENTIFIER ::= { 1 3 6 1 4 1 19348 2 1 769 }
id-at-zimbraDataSourceMaxNumEntries OBJECT IDENTIFIER ::= { 1 3 6 1 4 1 19348 2 1 426 }
id-at-zimbraDataSourceMaxTraceSize OBJECT IDENTIFIER ::= { 1 3 6 1 4 1 19348 2 1 1033 }
id-at-zimbraDataSourceMinPollingInterval OBJECT IDENTIFIER ::= { 1 3 6 1 4 1 19348 2 1 525 }
id-at-zimbraDataSourceName OBJECT IDENTIFIER ::= { 1 3 6 1 4 1 19348 2 1 418 }
id-at-zimbraDataSourcePassword OBJECT IDENTIFIER ::= { 1 3 6 1 4 1 19348 2 1 423 }
id-at-zimbraDataSourcePollingInterval OBJECT IDENTIFIER ::= { 1 3 6 1 4 1 19348 2 1 455 }
id-at-zimbraDataSourcePop3PollingInterval OBJECT IDENTIFIER ::= { 1 3 6 1 4 1 19348 2 1 767 }
id-at-zimbraDataSourcePort OBJECT IDENTIFIER ::= { 1 3 6 1 4 1 19348 2 1 421 }
id-at-zimbraDataSourceReadTimeout OBJECT IDENTIFIER ::= { 1 3 6 1 4 1 19348 2 1 1084 }
id-at-zimbraDataSourceRssPollingInterval OBJECT IDENTIFIER ::= { 1 3 6 1 4 1 19348 2 1 770 }
id-at-zimbraDataSourceType OBJECT IDENTIFIER ::= { 1 3 6 1 4 1 19348 2 1 716 }
id-at-zimbraDataSourceUseAddressForForwardReply OBJECT IDENTIFIER ::= { 1 3 6 1 4 1 19348 2 1 496 }
id-at-zimbraDataSourceUsername OBJECT IDENTIFIER ::= { 1 3 6 1 4 1 19348 2 1 422 }
id-at-zimbraDataSourceYabPollingInterval OBJECT IDENTIFIER ::= { 1 3 6 1 4 1 19348 2 1 789 }
id-at-zimbraDatabaseSlowSqlThreshold OBJECT IDENTIFIER ::= { 1 3 6 1 4 1 19348 2 1 1038 }
id-at-zimbraDebugInfo OBJECT IDENTIFIER ::= { 1 3 6 1 4 1 19348 2 1 365 }
id-at-zimbraDefaultAnalyzerStopWords OBJECT IDENTIFIER ::= { 1 3 6 1 4 1 19348 2 1 1587 }
id-at-zimbraDefaultDomainName OBJECT IDENTIFIER ::= { 1 3 6 1 4 1 19348 2 1 172 }
id-at-zimbraDefaultFolderFlags OBJECT IDENTIFIER ::= { 1 3 6 1 4 1 19348 2 1 1210 }
id-at-zimbraDeviceAllowedPasscodeLockoutDuration OBJECT IDENTIFIER ::= { 1 3 6 1 4 1 19348 2 1 1397 }
id-at-zimbraDeviceCalendarSoftDeleteExcludePattern OBJECT IDENTIFIER ::= { 1 3 6 1 4 1 19348 2 1 1450 }
id-at-zimbraDeviceFileOpenWithEnabled OBJECT IDENTIFIER ::= { 1 3 6 1 4 1 19348 2 1 1400 }
id-at-zimbraDeviceLockWhenInactive OBJECT IDENTIFIER ::= { 1 3 6 1 4 1 19348 2 1 1399 }
id-at-zimbraDeviceOfflineCacheEnabled OBJECT IDENTIFIER ::= { 1 3 6 1 4 1 19348 2 1 1412 }
id-at-zimbraDevicePasscodeEnabled OBJECT IDENTIFIER ::= { 1 3 6 1 4 1 19348 2 1 1396 }
id-at-zimbraDevicePasscodeLockoutDuration OBJECT IDENTIFIER ::= { 1 3 6 1 4 1 19348 2 1 1398 }
id-at-zimbraDistributionListSendShareMessageFromAddress OBJECT IDENTIFIER ::= { 1 3 6 1 4 1 19348 2 1 811 }
id-at-zimbraDistributionListSendShareMessageToNewMembers OBJECT IDENTIFIER ::= { 1 3 6 1 4 1 19348 2 1 810 }
id-at-zimbraDistributionListSubscriptionPolicy OBJECT IDENTIFIER ::= { 1 3 6 1 4 1 19348 2 1 1275 }
id-at-zimbraDistributionListUnsubscriptionPolicy OBJECT IDENTIFIER ::= { 1 3 6 1 4 1 19348 2 1 1276 }
id-at-zimbraDomainAdminMaxMailQuota OBJECT IDENTIFIER ::= { 1 3 6 1 4 1 19348 2 1 398 }
id-at-zimbraDomainAdminModifiableAttr OBJECT IDENTIFIER ::= { 1 3 6 1 4 1 19348 2 1 300 }
id-at-zimbraDomainAggregateQuota OBJECT IDENTIFIER ::= { 1 3 6 1 4 1 19348 2 1 1327 }
id-at-zimbraDomainAggregateQuotaPolicy OBJECT IDENTIFIER ::= { 1 3 6 1 4 1 19348 2 1 1329 }
id-at-zimbraDomainAggregateQuotaWarnEmailRecipient OBJECT IDENTIFIER ::= { 1 3 6 1 4 1 19348 2 1 1331 }
id-at-zimbraDomainAggregateQuotaWarnPercent OBJECT IDENTIFIER ::= { 1 3 6 1 4 1 19348 2 1 1330 }
id-at-zimbraDomainAliasTargetId OBJECT IDENTIFIER ::= { 1 3 6 1 4 1 19348 2 1 775 }
id-at-zimbraDomainCOSMaxAccounts OBJECT IDENTIFIER ::= { 1 3 6 1 4 1 19348 2 1 714 }
id-at-zimbraDomainDefaultCOSId OBJECT IDENTIFIER ::= { 1 3 6 1 4 1 19348 2 1 299 }
id-at-zimbraDomainDefaultExternalUserCOSId OBJECT IDENTIFIER ::= { 1 3 6 1 4 1 19348 2 1 1247 }
id-at-zimbraDomainExtraObjectClass OBJECT IDENTIFIER ::= { 1 3 6 1 4 1 19348 2 1 755 }
id-at-zimbraDomainFeatureMaxAccounts OBJECT IDENTIFIER ::= { 1 3 6 1 4 1 19348 2 1 715 }
id-at-zimbraDomainId OBJECT IDENTIFIER ::= { 1 3 6 1 4 1 19348 2 1 741 }
id-at-zimbraDomainInheritedAttr OBJECT IDENTIFIER ::= { 1 3 6 1 4 1 19348 2 1 63 }
id-at-zimbraDomainMandatoryMailSignatureEnabled OBJECT IDENTIFIER ::= { 1 3 6 1 4 1 19348 2 1 1069 }
id-at-zimbraDomainMandatoryMailSignatureHTML OBJECT IDENTIFIER ::= { 1 3 6 1 4 1 19348 2 1 1071 }
id-at-zimbraDomainMandatoryMailSignatureText OBJECT IDENTIFIER ::= { 1 3 6 1 4 1 19348 2 1 1070 }
id-at-zimbraDomainMaxAccounts OBJECT IDENTIFIER ::= { 1 3 6 1 4 1 19348 2 1 400 }
id-at-zimbraDomainName OBJECT IDENTIFIER ::= { 1 3 6 1 4 1 19348 2 1 19 }
id-at-zimbraDomainRenameInfo OBJECT IDENTIFIER ::= { 1 3 6 1 4 1 19348 2 1 536 }
id-at-zimbraDomainStatus OBJECT IDENTIFIER ::= { 1 3 6 1 4 1 19348 2 1 535 }
id-at-zimbraDomainType OBJECT IDENTIFIER ::= { 1 3 6 1 4 1 19348 2 1 212 }
id-at-zimbraDumpsterEnabled OBJECT IDENTIFIER ::= { 1 3 6 1 4 1 19348 2 1 1128 }
id-at-zimbraDumpsterPurgeEnabled OBJECT IDENTIFIER ::= { 1 3 6 1 4 1 19348 2 1 1315 }
id-at-zimbraDumpsterUserVisibleAge OBJECT IDENTIFIER ::= { 1 3 6 1 4 1 19348 2 1 1314 }
id-at-zimbraEmptyFolderOpTimeout OBJECT IDENTIFIER ::= { 1 3 6 1 4 1 19348 2 1 1652 }
id-at-zimbraErrorReportUrl OBJECT IDENTIFIER ::= { 1 3 6 1 4 1 19348 2 1 1075 }
id-at-zimbraExcludeFromCMBSearch OBJECT IDENTIFIER ::= { 1 3 6 1 4 1 19348 2 1 501 }
id-at-zimbraExtensionBindAddress OBJECT IDENTIFIER ::= { 1 3 6 1 4 1 19348 2 1 1369 }
id-at-zimbraExternalAccountDisabledTime OBJECT IDENTIFIER ::= { 1 3 6 1 4 1 19348 2 1 1371 }
id-at-zimbraExternalAccountLifetimeAfterDisabled OBJECT IDENTIFIER ::= { 1 3 6 1 4 1 19348 2 1 1372 }
id-at-zimbraExternalAccountProvisioningKey OBJECT IDENTIFIER ::= { 1 3 6 1 4 1 19348 2 1 1648 }
id-at-zimbraExternalAccountStatusCheckInterval OBJECT IDENTIFIER ::= { 1 3 6 1 4 1 19348 2 1 1370 }
id-at-zimbraExternalGroupHandlerClass OBJECT IDENTIFIER ::= { 1 3 6 1 4 1 19348 2 1 1251 }
id-at-zimbraExternalGroupLdapSearchBase OBJECT IDENTIFIER ::= { 1 3 6 1 4 1 19348 2 1 1249 }
id-at-zimbraExternalGroupLdapSearchFilter OBJECT IDENTIFIER ::= { 1 3 6 1 4 1 19348 2 1 1250 }
id-at-zimbraExternalImapHostname OBJECT IDENTIFIER ::= { 1 3 6 1 4 1 19348 2 1 786 }
id-at-zimbraExternalImapPort OBJECT IDENTIFIER ::= { 1 3 6 1 4 1 19348 2 1 782 }
id-at-zimbraExternalImapSSLHostname OBJECT IDENTIFIER ::= { 1 3 6 1 4 1 19348 2 1 787 }
id-at-zimbraExternalImapSSLPort OBJECT IDENTIFIER ::= { 1 3 6 1 4 1 19348 2 1 783 }
id-at-zimbraExternalPop3Hostname OBJECT IDENTIFIER ::= { 1 3 6 1 4 1 19348 2 1 784 }
id-at-zimbraExternalPop3Port OBJECT IDENTIFIER ::= { 1 3 6 1 4 1 19348 2 1 780 }
id-at-zimbraExternalPop3SSLHostname OBJECT IDENTIFIER ::= { 1 3 6 1 4 1 19348 2 1 785 }
id-at-zimbraExternalPop3SSLPort OBJECT IDENTIFIER ::= { 1 3 6 1 4 1 19348 2 1 781 }
id-at-zimbraExternalShareDomainWhitelistEnabled OBJECT IDENTIFIER ::= { 1 3 6 1 4 1 19348 2 1 1264 }
id-at-zimbraExternalShareInvitationUrlExpiration OBJECT IDENTIFIER ::= { 1 3 6 1 4 1 19348 2 1 1349 }
id-at-zimbraExternalShareLifetime OBJECT IDENTIFIER ::= { 1 3 6 1 4 1 19348 2 1 1260 }
id-at-zimbraExternalShareWhitelistDomain OBJECT IDENTIFIER ::= { 1 3 6 1 4 1 19348 2 1 1263 }
id-at-zimbraExternalSharingEnabled OBJECT IDENTIFIER ::= { 1 3 6 1 4 1 19348 2 1 1261 }
id-at-zimbraExternalUserMailAddress OBJECT IDENTIFIER ::= { 1 3 6 1 4 1 19348 2 1 1244 }
id-at-zimbraFeatureAdminMailEnabled OBJECT IDENTIFIER ::= { 1 3 6 1 4 1 19348 2 1 1170 }
id-at-zimbraFeatureAdvancedSearchEnabled OBJECT IDENTIFIER ::= { 1 3 6 1 4 1 19348 2 1 138 }
id-at-zimbraFeatureAntispamEnabled OBJECT IDENTIFIER ::= { 1 3 6 1 4 1 19348 2 1 1168 }
id-at-zimbraFeatureBriefcaseDocsEnabled OBJECT IDENTIFIER ::= { 1 3 6 1 4 1 19348 2 1 1055 }
id-at-zimbraFeatureBriefcaseSlidesEnabled OBJECT IDENTIFIER ::= { 1 3 6 1 4 1 19348 2 1 1054 }
id-at-zimbraFeatureBriefcaseSpreadsheetEnabled OBJECT IDENTIFIER ::= { 1 3 6 1 4 1 19348 2 1 1053 }
id-at-zimbraFeatureBriefcasesEnabled OBJECT IDENTIFIER ::= { 1 3 6 1 4 1 19348 2 1 498 }
id-at-zimbraFeatureCalendarEnabled OBJECT IDENTIFIER ::= { 1 3 6 1 4 1 19348 2 1 136 }
id-at-zimbraFeatureCalendarReminderDeviceEmailEnabled OBJECT IDENTIFIER ::= { 1 3 6 1 4 1 19348 2 1 1150 }
id-at-zimbraFeatureCalendarUpsellEnabled OBJECT IDENTIFIER ::= { 1 3 6 1 4 1 19348 2 1 531 }
id-at-zimbraFeatureCalendarUpsellURL OBJECT IDENTIFIER ::= { 1 3 6 1 4 1 19348 2 1 532 }
id-at-zimbraFeatureChangePasswordEnabled OBJECT IDENTIFIER ::= { 1 3 6 1 4 1 19348 2 1 141 }
id-at-zimbraFeatureComposeInNewWindowEnabled OBJECT IDENTIFIER ::= { 1 3 6 1 4 1 19348 2 1 584 }
id-at-zimbraFeatureConfirmationPageEnabled OBJECT IDENTIFIER ::= { 1 3 6 1 4 1 19348 2 1 806 }
id-at-zimbraFeatureContactsDetailedSearchEnabled OBJECT IDENTIFIER ::= { 1 3 6 1 4 1 19348 2 1 1164 }
id-at-zimbraFeatureContactsEnabled OBJECT IDENTIFIER ::= { 1 3 6 1 4 1 19348 2 1 135 }
id-at-zimbraFeatureContactsUpsellEnabled OBJECT IDENTIFIER ::= { 1 3 6 1 4 1 19348 2 1 529 }
id-at-zimbraFeatureContactsUpsellURL OBJECT IDENTIFIER ::= { 1 3 6 1 4 1 19348 2 1 530 }
id-at-zimbraFeatureConversationsEnabled OBJECT IDENTIFIER ::= { 1 3 6 1 4 1 19348 2 1 140 }
id-at-zimbraFeatureCrocodocEnabled OBJECT IDENTIFIER ::= { 1 3 6 1 4 1 19348 2 1 1381 }
id-at-zimbraFeatureDiscardInFiltersEnabled OBJECT IDENTIFIER ::= { 1 3 6 1 4 1 19348 2 1 773 }
id-at-zimbraFeatureDistributionListExpandMembersEnabled OBJECT IDENTIFIER ::= { 1 3 6 1 4 1 19348 2 1 1134 }
id-at-zimbraFeatureDistributionListFolderEnabled OBJECT IDENTIFIER ::= { 1 3 6 1 4 1 19348 2 1 1438 }
id-at-zimbraFeatureEwsEnabled OBJECT IDENTIFIER ::= { 1 3 6 1 4 1 19348 2 1 1574 }
id-at-zimbraFeatureExportFolderEnabled OBJECT IDENTIFIER ::= { 1 3 6 1 4 1 19348 2 1 1185 }
id-at-zimbraFeatureExternalFeedbackEnabled OBJECT IDENTIFIER ::= { 1 3 6 1 4 1 19348 2 1 1373 }
id-at-zimbraFeatureFiltersEnabled OBJECT IDENTIFIER ::= { 1 3 6 1 4 1 19348 2 1 143 }
id-at-zimbraFeatureFlaggingEnabled OBJECT IDENTIFIER ::= { 1 3 6 1 4 1 19348 2 1 499 }
id-at-zimbraFeatureFreeBusyViewEnabled OBJECT IDENTIFIER ::= { 1 3 6 1 4 1 19348 2 1 1143 }
id-at-zimbraFeatureFromDisplayEnabled OBJECT IDENTIFIER ::= { 1 3 6 1 4 1 19348 2 1 1455 }
id-at-zimbraFeatureGalAutoCompleteEnabled OBJECT IDENTIFIER ::= { 1 3 6 1 4 1 19348 2 1 359 }
id-at-zimbraFeatureGalEnabled OBJECT IDENTIFIER ::= { 1 3 6 1 4 1 19348 2 1 149 }
id-at-zimbraFeatureGalSyncEnabled OBJECT IDENTIFIER ::= { 1 3 6 1 4 1 19348 2 1 711 }
id-at-zimbraFeatureGroupCalendarEnabled OBJECT IDENTIFIER ::= { 1 3 6 1 4 1 19348 2 1 481 }
id-at-zimbraFeatureHtmlComposeEnabled OBJECT IDENTIFIER ::= { 1 3 6 1 4 1 19348 2 1 219 }
id-at-zimbraFeatureIMEnabled OBJECT IDENTIFIER ::= { 1 3 6 1 4 1 19348 2 1 305 }
id-at-zimbraFeatureIdentitiesEnabled OBJECT IDENTIFIER ::= { 1 3 6 1 4 1 19348 2 1 415 }
id-at-zimbraFeatureImapDataSourceEnabled OBJECT IDENTIFIER ::= { 1 3 6 1 4 1 19348 2 1 568 }
id-at-zimbraFeatureImportExportFolderEnabled OBJECT IDENTIFIER ::= { 1 3 6 1 4 1 19348 2 1 750 }
id-at-zimbraFeatureImportFolderEnabled OBJECT IDENTIFIER ::= { 1 3 6 1 4 1 19348 2 1 1184 }
id-at-zimbraFeatureInitialSearchPreferenceEnabled OBJECT IDENTIFIER ::= { 1 3 6 1 4 1 19348 2 1 142 }
id-at-zimbraFeatureInstantNotify OBJECT IDENTIFIER ::= { 1 3 6 1 4 1 19348 2 1 521 }
id-at-zimbraFeatureMAPIConnectorEnabled OBJECT IDENTIFIER ::= { 1 3 6 1 4 1 19348 2 1 1127 }
id-at-zimbraFeatureMailEnabled OBJECT IDENTIFIER ::= { 1 3 6 1 4 1 19348 2 1 489 }
id-at-zimbraFeatureMailForwardingEnabled OBJECT IDENTIFIER ::= { 1 3 6 1 4 1 19348 2 1 342 }
id-at-zimbraFeatureMailForwardingInFiltersEnabled OBJECT IDENTIFIER ::= { 1 3 6 1 4 1 19348 2 1 704 }
id-at-zimbraFeatureMailPollingIntervalPreferenceEnabled OBJECT IDENTIFIER ::= { 1 3 6 1 4 1 19348 2 1 441 }
id-at-zimbraFeatureMailPriorityEnabled OBJECT IDENTIFIER ::= { 1 3 6 1 4 1 19348 2 1 566 }
id-at-zimbraFeatureMailSendLaterEnabled OBJECT IDENTIFIER ::= { 1 3 6 1 4 1 19348 2 1 1137 }
id-at-zimbraFeatureMailUpsellEnabled OBJECT IDENTIFIER ::= { 1 3 6 1 4 1 19348 2 1 527 }
id-at-zimbraFeatureMailUpsellURL OBJECT IDENTIFIER ::= { 1 3 6 1 4 1 19348 2 1 528 }
id-at-zimbraFeatureManageSMIMECertificateEnabled OBJECT IDENTIFIER ::= { 1 3 6 1 4 1 19348 2 1 1183 }
id-at-zimbraFeatureManageZimlets OBJECT IDENTIFIER ::= { 1 3 6 1 4 1 19348 2 1 1051 }
id-at-zimbraFeatureMobilePolicyEnabled OBJECT IDENTIFIER ::= { 1 3 6 1 4 1 19348 2 1 833 }
id-at-zimbraFeatureMobileSyncEnabled OBJECT IDENTIFIER ::= { 1 3 6 1 4 1 19348 2 1 347 }
id-at-zimbraFeatureNewAddrBookEnabled OBJECT IDENTIFIER ::= { 1 3 6 1 4 1 19348 2 1 631 }
id-at-zimbraFeatureNewMailNotificationEnabled OBJECT IDENTIFIER ::= { 1 3 6 1 4 1 19348 2 1 367 }
id-at-zimbraFeatureNotebookEnabled OBJECT IDENTIFIER ::= { 1 3 6 1 4 1 19348 2 1 356 }
id-at-zimbraFeatureOpenMailInNewWindowEnabled OBJECT IDENTIFIER ::= { 1 3 6 1 4 1 19348 2 1 585 }
id-at-zimbraFeatureOptionsEnabled OBJECT IDENTIFIER ::= { 1 3 6 1 4 1 19348 2 1 451 }
id-at-zimbraFeatureOutOfOfficeReplyEnabled OBJECT IDENTIFIER ::= { 1 3 6 1 4 1 19348 2 1 366 }
id-at-zimbraFeaturePeopleSearchEnabled OBJECT IDENTIFIER ::= { 1 3 6 1 4 1 19348 2 1 1109 }
id-at-zimbraFeaturePop3DataSourceEnabled OBJECT IDENTIFIER ::= { 1 3 6 1 4 1 19348 2 1 416 }
id-at-zimbraFeaturePortalEnabled OBJECT IDENTIFIER ::= { 1 3 6 1 4 1 19348 2 1 447 }
id-at-zimbraFeaturePriorityInboxEnabled OBJECT IDENTIFIER ::= { 1 3 6 1 4 1 19348 2 1 1271 }
id-at-zimbraFeatureReadReceiptsEnabled OBJECT IDENTIFIER ::= { 1 3 6 1 4 1 19348 2 1 821 }
id-at-zimbraFeatureSMIMEEnabled OBJECT IDENTIFIER ::= { 1 3 6 1 4 1 19348 2 1 1186 }
id-at-zimbraFeatureSavedSearchesEnabled OBJECT IDENTIFIER ::= { 1 3 6 1 4 1 19348 2 1 139 }
id-at-zimbraFeatureSharingEnabled OBJECT IDENTIFIER ::= { 1 3 6 1 4 1 19348 2 1 335 }
id-at-zimbraFeatureShortcutAliasesEnabled OBJECT IDENTIFIER ::= { 1 3 6 1 4 1 19348 2 1 452 }
id-at-zimbraFeatureSignaturesEnabled OBJECT IDENTIFIER ::= { 1 3 6 1 4 1 19348 2 1 494 }
id-at-zimbraFeatureSkinChangeEnabled OBJECT IDENTIFIER ::= { 1 3 6 1 4 1 19348 2 1 354 }
id-at-zimbraFeatureSocialEnabled OBJECT IDENTIFIER ::= { 1 3 6 1 4 1 19348 2 1 1490 }
id-at-zimbraFeatureSocialExternalEnabled OBJECT IDENTIFIER ::= { 1 3 6 1 4 1 19348 2 1 1491 }
id-at-zimbraFeatureSocialExternalURL OBJECT IDENTIFIER ::= { 1 3 6 1 4 1 19348 2 1 1492 }
id-at-zimbraFeatureSocialFiltersEnabled OBJECT IDENTIFIER ::= { 1 3 6 1 4 1 19348 2 1 1272 }
id-at-zimbraFeatureSocialName OBJECT IDENTIFIER ::= { 1 3 6 1 4 1 19348 2 1 1625 }
id-at-zimbraFeatureSocialcastEnabled OBJECT IDENTIFIER ::= { 1 3 6 1 4 1 19348 2 1 1388 }
id-at-zimbraFeatureTaggingEnabled OBJECT IDENTIFIER ::= { 1 3 6 1 4 1 19348 2 1 137 }
id-at-zimbraFeatureTasksEnabled OBJECT IDENTIFIER ::= { 1 3 6 1 4 1 19348 2 1 436 }
id-at-zimbraFeatureTouchClientEnabled OBJECT IDENTIFIER ::= { 1 3 6 1 4 1 19348 2 1 1636 }
id-at-zimbraFeatureViewInHtmlEnabled OBJECT IDENTIFIER ::= { 1 3 6 1 4 1 19348 2 1 312 }
id-at-zimbraFeatureVoiceChangePinEnabled OBJECT IDENTIFIER ::= { 1 3 6 1 4 1 19348 2 1 1050 }
id-at-zimbraFeatureVoiceEnabled OBJECT IDENTIFIER ::= { 1 3 6 1 4 1 19348 2 1 445 }
id-at-zimbraFeatureVoiceUpsellEnabled OBJECT IDENTIFIER ::= { 1 3 6 1 4 1 19348 2 1 533 }
id-at-zimbraFeatureVoiceUpsellURL OBJECT IDENTIFIER ::= { 1 3 6 1 4 1 19348 2 1 534 }
id-at-zimbraFeatureWebClientOfflineAccessEnabled OBJECT IDENTIFIER ::= { 1 3 6 1 4 1 19348 2 1 1611 }
id-at-zimbraFeatureWebSearchEnabled OBJECT IDENTIFIER ::= { 1 3 6 1 4 1 19348 2 1 602 }
id-at-zimbraFeatureZimbraAssistantEnabled OBJECT IDENTIFIER ::= { 1 3 6 1 4 1 19348 2 1 544 }
id-at-zimbraFileAndroidCrashReportingEnabled OBJECT IDENTIFIER ::= { 1 3 6 1 4 1 19348 2 1 1385 }
id-at-zimbraFileDeletionNotificationBody OBJECT IDENTIFIER ::= { 1 3 6 1 4 1 19348 2 1 1313 }
id-at-zimbraFileDeletionNotificationSubject OBJECT IDENTIFIER ::= { 1 3 6 1 4 1 19348 2 1 1312 }
id-at-zimbraFileExpirationWarningBody OBJECT IDENTIFIER ::= { 1 3 6 1 4 1 19348 2 1 1311 }
id-at-zimbraFileExpirationWarningSubject OBJECT IDENTIFIER ::= { 1 3 6 1 4 1 19348 2 1 1310 }
id-at-zimbraFileExpirationWarningThreshold OBJECT IDENTIFIER ::= { 1 3 6 1 4 1 19348 2 1 1308 }
id-at-zimbraFileExternalShareLifetime OBJECT IDENTIFIER ::= { 1 3 6 1 4 1 19348 2 1 1363 }
id-at-zimbraFileIOSCrashReportingEnabled OBJECT IDENTIFIER ::= { 1 3 6 1 4 1 19348 2 1 1390 }
id-at-zimbraFileLifetime OBJECT IDENTIFIER ::= { 1 3 6 1 4 1 19348 2 1 1309 }
id-at-zimbraFilePreviewMaxSize OBJECT IDENTIFIER ::= { 1 3 6 1 4 1 19348 2 1 1442 }
id-at-zimbraFilePublicShareLifetime OBJECT IDENTIFIER ::= { 1 3 6 1 4 1 19348 2 1 1364 }
id-at-zimbraFileShareLifetime OBJECT IDENTIFIER ::= { 1 3 6 1 4 1 19348 2 1 1362 }
id-at-zimbraFileUploadMaxSize OBJECT IDENTIFIER ::= { 1 3 6 1 4 1 19348 2 1 227 }
id-at-zimbraFileUploadMaxSizePerFile OBJECT IDENTIFIER ::= { 1 3 6 1 4 1 19348 2 1 1350 }
id-at-zimbraFileVersionLifetime OBJECT IDENTIFIER ::= { 1 3 6 1 4 1 19348 2 1 1325 }
id-at-zimbraFileVersioningEnabled OBJECT IDENTIFIER ::= { 1 3 6 1 4 1 19348 2 1 1324 }
id-at-zimbraFilterBatchSize OBJECT IDENTIFIER ::= { 1 3 6 1 4 1 19348 2 1 1158 }
id-at-zimbraFilterSleepInterval OBJECT IDENTIFIER ::= { 1 3 6 1 4 1 19348 2 1 1159 }
id-at-zimbraForceClearCookies OBJECT IDENTIFIER ::= { 1 3 6 1 4 1 19348 2 1 1437 }
id-at-zimbraForeignName OBJECT IDENTIFIER ::= { 1 3 6 1 4 1 19348 2 1 1135 }
id-at-zimbraForeignNameHandler OBJECT IDENTIFIER ::= { 1 3 6 1 4 1 19348 2 1 1136 }
id-at-zimbraForeignPrincipal OBJECT IDENTIFIER ::= { 1 3 6 1 4 1 19348 2 1 295 }
id-at-zimbraFreebusyExchangeAuthPassword OBJECT IDENTIFIER ::= { 1 3 6 1 4 1 19348 2 1 609 }
id-at-zimbraFreebusyExchangeAuthScheme OBJECT IDENTIFIER ::= { 1 3 6 1 4 1 19348 2 1 611 }
id-at-zimbraFreebusyExchangeAuthUsername OBJECT IDENTIFIER ::= { 1 3 6 1 4 1 19348 2 1 608 }
id-at-zimbraFreebusyExchangeCachedInterval OBJECT IDENTIFIER ::= { 1 3 6 1 4 1 19348 2 1 621 }
id-at-zimbraFreebusyExchangeCachedIntervalStart OBJECT IDENTIFIER ::= { 1 3 6 1 4 1 19348 2 1 620 }
id-at-zimbraFreebusyExchangeServerType OBJECT IDENTIFIER ::= { 1 3 6 1 4 1 19348 2 1 1174 }
id-at-zimbraFreebusyExchangeURL OBJECT IDENTIFIER ::= { 1 3 6 1 4 1 19348 2 1 607 }
id-at-zimbraFreebusyExchangeUserOrg OBJECT IDENTIFIER ::= { 1 3 6 1 4 1 19348 2 1 610 }
id-at-zimbraFreebusyExternalZimbraURL OBJECT IDENTIFIER ::= { 1 3 6 1 4 1 19348 2 1 1253 }
id-at-zimbraFreebusyLocalMailboxNotActive OBJECT IDENTIFIER ::= { 1 3 6 1 4 1 19348 2 1 752 }
id-at-zimbraFreebusyPropagationRetryInterval OBJECT IDENTIFIER ::= { 1 3 6 1 4 1 19348 2 1 1026 }
id-at-zimbraGalAccountId OBJECT IDENTIFIER ::= { 1 3 6 1 4 1 19348 2 1 831 }
id-at-zimbraGalAlwaysIncludeLocalCalendarResources OBJECT IDENTIFIER ::= { 1 3 6 1 4 1 19348 2 1 1093 }
id-at-zimbraGalAutoCompleteLdapFilter OBJECT IDENTIFIER ::= { 1 3 6 1 4 1 19348 2 1 360 }
id-at-zimbraGalDefinitionLastModifiedTime OBJECT IDENTIFIER ::= { 1 3 6 1 4 1 19348 2 1 1413 }
id-at-zimbraGalGroupIndicatorEnabled OBJECT IDENTIFIER ::= { 1 3 6 1 4 1 19348 2 1 1153 }
id-at-zimbraGalInternalSearchBase OBJECT IDENTIFIER ::= { 1 3 6 1 4 1 19348 2 1 358 }
id-at-zimbraGalLastFailedSyncTimestamp OBJECT IDENTIFIER ::= { 1 3 6 1 4 1 19348 2 1 829 }
id-at-zimbraGalLastSuccessfulSyncTimestamp OBJECT IDENTIFIER ::= { 1 3 6 1 4 1 19348 2 1 828 }
id-at-zimbraGalLdapAttrMap OBJECT IDENTIFIER ::= { 1 3 6 1 4 1 19348 2 1 153 }
id-at-zimbraGalLdapAuthMech OBJECT IDENTIFIER ::= { 1 3 6 1 4 1 19348 2 1 549 }
id-at-zimbraGalLdapBindDn OBJECT IDENTIFIER ::= { 1 3 6 1 4 1 19348 2 1 49 }
id-at-zimbraGalLdapBindPassword OBJECT IDENTIFIER ::= { 1 3 6 1 4 1 19348 2 1 50 }
id-at-zimbraGalLdapFilter OBJECT IDENTIFIER ::= { 1 3 6 1 4 1 19348 2 1 51 }
id-at-zimbraGalLdapFilterDef OBJECT IDENTIFIER ::= { 1 3 6 1 4 1 19348 2 1 52 }
id-at-zimbraGalLdapGroupHandlerClass OBJECT IDENTIFIER ::= { 1 3 6 1 4 1 19348 2 1 1112 }
id-at-zimbraGalLdapKerberos5Keytab OBJECT IDENTIFIER ::= { 1 3 6 1 4 1 19348 2 1 551 }
id-at-zimbraGalLdapKerberos5Principal OBJECT IDENTIFIER ::= { 1 3 6 1 4 1 19348 2 1 550 }
id-at-zimbraGalLdapPageSize OBJECT IDENTIFIER ::= { 1 3 6 1 4 1 19348 2 1 583 }
id-at-zimbraGalLdapSearchBase OBJECT IDENTIFIER ::= { 1 3 6 1 4 1 19348 2 1 48 }
id-at-zimbraGalLdapStartTlsEnabled OBJECT IDENTIFIER ::= { 1 3 6 1 4 1 19348 2 1 655 }
id-at-zimbraGalLdapURL OBJECT IDENTIFIER ::= { 1 3 6 1 4 1 19348 2 1 47 }
id-at-zimbraGalLdapValueMap OBJECT IDENTIFIER ::= { 1 3 6 1 4 1 19348 2 1 1110 }
id-at-zimbraGalMaxResults OBJECT IDENTIFIER ::= { 1 3 6 1 4 1 19348 2 1 53 }
id-at-zimbraGalMode OBJECT IDENTIFIER ::= { 1 3 6 1 4 1 19348 2 1 46 }
id-at-zimbraGalStatus OBJECT IDENTIFIER ::= { 1 3 6 1 4 1 19348 2 1 830 }
id-at-zimbraGalSyncAccountBasedAutoCompleteEnabled OBJECT IDENTIFIER ::= { 1 3 6 1 4 1 19348 2 1 1027 }
id-at-zimbraGalSyncIgnoredAttributes OBJECT IDENTIFIER ::= { 1 3 6 1 4 1 19348 2 1 1145 }
id-at-zimbraGalSyncInternalSearchBase OBJECT IDENTIFIER ::= { 1 3 6 1 4 1 19348 2 1 598 }
id-at-zimbraGalSyncLdapAuthMech OBJECT IDENTIFIER ::= { 1 3 6 1 4 1 19348 2 1 592 }
id-at-zimbraGalSyncLdapBindDn OBJECT IDENTIFIER ::= { 1 3 6 1 4 1 19348 2 1 593 }
id-at-zimbraGalSyncLdapBindPassword OBJECT IDENTIFIER ::= { 1 3 6 1 4 1 19348 2 1 594 }
id-at-zimbraGalSyncLdapFilter OBJECT IDENTIFIER ::= { 1 3 6 1 4 1 19348 2 1 591 }
id-at-zimbraGalSyncLdapKerberos5Keytab OBJECT IDENTIFIER ::= { 1 3 6 1 4 1 19348 2 1 596 }
id-at-zimbraGalSyncLdapKerberos5Principal OBJECT IDENTIFIER ::= { 1 3 6 1 4 1 19348 2 1 595 }
id-at-zimbraGalSyncLdapPageSize OBJECT IDENTIFIER ::= { 1 3 6 1 4 1 19348 2 1 597 }
id-at-zimbraGalSyncLdapSearchBase OBJECT IDENTIFIER ::= { 1 3 6 1 4 1 19348 2 1 590 }
id-at-zimbraGalSyncLdapStartTlsEnabled OBJECT IDENTIFIER ::= { 1 3 6 1 4 1 19348 2 1 656 }
id-at-zimbraGalSyncLdapURL OBJECT IDENTIFIER ::= { 1 3 6 1 4 1 19348 2 1 589 }
id-at-zimbraGalSyncMaxConcurrentClients OBJECT IDENTIFIER ::= { 1 3 6 1 4 1 19348 2 1 1154 }
id-at-zimbraGalSyncTimestampFormat OBJECT IDENTIFIER ::= { 1 3 6 1 4 1 19348 2 1 1019 }
id-at-zimbraGalTokenizeAutoCompleteKey OBJECT IDENTIFIER ::= { 1 3 6 1 4 1 19348 2 1 599 }
id-at-zimbraGalTokenizeSearchKey OBJECT IDENTIFIER ::= { 1 3 6 1 4 1 19348 2 1 600 }
id-at-zimbraGalType OBJECT IDENTIFIER ::= { 1 3 6 1 4 1 19348 2 1 850 }
id-at-zimbraGlobalConfigExtraObjectClass OBJECT IDENTIFIER ::= { 1 3 6 1 4 1 19348 2 1 1254 }
id-at-zimbraGroupId OBJECT IDENTIFIER ::= { 1 3 6 1 4 1 19348 2 1 325 }
id-at-zimbraHelpAdminURL OBJECT IDENTIFIER ::= { 1 3 6 1 4 1 19348 2 1 674 }
id-at-zimbraHelpAdvancedURL OBJECT IDENTIFIER ::= { 1 3 6 1 4 1 19348 2 1 676 }
id-at-zimbraHelpDelegatedURL OBJECT IDENTIFIER ::= { 1 3 6 1 4 1 19348 2 1 675 }
id-at-zimbraHelpStandardURL OBJECT IDENTIFIER ::= { 1 3 6 1 4 1 19348 2 1 677 }
id-at-zimbraHideInGal OBJECT IDENTIFIER ::= { 1 3 6 1 4 1 19348 2 1 353 }
id-at-zimbraHsmAge OBJECT IDENTIFIER ::= { 1 3 6 1 4 1 19348 2 1 8 }
id-at-zimbraHsmBatchSize OBJECT IDENTIFIER ::= { 1 3 6 1 4 1 19348 2 1 1316 }
id-at-zimbraHsmMovePreviousRevisions OBJECT IDENTIFIER ::= { 1 3 6 1 4 1 19348 2 1 1393 }
id-at-zimbraHsmPolicy OBJECT IDENTIFIER ::= { 1 3 6 1 4 1 19348 2 1 1024 }
id-at-zimbraHttpCompressionEnabled OBJECT IDENTIFIER ::= { 1 3 6 1 4 1 19348 2 1 1467 }
id-at-zimbraHttpConnectorMaxIdleTimeMillis OBJECT IDENTIFIER ::= { 1 3 6 1 4 1 19348 2 1 1428 }
id-at-zimbraHttpContextPathBasedThreadPoolBalancingFilterRules OBJECT IDENTIFIER ::= { 1 3 6 1 4 1 19348 2 1 1593 }
id-at-zimbraHttpDebugHandlerEnabled OBJECT IDENTIFIER ::= { 1 3 6 1 4 1 19348 2 1 1043 }
id-at-zimbraHttpDosFilterDelayMillis OBJECT IDENTIFIER ::= { 1 3 6 1 4 1 19348 2 1 1430 }
id-at-zimbraHttpDosFilterMaxRequestsPerSec OBJECT IDENTIFIER ::= { 1 3 6 1 4 1 19348 2 1 1431 }
id-at-zimbraHttpHeaderCacheSize OBJECT IDENTIFIER ::= { 1 3 6 1 4 1 19348 2 1 1582 }
id-at-zimbraHttpMaxFormContentSize OBJECT IDENTIFIER ::= { 1 3 6 1 4 1 19348 2 1 1612 }
id-at-zimbraHttpNumThreads OBJECT IDENTIFIER ::= { 1 3 6 1 4 1 19348 2 1 518 }
id-at-zimbraHttpOutputBufferSize OBJECT IDENTIFIER ::= { 1 3 6 1 4 1 19348 2 1 1579 }
id-at-zimbraHttpProxyURL OBJECT IDENTIFIER ::= { 1 3 6 1 4 1 19348 2 1 388 }
id-at-zimbraHttpRequestHeaderSize OBJECT IDENTIFIER ::= { 1 3 6 1 4 1 19348 2 1 1580 }
id-at-zimbraHttpResponseHeaderSize OBJECT IDENTIFIER ::= { 1 3 6 1 4 1 19348 2 1 1581 }
id-at-zimbraHttpSSLNumThreads OBJECT IDENTIFIER ::= { 1 3 6 1 4 1 19348 2 1 519 }
id-at-zimbraHttpThreadPoolMaxIdleTimeMillis OBJECT IDENTIFIER ::= { 1 3 6 1 4 1 19348 2 1 1429 }
id-at-zimbraHttpThrottleSafeIPs OBJECT IDENTIFIER ::= { 1 3 6 1 4 1 19348 2 1 1427 }
id-at-zimbraIMAvailableInteropGateways OBJECT IDENTIFIER ::= { 1 3 6 1 4 1 19348 2 1 571 }
id-at-zimbraIMBindAddress OBJECT IDENTIFIER ::= { 1 3 6 1 4 1 19348 2 1 567 }
id-at-zimbraIMService OBJECT IDENTIFIER ::= { 1 3 6 1 4 1 19348 2 1 762 }
id-at-zimbraIPMode OBJECT IDENTIFIER ::= { 1 3 6 1 4 1 19348 2 1 1171 }
id-at-zimbraId OBJECT IDENTIFIER ::= { 1 3 6 1 4 1 19348 2 1 1 }
id-at-zimbraIdentityMaxNumEntries OBJECT IDENTIFIER ::= { 1 3 6 1 4 1 19348 2 1 414 }
id-at-zimbraImapAdvertisedName OBJECT IDENTIFIER ::= { 1 3 6 1 4 1 19348 2 1 178 }
id-at-zimbraImapBindAddress OBJECT IDENTIFIER ::= { 1 3 6 1 4 1 19348 2 1 179 }
id-at-zimbraImapBindOnStartup OBJECT IDENTIFIER ::= { 1 3 6 1 4 1 19348 2 1 268 }
id-at-zimbraImapBindPort OBJECT IDENTIFIER ::= { 1 3 6 1 4 1 19348 2 1 180 }
id-at-zimbraImapCleartextLoginEnabled OBJECT IDENTIFIER ::= { 1 3 6 1 4 1 19348 2 1 185 }
id-at-zimbraImapDisabledCapability OBJECT IDENTIFIER ::= { 1 3 6 1 4 1 19348 2 1 443 }
id-at-zimbraImapEnabled OBJECT IDENTIFIER ::= { 1 3 6 1 4 1 19348 2 1 174 }
id-at-zimbraImapExposeVersionOnBanner OBJECT IDENTIFIER ::= { 1 3 6 1 4 1 19348 2 1 693 }
id-at-zimbraImapMaxConnections OBJECT IDENTIFIER ::= { 1 3 6 1 4 1 19348 2 1 1156 }
id-at-zimbraImapMaxRequestSize OBJECT IDENTIFIER ::= { 1 3 6 1 4 1 19348 2 1 1085 }
id-at-zimbraImapNumThreads OBJECT IDENTIFIER ::= { 1 3 6 1 4 1 19348 2 1 181 }
id-at-zimbraImapProxyBindPort OBJECT IDENTIFIER ::= { 1 3 6 1 4 1 19348 2 1 348 }
id-at-zimbraImapSSLBindAddress OBJECT IDENTIFIER ::= { 1 3 6 1 4 1 19348 2 1 182 }
id-at-zimbraImapSSLBindOnStartup OBJECT IDENTIFIER ::= { 1 3 6 1 4 1 19348 2 1 269 }
id-at-zimbraImapSSLBindPort OBJECT IDENTIFIER ::= { 1 3 6 1 4 1 19348 2 1 183 }
id-at-zimbraImapSSLDisabledCapability OBJECT IDENTIFIER ::= { 1 3 6 1 4 1 19348 2 1 444 }
id-at-zimbraImapSSLProxyBindPort OBJECT IDENTIFIER ::= { 1 3 6 1 4 1 19348 2 1 349 }
id-at-zimbraImapSSLServerEnabled OBJECT IDENTIFIER ::= { 1 3 6 1 4 1 19348 2 1 184 }
id-at-zimbraImapSaslGssapiEnabled OBJECT IDENTIFIER ::= { 1 3 6 1 4 1 19348 2 1 555 }
id-at-zimbraImapServerEnabled OBJECT IDENTIFIER ::= { 1 3 6 1 4 1 19348 2 1 176 }
id-at-zimbraImapShutdownGraceSeconds OBJECT IDENTIFIER ::= { 1 3 6 1 4 1 19348 2 1 1080 }
id-at-zimbraInstalledSkin OBJECT IDENTIFIER ::= { 1 3 6 1 4 1 19348 2 1 368 }
id-at-zimbraInterceptAddress OBJECT IDENTIFIER ::= { 1 3 6 1 4 1 19348 2 1 614 }
id-at-zimbraInterceptBody OBJECT IDENTIFIER ::= { 1 3 6 1 4 1 19348 2 1 618 }
id-at-zimbraInterceptFrom OBJECT IDENTIFIER ::= { 1 3 6 1 4 1 19348 2 1 616 }
id-at-zimbraInterceptSendHeadersOnly OBJECT IDENTIFIER ::= { 1 3 6 1 4 1 19348 2 1 615 }
id-at-zimbraInterceptSubject OBJECT IDENTIFIER ::= { 1 3 6 1 4 1 19348 2 1 617 }
id-at-zimbraInternalSendersDomain OBJECT IDENTIFIER ::= { 1 3 6 1 4 1 19348 2 1 1319 }
id-at-zimbraInternalSharingCrossDomainEnabled OBJECT IDENTIFIER ::= { 1 3 6 1 4 1 19348 2 1 1386 }
id-at-zimbraInternalSharingDomain OBJECT IDENTIFIER ::= { 1 3 6 1 4 1 19348 2 1 1387 }
id-at-zimbraInvalidLoginFilterDelayInMinBetwnReqBeforeReinstating OBJECT IDENTIFIER ::= { 1 3 6 1 4 1 19348 2 1 1614 }
id-at-zimbraInvalidLoginFilterMaxFailedLogin OBJECT IDENTIFIER ::= { 1 3 6 1 4 1 19348 2 1 1613 }
id-at-zimbraInvalidLoginFilterMaxSizeOfFailedIpDb OBJECT IDENTIFIER ::= { 1 3 6 1 4 1 19348 2 1 1618 }
id-at-zimbraInvalidLoginFilterReinstateIpTaskIntervalInMin OBJECT IDENTIFIER ::= { 1 3 6 1 4 1 19348 2 1 1615 }
id-at-zimbraIsACLGroup OBJECT IDENTIFIER ::= { 1 3 6 1 4 1 19348 2 1 1242 }
id-at-zimbraIsAdminAccount OBJECT IDENTIFIER ::= { 1 3 6 1 4 1 19348 2 1 31 }
id-at-zimbraIsAdminGroup OBJECT IDENTIFIER ::= { 1 3 6 1 4 1 19348 2 1 802 }
id-at-zimbraIsCustomerCareAccount OBJECT IDENTIFIER ::= { 1 3 6 1 4 1 19348 2 1 601 }
id-at-zimbraIsDelegatedAdminAccount OBJECT IDENTIFIER ::= { 1 3 6 1 4 1 19348 2 1 852 }
id-at-zimbraIsDomainAdminAccount OBJECT IDENTIFIER ::= { 1 3 6 1 4 1 19348 2 1 298 }
id-at-zimbraIsExternalVirtualAccount OBJECT IDENTIFIER ::= { 1 3 6 1 4 1 19348 2 1 1243 }
id-at-zimbraIsMonitorHost OBJECT IDENTIFIER ::= { 1 3 6 1 4 1 19348 2 1 132 }
id-at-zimbraIsSystemAccount OBJECT IDENTIFIER ::= { 1 3 6 1 4 1 19348 2 1 1214 }
id-at-zimbraIsSystemResource OBJECT IDENTIFIER ::= { 1 3 6 1 4 1 19348 2 1 376 }
id-at-zimbraItemActionBatchSize OBJECT IDENTIFIER ::= { 1 3 6 1 4 1 19348 2 1 1451 }
id-at-zimbraJunkMessagesIndexingEnabled OBJECT IDENTIFIER ::= { 1 3 6 1 4 1 19348 2 1 579 }
id-at-zimbraLastLogonTimestamp OBJECT IDENTIFIER ::= { 1 3 6 1 4 1 19348 2 1 113 }
id-at-zimbraLastLogonTimestampFrequency OBJECT IDENTIFIER ::= { 1 3 6 1 4 1 19348 2 1 114 }
id-at-zimbraLastPurgeMaxDuration OBJECT IDENTIFIER ::= { 1 3 6 1 4 1 19348 2 1 1382 }
id-at-zimbraLdapGalSyncDisabled OBJECT IDENTIFIER ::= { 1 3 6 1 4 1 19348 2 1 1420 }
id-at-zimbraLmtpAdvertisedName OBJECT IDENTIFIER ::= { 1 3 6 1 4 1 19348 2 1 23 }
id-at-zimbraLmtpBindAddress OBJECT IDENTIFIER ::= { 1 3 6 1 4 1 19348 2 1 25 }
id-at-zimbraLmtpBindOnStartup OBJECT IDENTIFIER ::= { 1 3 6 1 4 1 19348 2 1 270 }
id-at-zimbraLmtpBindPort OBJECT IDENTIFIER ::= { 1 3 6 1 4 1 19348 2 1 24 }
id-at-zimbraLmtpExposeVersionOnBanner OBJECT IDENTIFIER ::= { 1 3 6 1 4 1 19348 2 1 691 }
id-at-zimbraLmtpLHLORequired OBJECT IDENTIFIER ::= { 1 3 6 1 4 1 19348 2 1 1675 }
id-at-zimbraLmtpNumThreads OBJECT IDENTIFIER ::= { 1 3 6 1 4 1 19348 2 1 26 }
id-at-zimbraLmtpPermanentFailureWhenOverQuota OBJECT IDENTIFIER ::= { 1 3 6 1 4 1 19348 2 1 657 }
id-at-zimbraLmtpServerEnabled OBJECT IDENTIFIER ::= { 1 3 6 1 4 1 19348 2 1 630 }
id-at-zimbraLmtpShutdownGraceSeconds OBJECT IDENTIFIER ::= { 1 3 6 1 4 1 19348 2 1 1082 }
id-at-zimbraLocale OBJECT IDENTIFIER ::= { 1 3 6 1 4 1 19348 2 1 345 }
id-at-zimbraLogHostname OBJECT IDENTIFIER ::= { 1 3 6 1 4 1 19348 2 1 250 }
id-at-zimbraLogOutFromAllServers OBJECT IDENTIFIER ::= { 1 3 6 1 4 1 19348 2 1 1634 }
id-at-zimbraLogRawLifetime OBJECT IDENTIFIER ::= { 1 3 6 1 4 1 19348 2 1 263 }
id-at-zimbraLogSummaryLifetime OBJECT IDENTIFIER ::= { 1 3 6 1 4 1 19348 2 1 264 }
id-at-zimbraLogToSyslog OBJECT IDENTIFIER ::= { 1 3 6 1 4 1 19348 2 1 520 }
id-at-zimbraLowestSupportedAuthVersion OBJECT IDENTIFIER ::= { 1 3 6 1 4 1 19348 2 1 1589 }
id-at-zimbraMailAddress OBJECT IDENTIFIER ::= { 1 3 6 1 4 1 19348 2 1 3 }
id-at-zimbraMailAddressValidationRegex OBJECT IDENTIFIER ::= { 1 3 6 1 4 1 19348 2 1 1241 }
id-at-zimbraMailAlias OBJECT IDENTIFIER ::= { 1 3 6 1 4 1 19348 2 1 20 }
id-at-zimbraMailAllowReceiveButNotSendWhenOverQuota OBJECT IDENTIFIER ::= { 1 3 6 1 4 1 19348 2 1 1099 }
id-at-zimbraMailBindAddress OBJECT IDENTIFIER ::= { 1 3 6 1 4 1 19348 2 1 1365 }
id-at-zimbraMailBlacklistMaxNumEntries OBJECT IDENTIFIER ::= { 1 3 6 1 4 1 19348 2 1 799 }
id-at-zimbraMailCanonicalAddress OBJECT IDENTIFIER ::= { 1 3 6 1 4 1 19348 2 1 213 }
id-at-zimbraMailCatchAllAddress OBJECT IDENTIFIER ::= { 1 3 6 1 4 1 19348 2 1 214 }
id-at-zimbraMailCatchAllCanonicalAddress OBJECT IDENTIFIER ::= { 1 3 6 1 4 1 19348 2 1 216 }
id-at-zimbraMailCatchAllForwardingAddress OBJECT IDENTIFIER ::= { 1 3 6 1 4 1 19348 2 1 215 }
id-at-zimbraMailClearTextPasswordEnabled OBJECT IDENTIFIER ::= { 1 3 6 1 4 1 19348 2 1 791 }
id-at-zimbraMailContentMaxSize OBJECT IDENTIFIER ::= { 1 3 6 1 4 1 19348 2 1 807 }
id-at-zimbraMailDeliveryAddress OBJECT IDENTIFIER ::= { 1 3 6 1 4 1 19348 2 1 13 }
id-at-zimbraMailDiskStreamingThreshold OBJECT IDENTIFIER ::= { 1 3 6 1 4 1 19348 2 1 565 }
id-at-zimbraMailDomainQuota OBJECT IDENTIFIER ::= { 1 3 6 1 4 1 19348 2 1 1326 }
id-at-zimbraMailDumpsterLifetime OBJECT IDENTIFIER ::= { 1 3 6 1 4 1 19348 2 1 1133 }
id-at-zimbraMailEmptyFolderBatchSize OBJECT IDENTIFIER ::= { 1 3 6 1 4 1 19348 2 1 1097 }
id-at-zimbraMailEmptyFolderBatchThreshold OBJECT IDENTIFIER ::= { 1 3 6 1 4 1 19348 2 1 1208 }
id-at-zimbraMailFileDescriptorBufferSize OBJECT IDENTIFIER ::= { 1 3 6 1 4 1 19348 2 1 1035 }
id-at-zimbraMailFileDescriptorCacheSize OBJECT IDENTIFIER ::= { 1 3 6 1 4 1 19348 2 1 1034 }
id-at-zimbraMailForwardingAddress OBJECT IDENTIFIER ::= { 1 3 6 1 4 1 19348 2 1 12 }
id-at-zimbraMailForwardingAddressMaxLength OBJECT IDENTIFIER ::= { 1 3 6 1 4 1 19348 2 1 1039 }
id-at-zimbraMailForwardingAddressMaxNumAddrs OBJECT IDENTIFIER ::= { 1 3 6 1 4 1 19348 2 1 1040 }
id-at-zimbraMailHighlightObjectsMaxSize OBJECT IDENTIFIER ::= { 1 3 6 1 4 1 19348 2 1 1213 }
id-at-zimbraMailHost OBJECT IDENTIFIER ::= { 1 3 6 1 4 1 19348 2 1 4 }
id-at-zimbraMailHostPool OBJECT IDENTIFIER ::= { 1 3 6 1 4 1 19348 2 1 125 }
id-at-zimbraMailIdleSessionTimeout OBJECT IDENTIFIER ::= { 1 3 6 1 4 1 19348 2 1 147 }
id-at-zimbraMailKeepOutWebCrawlers OBJECT IDENTIFIER ::= { 1 3 6 1 4 1 19348 2 1 1161 }
id-at-zimbraMailLastPurgedMailboxId OBJECT IDENTIFIER ::= { 1 3 6 1 4 1 19348 2 1 543 }
id-at-zimbraMailLocalBind OBJECT IDENTIFIER ::= { 1 3 6 1 4 1 19348 2 1 1380 }
id-at-zimbraMailMessageLifetime OBJECT IDENTIFIER ::= { 1 3 6 1 4 1 19348 2 1 106 }
id-at-zimbraMailMinPollingInterval OBJECT IDENTIFIER ::= { 1 3 6 1 4 1 19348 2 1 110 }
id-at-zimbraMailMode OBJECT IDENTIFIER ::= { 1 3 6 1 4 1 19348 2 1 308 }
id-at-zimbraMailOutgoingSieveScript OBJECT IDENTIFIER ::= { 1 3 6 1 4 1 19348 2 1 1130 }
id-at-zimbraMailPort OBJECT IDENTIFIER ::= { 1 3 6 1 4 1 19348 2 1 154 }
id-at-zimbraMailProxyMaxFails OBJECT IDENTIFIER ::= { 1 3 6 1 4 1 19348 2 1 1358 }
id-at-zimbraMailProxyPort OBJECT IDENTIFIER ::= { 1 3 6 1 4 1 19348 2 1 626 }
id-at-zimbraMailProxyReconnectTimeout OBJECT IDENTIFIER ::= { 1 3 6 1 4 1 19348 2 1 1268 }
id-at-zimbraMailPurgeBatchSize OBJECT IDENTIFIER ::= { 1 3 6 1 4 1 19348 2 1 1096 }
id-at-zimbraMailPurgeSleepInterval OBJECT IDENTIFIER ::= { 1 3 6 1 4 1 19348 2 1 542 }
id-at-zimbraMailPurgeSystemPolicy OBJECT IDENTIFIER ::= { 1 3 6 1 4 1 19348 2 1 1239 }
id-at-zimbraMailPurgeUseChangeDateForSpam OBJECT IDENTIFIER ::= { 1 3 6 1 4 1 19348 2 1 1117 }
id-at-zimbraMailPurgeUseChangeDateForTrash OBJECT IDENTIFIER ::= { 1 3 6 1 4 1 19348 2 1 748 }
id-at-zimbraMailQuota OBJECT IDENTIFIER ::= { 1 3 6 1 4 1 19348 2 1 16 }
id-at-zimbraMailRedirectSetEnvelopeSender OBJECT IDENTIFIER ::= { 1 3 6 1 4 1 19348 2 1 764 }
id-at-zimbraMailReferMode OBJECT IDENTIFIER ::= { 1 3 6 1 4 1 19348 2 1 613 }
id-at-zimbraMailSSLBindAddress OBJECT IDENTIFIER ::= { 1 3 6 1 4 1 19348 2 1 1366 }
id-at-zimbraMailSSLClientCertBindAddress OBJECT IDENTIFIER ::= { 1 3 6 1 4 1 19348 2 1 1367 }
id-at-zimbraMailSSLClientCertMode OBJECT IDENTIFIER ::= { 1 3 6 1 4 1 19348 2 1 1190 }
id-at-zimbraMailSSLClientCertOCSPEnabled OBJECT IDENTIFIER ::= { 1 3 6 1 4 1 19348 2 1 1395 }
id-at-zimbraMailSSLClientCertPort OBJECT IDENTIFIER ::= { 1 3 6 1 4 1 19348 2 1 1199 }
id-at-zimbraMailSSLClientCertPrincipalMap OBJECT IDENTIFIER ::= { 1 3 6 1 4 1 19348 2 1 1215 }
id-at-zimbraMailSSLClientCertPrincipalMapLdapFilterEnabled OBJECT IDENTIFIER ::= { 1 3 6 1 4 1 19348 2 1 1216 }
id-at-zimbraMailSSLPort OBJECT IDENTIFIER ::= { 1 3 6 1 4 1 19348 2 1 166 }
id-at-zimbraMailSSLProxyClientCertPort OBJECT IDENTIFIER ::= { 1 3 6 1 4 1 19348 2 1 1212 }
id-at-zimbraMailSSLProxyPort OBJECT IDENTIFIER ::= { 1 3 6 1 4 1 19348 2 1 627 }
id-at-zimbraMailSieveScript OBJECT IDENTIFIER ::= { 1 3 6 1 4 1 19348 2 1 32 }
id-at-zimbraMailSignatureMaxLength OBJECT IDENTIFIER ::= { 1 3 6 1 4 1 19348 2 1 454 }
id-at-zimbraMailSpamLifetime OBJECT IDENTIFIER ::= { 1 3 6 1 4 1 19348 2 1 105 }
id-at-zimbraMailStatus OBJECT IDENTIFIER ::= { 1 3 6 1 4 1 19348 2 1 15 }
id-at-zimbraMailThreadingAlgorithm OBJECT IDENTIFIER ::= { 1 3 6 1 4 1 19348 2 1 1160 }
id-at-zimbraMailTransport OBJECT IDENTIFIER ::= { 1 3 6 1 4 1 19348 2 1 247 }
id-at-zimbraMailTrashLifetime OBJECT IDENTIFIER ::= { 1 3 6 1 4 1 19348 2 1 104 }
id-at-zimbraMailTrustedIP OBJECT IDENTIFIER ::= { 1 3 6 1 4 1 19348 2 1 1025 }
id-at-zimbraMailTrustedSenderListMaxNumEntries OBJECT IDENTIFIER ::= { 1 3 6 1 4 1 19348 2 1 1139 }
id-at-zimbraMailURL OBJECT IDENTIFIER ::= { 1 3 6 1 4 1 19348 2 1 340 }
id-at-zimbraMailUncompressedCacheMaxBytes OBJECT IDENTIFIER ::= { 1 3 6 1 4 1 19348 2 1 825 }
id-at-zimbraMailUncompressedCacheMaxFiles OBJECT IDENTIFIER ::= { 1 3 6 1 4 1 19348 2 1 824 }
id-at-zimbraMailUseDirectBuffers OBJECT IDENTIFIER ::= { 1 3 6 1 4 1 19348 2 1 1002 }
id-at-zimbraMailWhitelistMaxNumEntries OBJECT IDENTIFIER ::= { 1 3 6 1 4 1 19348 2 1 798 }
id-at-zimbraMailboxLocationBeforeMove OBJECT IDENTIFIER ::= { 1 3 6 1 4 1 19348 2 1 346 }
id-at-zimbraMailboxMoveSkipBlobs OBJECT IDENTIFIER ::= { 1 3 6 1 4 1 19348 2 1 1007 }
id-at-zimbraMailboxMoveSkipHsmBlobs OBJECT IDENTIFIER ::= { 1 3 6 1 4 1 19348 2 1 1008 }
id-at-zimbraMailboxMoveSkipSearchIndex OBJECT IDENTIFIER ::= { 1 3 6 1 4 1 19348 2 1 1006 }
id-at-zimbraMailboxMoveTempDir OBJECT IDENTIFIER ::= { 1 3 6 1 4 1 19348 2 1 1175 }
id-at-zimbraMailboxdSSLProtocols OBJECT IDENTIFIER ::= { 1 3 6 1 4 1 19348 2 1 1657 }
id-at-zimbraMaxContactsPerPage OBJECT IDENTIFIER ::= { 1 3 6 1 4 1 19348 2 1 1012 }
id-at-zimbraMaxMailItemsPerPage OBJECT IDENTIFIER ::= { 1 3 6 1 4 1 19348 2 1 1011 }
id-at-zimbraMaxVoiceItemsPerPage OBJECT IDENTIFIER ::= { 1 3 6 1 4 1 19348 2 1 1013 }
id-at-zimbraMemberOf OBJECT IDENTIFIER ::= { 1 3 6 1 4 1 19348 2 1 11 }
id-at-zimbraMemcachedBindAddress OBJECT IDENTIFIER ::= { 1 3 6 1 4 1 19348 2 1 581 }
id-at-zimbraMemcachedBindPort OBJECT IDENTIFIER ::= { 1 3 6 1 4 1 19348 2 1 580 }
id-at-zimbraMemcachedClientBinaryProtocolEnabled OBJECT IDENTIFIER ::= { 1 3 6 1 4 1 19348 2 1 1015 }
id-at-zimbraMemcachedClientExpirySeconds OBJECT IDENTIFIER ::= { 1 3 6 1 4 1 19348 2 1 1017 }
id-at-zimbraMemcachedClientHashAlgorithm OBJECT IDENTIFIER ::= { 1 3 6 1 4 1 19348 2 1 1016 }
id-at-zimbraMemcachedClientServerList OBJECT IDENTIFIER ::= { 1 3 6 1 4 1 19348 2 1 1014 }
id-at-zimbraMemcachedClientTimeoutMillis OBJECT IDENTIFIER ::= { 1 3 6 1 4 1 19348 2 1 1018 }
id-at-zimbraMessageCacheSize OBJECT IDENTIFIER ::= { 1 3 6 1 4 1 19348 2 1 297 }
id-at-zimbraMessageChannelEnabled OBJECT IDENTIFIER ::= { 1 3 6 1 4 1 19348 2 1 1417 }
id-at-zimbraMessageChannelPort OBJECT IDENTIFIER ::= { 1 3 6 1 4 1 19348 2 1 1415 }
id-at-zimbraMessageIdDedupeCacheSize OBJECT IDENTIFIER ::= { 1 3 6 1 4 1 19348 2 1 334 }
id-at-zimbraMessageIdDedupeCacheTimeout OBJECT IDENTIFIER ::= { 1 3 6 1 4 1 19348 2 1 1340 }
id-at-zimbraMilterBindAddress OBJECT IDENTIFIER ::= { 1 3 6 1 4 1 19348 2 1 1115 }
id-at-zimbraMilterBindPort OBJECT IDENTIFIER ::= { 1 3 6 1 4 1 19348 2 1 1114 }
id-at-zimbraMilterMaxConnections OBJECT IDENTIFIER ::= { 1 3 6 1 4 1 19348 2 1 1157 }
id-at-zimbraMilterNumThreads OBJECT IDENTIFIER ::= { 1 3 6 1 4 1 19348 2 1 1144 }
id-at-zimbraMilterServerEnabled OBJECT IDENTIFIER ::= { 1 3 6 1 4 1 19348 2 1 1116 }
id-at-zimbraMimeFileExtension OBJECT IDENTIFIER ::= { 1 3 6 1 4 1 19348 2 1 160 }
id-at-zimbraMimeHandlerClass OBJECT IDENTIFIER ::= { 1 3 6 1 4 1 19348 2 1 159 }
id-at-zimbraMimeHandlerExtension OBJECT IDENTIFIER ::= { 1 3 6 1 4 1 19348 2 1 293 }
id-at-zimbraMimeIndexingEnabled OBJECT IDENTIFIER ::= { 1 3 6 1 4 1 19348 2 1 158 }
id-at-zimbraMimePriority OBJECT IDENTIFIER ::= { 1 3 6 1 4 1 19348 2 1 503 }
id-at-zimbraMimeType OBJECT IDENTIFIER ::= { 1 3 6 1 4 1 19348 2 1 157 }
id-at-zimbraMobileAttachSkippedItemEnabled OBJECT IDENTIFIER ::= { 1 3 6 1 4 1 19348 2 1 1423 }
id-at-zimbraMobileForceProtocol25 OBJECT IDENTIFIER ::= { 1 3 6 1 4 1 19348 2 1 1573 }
id-at-zimbraMobileForceSamsungProtocol25 OBJECT IDENTIFIER ::= { 1 3 6 1 4 1 19348 2 1 1572 }
id-at-zimbraMobileItemsToTrackPerFolderMaxSize OBJECT IDENTIFIER ::= { 1 3 6 1 4 1 19348 2 1 1426 }
id-at-zimbraMobileMaxMessageSize OBJECT IDENTIFIER ::= { 1 3 6 1 4 1 19348 2 1 1596 }
id-at-zimbraMobileMetadataMaxSizeEnabled OBJECT IDENTIFIER ::= { 1 3 6 1 4 1 19348 2 1 1425 }
id-at-zimbraMobileMetadataRetentionPolicy OBJECT IDENTIFIER ::= { 1 3 6 1 4 1 19348 2 1 1617 }
id-at-zimbraMobileNotificationAdminAddress OBJECT IDENTIFIER ::= { 1 3 6 1 4 1 19348 2 1 1422 }
id-at-zimbraMobileNotificationEnabled OBJECT IDENTIFIER ::= { 1 3 6 1 4 1 19348 2 1 1421 }
id-at-zimbraMobileOutlookSyncEnabled OBJECT IDENTIFIER ::= { 1 3 6 1 4 1 19348 2 1 1453 }
id-at-zimbraMobilePolicyAllowBluetooth OBJECT IDENTIFIER ::= { 1 3 6 1 4 1 19348 2 1 1285 }
id-at-zimbraMobilePolicyAllowBrowser OBJECT IDENTIFIER ::= { 1 3 6 1 4 1 19348 2 1 1300 }
id-at-zimbraMobilePolicyAllowCamera OBJECT IDENTIFIER ::= { 1 3 6 1 4 1 19348 2 1 1278 }
id-at-zimbraMobilePolicyAllowConsumerEmail OBJECT IDENTIFIER ::= { 1 3 6 1 4 1 19348 2 1 1301 }
id-at-zimbraMobilePolicyAllowDesktopSync OBJECT IDENTIFIER ::= { 1 3 6 1 4 1 19348 2 1 1288 }
id-at-zimbraMobilePolicyAllowHTMLEmail OBJECT IDENTIFIER ::= { 1 3 6 1 4 1 19348 2 1 1290 }
id-at-zimbraMobilePolicyAllowInternetSharing OBJECT IDENTIFIER ::= { 1 3 6 1 4 1 19348 2 1 1303 }
id-at-zimbraMobilePolicyAllowIrDA OBJECT IDENTIFIER ::= { 1 3 6 1 4 1 19348 2 1 1286 }
id-at-zimbraMobilePolicyAllowNonProvisionableDevices OBJECT IDENTIFIER ::= { 1 3 6 1 4 1 19348 2 1 834 }
id-at-zimbraMobilePolicyAllowPOPIMAPEmail OBJECT IDENTIFIER ::= { 1 3 6 1 4 1 19348 2 1 1284 }
id-at-zimbraMobilePolicyAllowPartialProvisioning OBJECT IDENTIFIER ::= { 1 3 6 1 4 1 19348 2 1 835 }
id-at-zimbraMobilePolicyAllowRemoteDesktop OBJECT IDENTIFIER ::= { 1 3 6 1 4 1 19348 2 1 1302 }
id-at-zimbraMobilePolicyAllowSMIMEEncryptionAlgorithmNegotiation OBJECT IDENTIFIER ::= { 1 3 6 1 4 1 19348 2 1 1298 }
id-at-zimbraMobilePolicyAllowSMIMESoftCerts OBJECT IDENTIFIER ::= { 1 3 6 1 4 1 19348 2 1 1299 }
id-at-zimbraMobilePolicyAllowSimpleDevicePassword OBJECT IDENTIFIER ::= { 1 3 6 1 4 1 19348 2 1 839 }
id-at-zimbraMobilePolicyAllowStorageCard OBJECT IDENTIFIER ::= { 1 3 6 1 4 1 19348 2 1 1277 }
id-at-zimbraMobilePolicyAllowTextMessaging OBJECT IDENTIFIER ::= { 1 3 6 1 4 1 19348 2 1 1283 }
id-at-zimbraMobilePolicyAllowUnsignedApplications OBJECT IDENTIFIER ::= { 1 3 6 1 4 1 19348 2 1 1280 }
id-at-zimbraMobilePolicyAllowUnsignedInstallationPackages OBJECT IDENTIFIER ::= { 1 3 6 1 4 1 19348 2 1 1281 }
id-at-zimbraMobilePolicyAllowWiFi OBJECT IDENTIFIER ::= { 1 3 6 1 4 1 19348 2 1 1282 }
id-at-zimbraMobilePolicyAlphanumericDevicePasswordRequired OBJECT IDENTIFIER ::= { 1 3 6 1 4 1 19348 2 1 840 }
id-at-zimbraMobilePolicyApprovedApplication OBJECT IDENTIFIER ::= { 1 3 6 1 4 1 19348 2 1 1305 }
id-at-zimbraMobilePolicyApprovedApplicationList OBJECT IDENTIFIER ::= { 1 3 6 1 4 1 19348 2 1 1411 }
id-at-zimbraMobilePolicyDeviceEncryptionEnabled OBJECT IDENTIFIER ::= { 1 3 6 1 4 1 19348 2 1 847 }
id-at-zimbraMobilePolicyDevicePasswordEnabled OBJECT IDENTIFIER ::= { 1 3 6 1 4 1 19348 2 1 837 }
id-at-zimbraMobilePolicyDevicePasswordExpiration OBJECT IDENTIFIER ::= { 1 3 6 1 4 1 19348 2 1 842 }
id-at-zimbraMobilePolicyDevicePasswordHistory OBJECT IDENTIFIER ::= { 1 3 6 1 4 1 19348 2 1 843 }
id-at-zimbraMobilePolicyMaxCalendarAgeFilter OBJECT IDENTIFIER ::= { 1 3 6 1 4 1 19348 2 1 1289 }
id-at-zimbraMobilePolicyMaxDevicePasswordFailedAttempts OBJECT IDENTIFIER ::= { 1 3 6 1 4 1 19348 2 1 845 }
id-at-zimbraMobilePolicyMaxEmailAgeFilter OBJECT IDENTIFIER ::= { 1 3 6 1 4 1 19348 2 1 1291 }
id-at-zimbraMobilePolicyMaxEmailBodyTruncationSize OBJECT IDENTIFIER ::= { 1 3 6 1 4 1 19348 2 1 1292 }
id-at-zimbraMobilePolicyMaxEmailHTMLBodyTruncationSize OBJECT IDENTIFIER ::= { 1 3 6 1 4 1 19348 2 1 1293 }
id-at-zimbraMobilePolicyMaxInactivityTimeDeviceLock OBJECT IDENTIFIER ::= { 1 3 6 1 4 1 19348 2 1 844 }
id-at-zimbraMobilePolicyMinDevicePasswordComplexCharacters OBJECT IDENTIFIER ::= { 1 3 6 1 4 1 19348 2 1 841 }
id-at-zimbraMobilePolicyMinDevicePasswordLength OBJECT IDENTIFIER ::= { 1 3 6 1 4 1 19348 2 1 838 }
id-at-zimbraMobilePolicyPasswordRecoveryEnabled OBJECT IDENTIFIER ::= { 1 3 6 1 4 1 19348 2 1 846 }
id-at-zimbraMobilePolicyRefreshInterval OBJECT IDENTIFIER ::= { 1 3 6 1 4 1 19348 2 1 836 }
id-at-zimbraMobilePolicyRequireDeviceEncryption OBJECT IDENTIFIER ::= { 1 3 6 1 4 1 19348 2 1 1279 }
id-at-zimbraMobilePolicyRequireEncryptedSMIMEMessages OBJECT IDENTIFIER ::= { 1 3 6 1 4 1 19348 2 1 1295 }
id-at-zimbraMobilePolicyRequireEncryptionSMIMEAlgorithm OBJECT IDENTIFIER ::= { 1 3 6 1 4 1 19348 2 1 1297 }
id-at-zimbraMobilePolicyRequireManualSyncWhenRoaming OBJECT IDENTIFIER ::= { 1 3 6 1 4 1 19348 2 1 1287 }
id-at-zimbraMobilePolicyRequireSignedSMIMEAlgorithm OBJECT IDENTIFIER ::= { 1 3 6 1 4 1 19348 2 1 1296 }
id-at-zimbraMobilePolicyRequireSignedSMIMEMessages OBJECT IDENTIFIER ::= { 1 3 6 1 4 1 19348 2 1 1294 }
id-at-zimbraMobilePolicyRequireStorageCardEncryption OBJECT IDENTIFIER ::= { 1 3 6 1 4 1 19348 2 1 1444 }
id-at-zimbraMobilePolicySuppressDeviceEncryption OBJECT IDENTIFIER ::= { 1 3 6 1 4 1 19348 2 1 1306 }
id-at-zimbraMobilePolicyUnapprovedInROMApplication OBJECT IDENTIFIER ::= { 1 3 6 1 4 1 19348 2 1 1304 }
id-at-zimbraMobileShareContactEnabled OBJECT IDENTIFIER ::= { 1 3 6 1 4 1 19348 2 1 1570 }
id-at-zimbraMobileSmartForwardRFC822Enabled OBJECT IDENTIFIER ::= { 1 3 6 1 4 1 19348 2 1 1205 }
id-at-zimbraMobileSyncKeyFormatConvertedFolders OBJECT IDENTIFIER ::= { 1 3 6 1 4 1 19348 2 1 1439 }
id-at-zimbraMobileSyncRedoMaxAttempts OBJECT IDENTIFIER ::= { 1 3 6 1 4 1 19348 2 1 1642 }
id-at-zimbraMobileTombstoneEnabled OBJECT IDENTIFIER ::= { 1 3 6 1 4 1 19348 2 1 1633 }
id-at-zimbraMtaAddressVerifyNegativeRefreshTime OBJECT IDENTIFIER ::= { 1 3 6 1 4 1 19348 2 1 1609 }
id-at-zimbraMtaAddressVerifyPollCount OBJECT IDENTIFIER ::= { 1 3 6 1 4 1 19348 2 1 1607 }
id-at-zimbraMtaAddressVerifyPollDelay OBJECT IDENTIFIER ::= { 1 3 6 1 4 1 19348 2 1 1608 }
id-at-zimbraMtaAddressVerifyPositiveRefreshTime OBJECT IDENTIFIER ::= { 1 3 6 1 4 1 19348 2 1 1610 }
id-at-zimbraMtaAliasMaps OBJECT IDENTIFIER ::= { 1 3 6 1 4 1 19348 2 1 1493 }
id-at-zimbraMtaAlwaysAddMissingHeaders OBJECT IDENTIFIER ::= { 1 3 6 1 4 1 19348 2 1 1494 }
id-at-zimbraMtaAntiSpamLockMethod OBJECT IDENTIFIER ::= { 1 3 6 1 4 1 19348 2 1 612 }
id-at-zimbraMtaAuthEnabled OBJECT IDENTIFIER ::= { 1 3 6 1 4 1 19348 2 1 194 }
id-at-zimbraMtaAuthHost OBJECT IDENTIFIER ::= { 1 3 6 1 4 1 19348 2 1 309 }
id-at-zimbraMtaAuthTarget OBJECT IDENTIFIER ::= { 1 3 6 1 4 1 19348 2 1 505 }
id-at-zimbraMtaAuthURL OBJECT IDENTIFIER ::= { 1 3 6 1 4 1 19348 2 1 310 }
id-at-zimbraMtaBlockedExtension OBJECT IDENTIFIER ::= { 1 3 6 1 4 1 19348 2 1 195 }
id-at-zimbraMtaBlockedExtensionWarnAdmin OBJECT IDENTIFIER ::= { 1 3 6 1 4 1 19348 2 1 1031 }
id-at-zimbraMtaBlockedExtensionWarnRecipient OBJECT IDENTIFIER ::= { 1 3 6 1 4 1 19348 2 1 1032 }
id-at-zimbraMtaBounceNoticeRecipient OBJECT IDENTIFIER ::= { 1 3 6 1 4 1 19348 2 1 1496 }
id-at-zimbraMtaBounceQueueLifetime OBJECT IDENTIFIER ::= { 1 3 6 1 4 1 19348 2 1 1497 }
id-at-zimbraMtaBrokenSaslAuthClients OBJECT IDENTIFIER ::= { 1 3 6 1 4 1 19348 2 1 1495 }
id-at-zimbraMtaCommandDirectory OBJECT IDENTIFIER ::= { 1 3 6 1 4 1 19348 2 1 1498 }
id-at-zimbraMtaCommonBlockedExtension OBJECT IDENTIFIER ::= { 1 3 6 1 4 1 19348 2 1 196 }
id-at-zimbraMtaDaemonDirectory OBJECT IDENTIFIER ::= { 1 3 6 1 4 1 19348 2 1 1499 }
id-at-zimbraMtaDefaultProcessLimit OBJECT IDENTIFIER ::= { 1 3 6 1 4 1 19348 2 1 1501 }
id-at-zimbraMtaDelayWarningTime OBJECT IDENTIFIER ::= { 1 3 6 1 4 1 19348 2 1 1500 }
id-at-zimbraMtaDnsLookupsEnabled OBJECT IDENTIFIER ::= { 1 3 6 1 4 1 19348 2 1 197 }
id-at-zimbraMtaEnableSmtpdPolicyd OBJECT IDENTIFIER ::= { 1 3 6 1 4 1 19348 2 1 1466 }
id-at-zimbraMtaFallbackRelayHost OBJECT IDENTIFIER ::= { 1 3 6 1 4 1 19348 2 1 1435 }
id-at-zimbraMtaHeaderChecks OBJECT IDENTIFIER ::= { 1 3 6 1 4 1 19348 2 1 1502 }
id-at-zimbraMtaImportEnvironment OBJECT IDENTIFIER ::= { 1 3 6 1 4 1 19348 2 1 1503 }
id-at-zimbraMtaInFlowDelay OBJECT IDENTIFIER ::= { 1 3 6 1 4 1 19348 2 1 1504 }
id-at-zimbraMtaLmdbMapSize OBJECT IDENTIFIER ::= { 1 3 6 1 4 1 19348 2 1 1489 }
id-at-zimbraMtaLmtpConnectionCacheDestinations OBJECT IDENTIFIER ::= { 1 3 6 1 4 1 19348 2 1 1505 }
id-at-zimbraMtaLmtpConnectionCacheTimeLimit OBJECT IDENTIFIER ::= { 1 3 6 1 4 1 19348 2 1 1506 }
id-at-zimbraMtaLmtpHostLookup OBJECT IDENTIFIER ::= { 1 3 6 1 4 1 19348 2 1 1507 }
id-at-zimbraMtaLmtpTlsCAfile OBJECT IDENTIFIER ::= { 1 3 6 1 4 1 19348 2 1 1663 }
id-at-zimbraMtaLmtpTlsCApath OBJECT IDENTIFIER ::= { 1 3 6 1 4 1 19348 2 1 1664 }
id-at-zimbraMtaLmtpTlsCiphers OBJECT IDENTIFIER ::= { 1 3 6 1 4 1 19348 2 1 1661 }
id-at-zimbraMtaLmtpTlsExcludeCiphers OBJECT IDENTIFIER ::= { 1 3 6 1 4 1 19348 2 1 1659 }
id-at-zimbraMtaLmtpTlsLoglevel OBJECT IDENTIFIER ::= { 1 3 6 1 4 1 19348 2 1 1665 }
id-at-zimbraMtaLmtpTlsMandatoryCiphers OBJECT IDENTIFIER ::= { 1 3 6 1 4 1 19348 2 1 1662 }
id-at-zimbraMtaLmtpTlsProtocols OBJECT IDENTIFIER ::= { 1 3 6 1 4 1 19348 2 1 1658 }
id-at-zimbraMtaLmtpTlsSecurityLevel OBJECT IDENTIFIER ::= { 1 3 6 1 4 1 19348 2 1 1660 }
id-at-zimbraMtaMailqPath OBJECT IDENTIFIER ::= { 1 3 6 1 4 1 19348 2 1 1508 }
id-at-zimbraMtaManpageDirectory OBJECT IDENTIFIER ::= { 1 3 6 1 4 1 19348 2 1 1509 }
id-at-zimbraMtaMaxMessageSize OBJECT IDENTIFIER ::= { 1 3 6 1 4 1 19348 2 1 198 }
id-at-zimbraMtaMaxUse OBJECT IDENTIFIER ::= { 1 3 6 1 4 1 19348 2 1 1531 }
id-at-zimbraMtaMaximalBackoffTime OBJECT IDENTIFIER ::= { 1 3 6 1 4 1 19348 2 1 1517 }
id-at-zimbraMtaMilterCommandTimeout OBJECT IDENTIFIER ::= { 1 3 6 1 4 1 19348 2 1 1521 }
id-at-zimbraMtaMilterConnectTimeout OBJECT IDENTIFIER ::= { 1 3 6 1 4 1 19348 2 1 1520 }
id-at-zimbraMtaMilterContentTimeout OBJECT IDENTIFIER ::= { 1 3 6 1 4 1 19348 2 1 1522 }
id-at-zimbraMtaMilterDefaultAction OBJECT IDENTIFIER ::= { 1 3 6 1 4 1 19348 2 1 1523 }
id-at-zimbraMtaMinimalBackoffTime OBJECT IDENTIFIER ::= { 1 3 6 1 4 1 19348 2 1 1518 }
id-at-zimbraMtaMyDestination OBJECT IDENTIFIER ::= { 1 3 6 1 4 1 19348 2 1 524 }
id-at-zimbraMtaMyHostname OBJECT IDENTIFIER ::= { 1 3 6 1 4 1 19348 2 1 509 }
id-at-zimbraMtaMyNetworks OBJECT IDENTIFIER ::= { 1 3 6 1 4 1 19348 2 1 311 }
id-at-zimbraMtaMyOrigin OBJECT IDENTIFIER ::= { 1 3 6 1 4 1 19348 2 1 510 }
id-at-zimbraMtaNewaliasesPath OBJECT IDENTIFIER ::= { 1 3 6 1 4 1 19348 2 1 1510 }
id-at-zimbraMtaNonSmtpdMilters OBJECT IDENTIFIER ::= { 1 3 6 1 4 1 19348 2 1 673 }
id-at-zimbraMtaNotifyClasses OBJECT IDENTIFIER ::= { 1 3 6 1 4 1 19348 2 1 1546 }
id-at-zimbraMtaPolicyTimeLimit OBJECT IDENTIFIER ::= { 1 3 6 1 4 1 19348 2 1 1530 }
id-at-zimbraMtaPropagateUnmatchedExtensions OBJECT IDENTIFIER ::= { 1 3 6 1 4 1 19348 2 1 1547 }
id-at-zimbraMtaQueueDirectory OBJECT IDENTIFIER ::= { 1 3 6 1 4 1 19348 2 1 1511 }
id-at-zimbraMtaQueueRunDelay OBJECT IDENTIFIER ::= { 1 3 6 1 4 1 19348 2 1 1519 }
id-at-zimbraMtaRecipientDelimiter OBJECT IDENTIFIER ::= { 1 3 6 1 4 1 19348 2 1 306 }
id-at-zimbraMtaRelayHost OBJECT IDENTIFIER ::= { 1 3 6 1 4 1 19348 2 1 199 }
id-at-zimbraMtaRestriction OBJECT IDENTIFIER ::= { 1 3 6 1 4 1 19348 2 1 226 }
id-at-zimbraMtaSaslAuthEnable OBJECT IDENTIFIER ::= { 1 3 6 1 4 1 19348 2 1 796 }
id-at-zimbraMtaSaslSmtpdMechList OBJECT IDENTIFIER ::= { 1 3 6 1 4 1 19348 2 1 1560 }
id-at-zimbraMtaSenderCanonicalMaps OBJECT IDENTIFIER ::= { 1 3 6 1 4 1 19348 2 1 1548 }
id-at-zimbraMtaSendmailPath OBJECT IDENTIFIER ::= { 1 3 6 1 4 1 19348 2 1 1512 }
id-at-zimbraMtaSmtpCnameOverridesServername OBJECT IDENTIFIER ::= { 1 3 6 1 4 1 19348 2 1 1524 }
id-at-zimbraMtaSmtpGenericMaps OBJECT IDENTIFIER ::= { 1 3 6 1 4 1 19348 2 1 1645 }
id-at-zimbraMtaSmtpHeloName OBJECT IDENTIFIER ::= { 1 3 6 1 4 1 19348 2 1 1525 }
id-at-zimbraMtaSmtpSaslAuthEnable OBJECT IDENTIFIER ::= { 1 3 6 1 4 1 19348 2 1 1526 }
id-at-zimbraMtaSmtpSaslMechanismFilter OBJECT IDENTIFIER ::= { 1 3 6 1 4 1 19348 2 1 1528 }
id-at-zimbraMtaSmtpSaslPasswordMaps OBJECT IDENTIFIER ::= { 1 3 6 1 4 1 19348 2 1 1529 }
id-at-zimbraMtaSmtpSaslSecurityOptions OBJECT IDENTIFIER ::= { 1 3 6 1 4 1 19348 2 1 1549 }
id-at-zimbraMtaSmtpTlsCAfile OBJECT IDENTIFIER ::= { 1 3 6 1 4 1 19348 2 1 1565 }
id-at-zimbraMtaSmtpTlsCApath OBJECT IDENTIFIER ::= { 1 3 6 1 4 1 19348 2 1 1566 }
id-at-zimbraMtaSmtpTlsCiphers OBJECT IDENTIFIER ::= { 1 3 6 1 4 1 19348 2 1 1513 }
id-at-zimbraMtaSmtpTlsLoglevel OBJECT IDENTIFIER ::= { 1 3 6 1 4 1 19348 2 1 1568 }
id-at-zimbraMtaSmtpTlsMandatoryCiphers OBJECT IDENTIFIER ::= { 1 3 6 1 4 1 19348 2 1 1514 }
id-at-zimbraMtaSmtpTlsProtocols OBJECT IDENTIFIER ::= { 1 3 6 1 4 1 19348 2 1 1670 }
id-at-zimbraMtaSmtpTlsSecurityLevel OBJECT IDENTIFIER ::= { 1 3 6 1 4 1 19348 2 1 1527 }
id-at-zimbraMtaSmtpdBanner OBJECT IDENTIFIER ::= { 1 3 6 1 4 1 19348 2 1 1532 }
id-at-zimbraMtaSmtpdClientPortLogging OBJECT IDENTIFIER ::= { 1 3 6 1 4 1 19348 2 1 1588 }
id-at-zimbraMtaSmtpdClientRestrictions OBJECT IDENTIFIER ::= { 1 3 6 1 4 1 19348 2 1 1553 }
id-at-zimbraMtaSmtpdDataRestrictions OBJECT IDENTIFIER ::= { 1 3 6 1 4 1 19348 2 1 1554 }
id-at-zimbraMtaSmtpdErrorSleepTime OBJECT IDENTIFIER ::= { 1 3 6 1 4 1 19348 2 1 1539 }
id-at-zimbraMtaSmtpdHardErrorLimit OBJECT IDENTIFIER ::= { 1 3 6 1 4 1 19348 2 1 1537 }
id-at-zimbraMtaSmtpdHeloRequired OBJECT IDENTIFIER ::= { 1 3 6 1 4 1 19348 2 1 1540 }
id-at-zimbraMtaSmtpdMilters OBJECT IDENTIFIER ::= { 1 3 6 1 4 1 19348 2 1 672 }
id-at-zimbraMtaSmtpdProxyTimeout OBJECT IDENTIFIER ::= { 1 3 6 1 4 1 19348 2 1 1533 }
id-at-zimbraMtaSmtpdRejectUnlistedRecipient OBJECT IDENTIFIER ::= { 1 3 6 1 4 1 19348 2 1 1534 }
id-at-zimbraMtaSmtpdRejectUnlistedSender OBJECT IDENTIFIER ::= { 1 3 6 1 4 1 19348 2 1 1535 }
id-at-zimbraMtaSmtpdSaslAuthenticatedHeader OBJECT IDENTIFIER ::= { 1 3 6 1 4 1 19348 2 1 1536 }
id-at-zimbraMtaSmtpdSaslSecurityOptions OBJECT IDENTIFIER ::= { 1 3 6 1 4 1 19348 2 1 1550 }
id-at-zimbraMtaSmtpdSaslTlsSecurityOptions OBJECT IDENTIFIER ::= { 1 3 6 1 4 1 19348 2 1 1552 }
id-at-zimbraMtaSmtpdSenderLoginMaps OBJECT IDENTIFIER ::= { 1 3 6 1 4 1 19348 2 1 1591 }
id-at-zimbraMtaSmtpdSenderRestrictions OBJECT IDENTIFIER ::= { 1 3 6 1 4 1 19348 2 1 1590 }
id-at-zimbraMtaSmtpdTlsAskCcert OBJECT IDENTIFIER ::= { 1 3 6 1 4 1 19348 2 1 1542 }
id-at-zimbraMtaSmtpdTlsCAfile OBJECT IDENTIFIER ::= { 1 3 6 1 4 1 19348 2 1 1563 }
id-at-zimbraMtaSmtpdTlsCApath OBJECT IDENTIFIER ::= { 1 3 6 1 4 1 19348 2 1 1564 }
id-at-zimbraMtaSmtpdTlsCcertVerifydepth OBJECT IDENTIFIER ::= { 1 3 6 1 4 1 19348 2 1 1543 }
id-at-zimbraMtaSmtpdTlsCiphers OBJECT IDENTIFIER ::= { 1 3 6 1 4 1 19348 2 1 1515 }
id-at-zimbraMtaSmtpdTlsExcludeCiphers OBJECT IDENTIFIER ::= { 1 3 6 1 4 1 19348 2 1 1647 }
id-at-zimbraMtaSmtpdTlsLoglevel OBJECT IDENTIFIER ::= { 1 3 6 1 4 1 19348 2 1 1541 }
id-at-zimbraMtaSmtpdTlsMandatoryCiphers OBJECT IDENTIFIER ::= { 1 3 6 1 4 1 19348 2 1 1516 }
id-at-zimbraMtaSmtpdTlsProtocols OBJECT IDENTIFIER ::= { 1 3 6 1 4 1 19348 2 1 1646 }
id-at-zimbraMtaSmtpdVirtualTransport OBJECT IDENTIFIER ::= { 1 3 6 1 4 1 19348 2 1 1545 }
id-at-zimbraMtaStpdSoftErrorLimit OBJECT IDENTIFIER ::= { 1 3 6 1 4 1 19348 2 1 1538 }
id-at-zimbraMtaTlsAppendDefaultCA OBJECT IDENTIFIER ::= { 1 3 6 1 4 1 19348 2 1 1567 }
id-at-zimbraMtaTlsAuthOnly OBJECT IDENTIFIER ::= { 1 3 6 1 4 1 19348 2 1 200 }
id-at-zimbraMtaTlsSecurityLevel OBJECT IDENTIFIER ::= { 1 3 6 1 4 1 19348 2 1 795 }
id-at-zimbraMtaTransportMaps OBJECT IDENTIFIER ::= { 1 3 6 1 4 1 19348 2 1 1555 }
id-at-zimbraMtaUnverifiedRecipientDeferCode OBJECT IDENTIFIER ::= { 1 3 6 1 4 1 19348 2 1 1606 }
id-at-zimbraMtaVirtualAliasDomains OBJECT IDENTIFIER ::= { 1 3 6 1 4 1 19348 2 1 1556 }
id-at-zimbraMtaVirtualAliasExpansionLimit OBJECT IDENTIFIER ::= { 1 3 6 1 4 1 19348 2 1 1544 }
id-at-zimbraMtaVirtualAliasMaps OBJECT IDENTIFIER ::= { 1 3 6 1 4 1 19348 2 1 1557 }
id-at-zimbraMtaVirtualMailboxDomains OBJECT IDENTIFIER ::= { 1 3 6 1 4 1 19348 2 1 1558 }
id-at-zimbraMtaVirtualMailboxMaps OBJECT IDENTIFIER ::= { 1 3 6 1 4 1 19348 2 1 1559 }
id-at-zimbraMyoneloginSamlSigningCert OBJECT IDENTIFIER ::= { 1 3 6 1 4 1 19348 2 1 1169 }
id-at-zimbraNetworkActivation OBJECT IDENTIFIER ::= { 1 3 6 1 4 1 19348 2 1 375 }
id-at-zimbraNetworkLicense OBJECT IDENTIFIER ::= { 1 3 6 1 4 1 19348 2 1 374 }
id-at-zimbraNewMailNotificationBody OBJECT IDENTIFIER ::= { 1 3 6 1 4 1 19348 2 1 152 }
id-at-zimbraNewMailNotificationFrom OBJECT IDENTIFIER ::= { 1 3 6 1 4 1 19348 2 1 150 }
id-at-zimbraNewMailNotificationSubject OBJECT IDENTIFIER ::= { 1 3 6 1 4 1 19348 2 1 151 }
id-at-zimbraNotebookAccount OBJECT IDENTIFIER ::= { 1 3 6 1 4 1 19348 2 1 363 }
id-at-zimbraNotebookFolderCacheSize OBJECT IDENTIFIER ::= { 1 3 6 1 4 1 19348 2 1 370 }
id-at-zimbraNotebookMaxCachedTemplatesPerFolder OBJECT IDENTIFIER ::= { 1 3 6 1 4 1 19348 2 1 371 }
id-at-zimbraNotebookMaxRevisions OBJECT IDENTIFIER ::= { 1 3 6 1 4 1 19348 2 1 482 }
id-at-zimbraNotebookPageCacheSize OBJECT IDENTIFIER ::= { 1 3 6 1 4 1 19348 2 1 369 }
id-at-zimbraNotebookSanitizeHtml OBJECT IDENTIFIER ::= { 1 3 6 1 4 1 19348 2 1 646 }
id-at-zimbraNotes OBJECT IDENTIFIER ::= { 1 3 6 1 4 1 19348 2 1 9 }
id-at-zimbraNotifyBindAddress OBJECT IDENTIFIER ::= { 1 3 6 1 4 1 19348 2 1 317 }
id-at-zimbraNotifyBindPort OBJECT IDENTIFIER ::= { 1 3 6 1 4 1 19348 2 1 318 }
id-at-zimbraNotifySSLBindAddress OBJECT IDENTIFIER ::= { 1 3 6 1 4 1 19348 2 1 320 }
id-at-zimbraNotifySSLBindPort OBJECT IDENTIFIER ::= { 1 3 6 1 4 1 19348 2 1 321 }
id-at-zimbraNotifySSLServerEnabled OBJECT IDENTIFIER ::= { 1 3 6 1 4 1 19348 2 1 319 }
id-at-zimbraNotifyServerEnabled OBJECT IDENTIFIER ::= { 1 3 6 1 4 1 19348 2 1 316 }
id-at-zimbraOAuthConsumerCredentials OBJECT IDENTIFIER ::= { 1 3 6 1 4 1 19348 2 1 1131 }
id-at-zimbraObjectHandlerClass OBJECT IDENTIFIER ::= { 1 3 6 1 4 1 19348 2 1 164 }
id-at-zimbraObjectHandlerConfig OBJECT IDENTIFIER ::= { 1 3 6 1 4 1 19348 2 1 165 }
id-at-zimbraObjectIndexingEnabled OBJECT IDENTIFIER ::= { 1 3 6 1 4 1 19348 2 1 162 }
id-at-zimbraObjectStoreMatched OBJECT IDENTIFIER ::= { 1 3 6 1 4 1 19348 2 1 163 }
id-at-zimbraObjectType OBJECT IDENTIFIER ::= { 1 3 6 1 4 1 19348 2 1 161 }
id-at-zimbraOpenidConsumerAllowedOPEndpointURL OBJECT IDENTIFIER ::= { 1 3 6 1 4 1 19348 2 1 1191 }
id-at-zimbraOpenidConsumerStatelessModeEnabled OBJECT IDENTIFIER ::= { 1 3 6 1 4 1 19348 2 1 1189 }
id-at-zimbraPasswordAllowedChars OBJECT IDENTIFIER ::= { 1 3 6 1 4 1 19348 2 1 1163 }
id-at-zimbraPasswordAllowedPunctuationChars OBJECT IDENTIFIER ::= { 1 3 6 1 4 1 19348 2 1 1256 }
id-at-zimbraPasswordChangeListener OBJECT IDENTIFIER ::= { 1 3 6 1 4 1 19348 2 1 586 }
id-at-zimbraPasswordEnforceHistory OBJECT IDENTIFIER ::= { 1 3 6 1 4 1 19348 2 1 37 }
id-at-zimbraPasswordHistory OBJECT IDENTIFIER ::= { 1 3 6 1 4 1 19348 2 1 38 }
id-at-zimbraPasswordLocked OBJECT IDENTIFIER ::= { 1 3 6 1 4 1 19348 2 1 45 }
id-at-zimbraPasswordLockoutDuration OBJECT IDENTIFIER ::= { 1 3 6 1 4 1 19348 2 1 379 }
id-at-zimbraPasswordLockoutEnabled OBJECT IDENTIFIER ::= { 1 3 6 1 4 1 19348 2 1 378 }
id-at-zimbraPasswordLockoutFailureLifetime OBJECT IDENTIFIER ::= { 1 3 6 1 4 1 19348 2 1 381 }
id-at-zimbraPasswordLockoutFailureTime OBJECT IDENTIFIER ::= { 1 3 6 1 4 1 19348 2 1 383 }
id-at-zimbraPasswordLockoutLockedTime OBJECT IDENTIFIER ::= { 1 3 6 1 4 1 19348 2 1 382 }
id-at-zimbraPasswordLockoutMaxFailures OBJECT IDENTIFIER ::= { 1 3 6 1 4 1 19348 2 1 380 }
id-at-zimbraPasswordMaxAge OBJECT IDENTIFIER ::= { 1 3 6 1 4 1 19348 2 1 36 }
id-at-zimbraPasswordMaxLength OBJECT IDENTIFIER ::= { 1 3 6 1 4 1 19348 2 1 34 }
id-at-zimbraPasswordMinAge OBJECT IDENTIFIER ::= { 1 3 6 1 4 1 19348 2 1 35 }
id-at-zimbraPasswordMinAlphaChars OBJECT IDENTIFIER ::= { 1 3 6 1 4 1 19348 2 1 1162 }
id-at-zimbraPasswordMinDigitsOrPuncs OBJECT IDENTIFIER ::= { 1 3 6 1 4 1 19348 2 1 1255 }
id-at-zimbraPasswordMinLength OBJECT IDENTIFIER ::= { 1 3 6 1 4 1 19348 2 1 33 }
id-at-zimbraPasswordMinLowerCaseChars OBJECT IDENTIFIER ::= { 1 3 6 1 4 1 19348 2 1 390 }
id-at-zimbraPasswordMinNumericChars OBJECT IDENTIFIER ::= { 1 3 6 1 4 1 19348 2 1 392 }
id-at-zimbraPasswordMinPunctuationChars OBJECT IDENTIFIER ::= { 1 3 6 1 4 1 19348 2 1 391 }
id-at-zimbraPasswordMinUpperCaseChars OBJECT IDENTIFIER ::= { 1 3 6 1 4 1 19348 2 1 389 }
id-at-zimbraPasswordModifiedTime OBJECT IDENTIFIER ::= { 1 3 6 1 4 1 19348 2 1 39 }
id-at-zimbraPasswordMustChange OBJECT IDENTIFIER ::= { 1 3 6 1 4 1 19348 2 1 41 }
id-at-zimbraPhoneticCompany OBJECT IDENTIFIER ::= { 1 3 6 1 4 1 19348 2 1 1149 }
id-at-zimbraPhoneticFirstName OBJECT IDENTIFIER ::= { 1 3 6 1 4 1 19348 2 1 1147 }
id-at-zimbraPhoneticLastName OBJECT IDENTIFIER ::= { 1 3 6 1 4 1 19348 2 1 1148 }
id-at-zimbraPop3AdvertisedName OBJECT IDENTIFIER ::= { 1 3 6 1 4 1 19348 2 1 93 }
id-at-zimbraPop3BindAddress OBJECT IDENTIFIER ::= { 1 3 6 1 4 1 19348 2 1 95 }
id-at-zimbraPop3BindOnStartup OBJECT IDENTIFIER ::= { 1 3 6 1 4 1 19348 2 1 271 }
id-at-zimbraPop3BindPort OBJECT IDENTIFIER ::= { 1 3 6 1 4 1 19348 2 1 94 }
id-at-zimbraPop3CleartextLoginEnabled OBJECT IDENTIFIER ::= { 1 3 6 1 4 1 19348 2 1 189 }
id-at-zimbraPop3Enabled OBJECT IDENTIFIER ::= { 1 3 6 1 4 1 19348 2 1 175 }
id-at-zimbraPop3ExposeVersionOnBanner OBJECT IDENTIFIER ::= { 1 3 6 1 4 1 19348 2 1 692 }
id-at-zimbraPop3MaxConnections OBJECT IDENTIFIER ::= { 1 3 6 1 4 1 19348 2 1 1155 }
id-at-zimbraPop3NumThreads OBJECT IDENTIFIER ::= { 1 3 6 1 4 1 19348 2 1 96 }
id-at-zimbraPop3ProxyBindPort OBJECT IDENTIFIER ::= { 1 3 6 1 4 1 19348 2 1 350 }
id-at-zimbraPop3SSLBindAddress OBJECT IDENTIFIER ::= { 1 3 6 1 4 1 19348 2 1 186 }
id-at-zimbraPop3SSLBindOnStartup OBJECT IDENTIFIER ::= { 1 3 6 1 4 1 19348 2 1 272 }
id-at-zimbraPop3SSLBindPort OBJECT IDENTIFIER ::= { 1 3 6 1 4 1 19348 2 1 187 }
id-at-zimbraPop3SSLProxyBindPort OBJECT IDENTIFIER ::= { 1 3 6 1 4 1 19348 2 1 351 }
id-at-zimbraPop3SSLServerEnabled OBJECT IDENTIFIER ::= { 1 3 6 1 4 1 19348 2 1 188 }
id-at-zimbraPop3SaslGssapiEnabled OBJECT IDENTIFIER ::= { 1 3 6 1 4 1 19348 2 1 554 }
id-at-zimbraPop3ServerEnabled OBJECT IDENTIFIER ::= { 1 3 6 1 4 1 19348 2 1 177 }
id-at-zimbraPop3ShutdownGraceSeconds OBJECT IDENTIFIER ::= { 1 3 6 1 4 1 19348 2 1 1081 }
id-at-zimbraPortalName OBJECT IDENTIFIER ::= { 1 3 6 1 4 1 19348 2 1 448 }
id-at-zimbraPreAuthKey OBJECT IDENTIFIER ::= { 1 3 6 1 4 1 19348 2 1 307 }
id-at-zimbraPrefAccountTreeOpen OBJECT IDENTIFIER ::= { 1 3 6 1 4 1 19348 2 1 1048 }
id-at-zimbraPrefAdminConsoleWarnOnExit OBJECT IDENTIFIER ::= { 1 3 6 1 4 1 19348 2 1 1036 }
id-at-zimbraPrefAdvancedClientEnforceMinDisplay OBJECT IDENTIFIER ::= { 1 3 6 1 4 1 19348 2 1 678 }
id-at-zimbraPrefAllowAddressForDelegatedSender OBJECT IDENTIFIER ::= { 1 3 6 1 4 1 19348 2 1 1333 }
id-at-zimbraPrefAppleIcalDelegationEnabled OBJECT IDENTIFIER ::= { 1 3 6 1 4 1 19348 2 1 1028 }
id-at-zimbraPrefAutoAddAddressEnabled OBJECT IDENTIFIER ::= { 1 3 6 1 4 1 19348 2 1 131 }
id-at-zimbraPrefAutoCompleteQuickCompletionOnComma OBJECT IDENTIFIER ::= { 1 3 6 1 4 1 19348 2 1 1091 }
id-at-zimbraPrefAutoSaveDraftInterval OBJECT IDENTIFIER ::= { 1 3 6 1 4 1 19348 2 1 561 }
id-at-zimbraPrefAutocompleteAddressBubblesEnabled OBJECT IDENTIFIER ::= { 1 3 6 1 4 1 19348 2 1 1146 }
id-at-zimbraPrefBccAddress OBJECT IDENTIFIER ::= { 1 3 6 1 4 1 19348 2 1 411 }
id-at-zimbraPrefBriefcaseReadingPaneLocation OBJECT IDENTIFIER ::= { 1 3 6 1 4 1 19348 2 1 1152 }
id-at-zimbraPrefCalendarAcceptSignatureId OBJECT IDENTIFIER ::= { 1 3 6 1 4 1 19348 2 1 1202 }
id-at-zimbraPrefCalendarAllowCancelEmailToSelf OBJECT IDENTIFIER ::= { 1 3 6 1 4 1 19348 2 1 702 }
id-at-zimbraPrefCalendarAllowForwardedInvite OBJECT IDENTIFIER ::= { 1 3 6 1 4 1 19348 2 1 686 }
id-at-zimbraPrefCalendarAllowPublishMethodInvite OBJECT IDENTIFIER ::= { 1 3 6 1 4 1 19348 2 1 688 }
id-at-zimbraPrefCalendarAllowedTargetsForInviteDeniedAutoReply OBJECT IDENTIFIER ::= { 1 3 6 1 4 1 19348 2 1 1632 }
id-at-zimbraPrefCalendarAlwaysShowMiniCal OBJECT IDENTIFIER ::= { 1 3 6 1 4 1 19348 2 1 276 }
id-at-zimbraPrefCalendarApptAllowAtendeeEdit OBJECT IDENTIFIER ::= { 1 3 6 1 4 1 19348 2 1 1089 }
id-at-zimbraPrefCalendarApptReminderWarningTime OBJECT IDENTIFIER ::= { 1 3 6 1 4 1 19348 2 1 341 }
id-at-zimbraPrefCalendarApptVisibility OBJECT IDENTIFIER ::= { 1 3 6 1 4 1 19348 2 1 832 }
id-at-zimbraPrefCalendarAutoAcceptSignatureId OBJECT IDENTIFIER ::= { 1 3 6 1 4 1 19348 2 1 1192 }
id-at-zimbraPrefCalendarAutoAddInvites OBJECT IDENTIFIER ::= { 1 3 6 1 4 1 19348 2 1 848 }
id-at-zimbraPrefCalendarAutoDeclineSignatureId OBJECT IDENTIFIER ::= { 1 3 6 1 4 1 19348 2 1 1193 }
id-at-zimbraPrefCalendarAutoDenySignatureId OBJECT IDENTIFIER ::= { 1 3 6 1 4 1 19348 2 1 1194 }
id-at-zimbraPrefCalendarDayHourEnd OBJECT IDENTIFIER ::= { 1 3 6 1 4 1 19348 2 1 440 }
id-at-zimbraPrefCalendarDayHourStart OBJECT IDENTIFIER ::= { 1 3 6 1 4 1 19348 2 1 439 }
id-at-zimbraPrefCalendarDeclineSignatureId OBJECT IDENTIFIER ::= { 1 3 6 1 4 1 19348 2 1 1204 }
id-at-zimbraPrefCalendarDefaultApptDuration OBJECT IDENTIFIER ::= { 1 3 6 1 4 1 19348 2 1 1187 }
id-at-zimbraPrefCalendarFirstDayOfWeek OBJECT IDENTIFIER ::= { 1 3 6 1 4 1 19348 2 1 261 }
id-at-zimbraPrefCalendarForwardInvitesTo OBJECT IDENTIFIER ::= { 1 3 6 1 4 1 19348 2 1 851 }
id-at-zimbraPrefCalendarInitialCheckedCalendars OBJECT IDENTIFIER ::= { 1 3 6 1 4 1 19348 2 1 275 }
id-at-zimbraPrefCalendarInitialView OBJECT IDENTIFIER ::= { 1 3 6 1 4 1 19348 2 1 240 }
id-at-zimbraPrefCalendarNotifyDelegatedChanges OBJECT IDENTIFIER ::= { 1 3 6 1 4 1 19348 2 1 273 }
id-at-zimbraPrefCalendarReminderDeviceInfo OBJECT IDENTIFIER ::= { 1 3 6 1 4 1 19348 2 1 1307 }
id-at-zimbraPrefCalendarReminderDuration1 OBJECT IDENTIFIER ::= { 1 3 6 1 4 1 19348 2 1 573 }
id-at-zimbraPrefCalendarReminderDuration2 OBJECT IDENTIFIER ::= { 1 3 6 1 4 1 19348 2 1 574 }
id-at-zimbraPrefCalendarReminderEmail OBJECT IDENTIFIER ::= { 1 3 6 1 4 1 19348 2 1 575 }
id-at-zimbraPrefCalendarReminderFlashTitle OBJECT IDENTIFIER ::= { 1 3 6 1 4 1 19348 2 1 682 }
id-at-zimbraPrefCalendarReminderMobile OBJECT IDENTIFIER ::= { 1 3 6 1 4 1 19348 2 1 577 }
id-at-zimbraPrefCalendarReminderSendEmail OBJECT IDENTIFIER ::= { 1 3 6 1 4 1 19348 2 1 576 }
id-at-zimbraPrefCalendarReminderSoundsEnabled OBJECT IDENTIFIER ::= { 1 3 6 1 4 1 19348 2 1 667 }
id-at-zimbraPrefCalendarReminderYMessenger OBJECT IDENTIFIER ::= { 1 3 6 1 4 1 19348 2 1 578 }
id-at-zimbraPrefCalendarSendInviteDeniedAutoReply OBJECT IDENTIFIER ::= { 1 3 6 1 4 1 19348 2 1 849 }
id-at-zimbraPrefCalendarShowDeclinedMeetings OBJECT IDENTIFIER ::= { 1 3 6 1 4 1 19348 2 1 1196 }
id-at-zimbraPrefCalendarShowPastDueReminders OBJECT IDENTIFIER ::= { 1 3 6 1 4 1 19348 2 1 1022 }
id-at-zimbraPrefCalendarTentativeSignatureId OBJECT IDENTIFIER ::= { 1 3 6 1 4 1 19348 2 1 1203 }
id-at-zimbraPrefCalendarToasterEnabled OBJECT IDENTIFIER ::= { 1 3 6 1 4 1 19348 2 1 813 }
id-at-zimbraPrefCalendarUseQuickAdd OBJECT IDENTIFIER ::= { 1 3 6 1 4 1 19348 2 1 274 }
id-at-zimbraPrefCalendarViewTimeInterval OBJECT IDENTIFIER ::= { 1 3 6 1 4 1 19348 2 1 1195 }
id-at-zimbraPrefCalendarWorkingHours OBJECT IDENTIFIER ::= { 1 3 6 1 4 1 19348 2 1 1103 }
id-at-zimbraPrefChildVisibleAccount OBJECT IDENTIFIER ::= { 1 3 6 1 4 1 19348 2 1 553 }
id-at-zimbraPrefClientType OBJECT IDENTIFIER ::= { 1 3 6 1 4 1 19348 2 1 453 }
id-at-zimbraPrefColorMessagesEnabled OBJECT IDENTIFIER ::= { 1 3 6 1 4 1 19348 2 1 1424 }
id-at-zimbraPrefComposeDirection OBJECT IDENTIFIER ::= { 1 3 6 1 4 1 19348 2 1 1273 }
id-at-zimbraPrefComposeFormat OBJECT IDENTIFIER ::= { 1 3 6 1 4 1 19348 2 1 217 }
id-at-zimbraPrefComposeInNewWindow OBJECT IDENTIFIER ::= { 1 3 6 1 4 1 19348 2 1 209 }
id-at-zimbraPrefContactsDisableAutocompleteOnContactGroupMembers OBJECT IDENTIFIER ::= { 1 3 6 1 4 1 19348 2 1 1090 }
id-at-zimbraPrefContactsExpandAppleContactGroups OBJECT IDENTIFIER ::= { 1 3 6 1 4 1 19348 2 1 1102 }
id-at-zimbraPrefContactsInitialView OBJECT IDENTIFIER ::= { 1 3 6 1 4 1 19348 2 1 167 }
id-at-zimbraPrefContactsPerPage OBJECT IDENTIFIER ::= { 1 3 6 1 4 1 19348 2 1 148 }
id-at-zimbraPrefConvReadingPaneLocation OBJECT IDENTIFIER ::= { 1 3 6 1 4 1 19348 2 1 1010 }
id-at-zimbraPrefConvShowCalendar OBJECT IDENTIFIER ::= { 1 3 6 1 4 1 19348 2 1 1394 }
id-at-zimbraPrefConversationOrder OBJECT IDENTIFIER ::= { 1 3 6 1 4 1 19348 2 1 818 }
id-at-zimbraPrefDedupeMessagesSentToSelf OBJECT IDENTIFIER ::= { 1 3 6 1 4 1 19348 2 1 144 }
id-at-zimbraPrefDefaultPrintFontSize OBJECT IDENTIFIER ::= { 1 3 6 1 4 1 19348 2 1 1095 }
id-at-zimbraPrefDefaultSignatureId OBJECT IDENTIFIER ::= { 1 3 6 1 4 1 19348 2 1 492 }
id-at-zimbraPrefDelegatedSendSaveTarget OBJECT IDENTIFIER ::= { 1 3 6 1 4 1 19348 2 1 1651 }
id-at-zimbraPrefDeleteInviteOnReply OBJECT IDENTIFIER ::= { 1 3 6 1 4 1 19348 2 1 470 }
id-at-zimbraPrefDisabledZimlets OBJECT IDENTIFIER ::= { 1 3 6 1 4 1 19348 2 1 1076 }
id-at-zimbraPrefDisplayExternalImages OBJECT IDENTIFIER ::= { 1 3 6 1 4 1 19348 2 1 511 }
id-at-zimbraPrefExternalSendersType OBJECT IDENTIFIER ::= { 1 3 6 1 4 1 19348 2 1 1320 }
id-at-zimbraPrefFileSharingApplication OBJECT IDENTIFIER ::= { 1 3 6 1 4 1 19348 2 1 1197 }
id-at-zimbraPrefFolderColorEnabled OBJECT IDENTIFIER ::= { 1 3 6 1 4 1 19348 2 1 771 }
id-at-zimbraPrefFolderTreeOpen OBJECT IDENTIFIER ::= { 1 3 6 1 4 1 19348 2 1 637 }
id-at-zimbraPrefFont OBJECT IDENTIFIER ::= { 1 3 6 1 4 1 19348 2 1 1246 }
id-at-zimbraPrefFontSize OBJECT IDENTIFIER ::= { 1 3 6 1 4 1 19348 2 1 1448 }
id-at-zimbraPrefForwardIncludeOriginalText OBJECT IDENTIFIER ::= { 1 3 6 1 4 1 19348 2 1 134 }
id-at-zimbraPrefForwardReplyFormat OBJECT IDENTIFIER ::= { 1 3 6 1 4 1 19348 2 1 413 }
id-at-zimbraPrefForwardReplyInOriginalFormat OBJECT IDENTIFIER ::= { 1 3 6 1 4 1 19348 2 1 218 }
id-at-zimbraPrefForwardReplyPrefixChar OBJECT IDENTIFIER ::= { 1 3 6 1 4 1 19348 2 1 130 }
id-at-zimbraPrefForwardReplySignatureId OBJECT IDENTIFIER ::= { 1 3 6 1 4 1 19348 2 1 1125 }
id-at-zimbraPrefFromAddress OBJECT IDENTIFIER ::= { 1 3 6 1 4 1 19348 2 1 403 }
id-at-zimbraPrefFromAddressType OBJECT IDENTIFIER ::= { 1 3 6 1 4 1 19348 2 1 1419 }
id-at-zimbraPrefFromDisplay OBJECT IDENTIFIER ::= { 1 3 6 1 4 1 19348 2 1 402 }
id-at-zimbraPrefGalAutoCompleteEnabled OBJECT IDENTIFIER ::= { 1 3 6 1 4 1 19348 2 1 372 }
id-at-zimbraPrefGalSearchEnabled OBJECT IDENTIFIER ::= { 1 3 6 1 4 1 19348 2 1 635 }
id-at-zimbraPrefGetMailAction OBJECT IDENTIFIER ::= { 1 3 6 1 4 1 19348 2 1 1067 }
id-at-zimbraPrefGroupMailBy OBJECT IDENTIFIER ::= { 1 3 6 1 4 1 19348 2 1 54 }
id-at-zimbraPrefHtmlEditorDefaultFontColor OBJECT IDENTIFIER ::= { 1 3 6 1 4 1 19348 2 1 260 }
id-at-zimbraPrefHtmlEditorDefaultFontFamily OBJECT IDENTIFIER ::= { 1 3 6 1 4 1 19348 2 1 258 }
id-at-zimbraPrefHtmlEditorDefaultFontSize OBJECT IDENTIFIER ::= { 1 3 6 1 4 1 19348 2 1 259 }
id-at-zimbraPrefIMAutoLogin OBJECT IDENTIFIER ::= { 1 3 6 1 4 1 19348 2 1 488 }
id-at-zimbraPrefIMBuddyListSort OBJECT IDENTIFIER ::= { 1 3 6 1 4 1 19348 2 1 705 }
id-at-zimbraPrefIMCustomStatusMessage OBJECT IDENTIFIER ::= { 1 3 6 1 4 1 19348 2 1 645 }
id-at-zimbraPrefIMFlashIcon OBJECT IDENTIFIER ::= { 1 3 6 1 4 1 19348 2 1 462 }
id-at-zimbraPrefIMFlashTitle OBJECT IDENTIFIER ::= { 1 3 6 1 4 1 19348 2 1 679 }
id-at-zimbraPrefIMHideBlockedBuddies OBJECT IDENTIFIER ::= { 1 3 6 1 4 1 19348 2 1 707 }
id-at-zimbraPrefIMHideOfflineBuddies OBJECT IDENTIFIER ::= { 1 3 6 1 4 1 19348 2 1 706 }
id-at-zimbraPrefIMIdleStatus OBJECT IDENTIFIER ::= { 1 3 6 1 4 1 19348 2 1 560 }
id-at-zimbraPrefIMIdleTimeout OBJECT IDENTIFIER ::= { 1 3 6 1 4 1 19348 2 1 559 }
id-at-zimbraPrefIMInstantNotify OBJECT IDENTIFIER ::= { 1 3 6 1 4 1 19348 2 1 517 }
id-at-zimbraPrefIMLogChats OBJECT IDENTIFIER ::= { 1 3 6 1 4 1 19348 2 1 556 }
id-at-zimbraPrefIMLogChatsEnabled OBJECT IDENTIFIER ::= { 1 3 6 1 4 1 19348 2 1 552 }
id-at-zimbraPrefIMNotifyPresence OBJECT IDENTIFIER ::= { 1 3 6 1 4 1 19348 2 1 463 }
id-at-zimbraPrefIMNotifyStatus OBJECT IDENTIFIER ::= { 1 3 6 1 4 1 19348 2 1 464 }
id-at-zimbraPrefIMReportIdle OBJECT IDENTIFIER ::= { 1 3 6 1 4 1 19348 2 1 558 }
id-at-zimbraPrefIMSoundsEnabled OBJECT IDENTIFIER ::= { 1 3 6 1 4 1 19348 2 1 570 }
id-at-zimbraPrefIMToasterEnabled OBJECT IDENTIFIER ::= { 1 3 6 1 4 1 19348 2 1 814 }
id-at-zimbraPrefIMYahooId OBJECT IDENTIFIER ::= { 1 3 6 1 4 1 19348 2 1 757 }
id-at-zimbraPrefIdentityId OBJECT IDENTIFIER ::= { 1 3 6 1 4 1 19348 2 1 433 }
id-at-zimbraPrefIdentityName OBJECT IDENTIFIER ::= { 1 3 6 1 4 1 19348 2 1 412 }
id-at-zimbraPrefImapSearchFoldersEnabled OBJECT IDENTIFIER ::= { 1 3 6 1 4 1 19348 2 1 241 }
id-at-zimbraPrefInboxReadLifetime OBJECT IDENTIFIER ::= { 1 3 6 1 4 1 19348 2 1 538 }
id-at-zimbraPrefInboxUnreadLifetime OBJECT IDENTIFIER ::= { 1 3 6 1 4 1 19348 2 1 537 }
id-at-zimbraPrefIncludeSharedItemsInSearch OBJECT IDENTIFIER ::= { 1 3 6 1 4 1 19348 2 1 1338 }
id-at-zimbraPrefIncludeSpamInSearch OBJECT IDENTIFIER ::= { 1 3 6 1 4 1 19348 2 1 55 }
id-at-zimbraPrefIncludeTrashInSearch OBJECT IDENTIFIER ::= { 1 3 6 1 4 1 19348 2 1 56 }
id-at-zimbraPrefItemsPerVirtualPage OBJECT IDENTIFIER ::= { 1 3 6 1 4 1 19348 2 1 1079 }
id-at-zimbraPrefJunkLifetime OBJECT IDENTIFIER ::= { 1 3 6 1 4 1 19348 2 1 540 }
id-at-zimbraPrefLabel OBJECT IDENTIFIER ::= { 1 3 6 1 4 1 19348 2 1 603 }
id-at-zimbraPrefListViewColumns OBJECT IDENTIFIER ::= { 1 3 6 1 4 1 19348 2 1 694 }
id-at-zimbraPrefLocale OBJECT IDENTIFIER ::= { 1 3 6 1 4 1 19348 2 1 442 }
id-at-zimbraPrefMailDefaultCharset OBJECT IDENTIFIER ::= { 1 3 6 1 4 1 19348 2 1 469 }
id-at-zimbraPrefMailFlashIcon OBJECT IDENTIFIER ::= { 1 3 6 1 4 1 19348 2 1 681 }
id-at-zimbraPrefMailFlashTitle OBJECT IDENTIFIER ::= { 1 3 6 1 4 1 19348 2 1 680 }
id-at-zimbraPrefMailFoldersCheckedForNewMsgIndicator OBJECT IDENTIFIER ::= { 1 3 6 1 4 1 19348 2 1 1072 }
id-at-zimbraPrefMailForwardingAddress OBJECT IDENTIFIER ::= { 1 3 6 1 4 1 19348 2 1 343 }
id-at-zimbraPrefMailInitialSearch OBJECT IDENTIFIER ::= { 1 3 6 1 4 1 19348 2 1 102 }
id-at-zimbraPrefMailItemsPerPage OBJECT IDENTIFIER ::= { 1 3 6 1 4 1 19348 2 1 57 }
id-at-zimbraPrefMailLocalDeliveryDisabled OBJECT IDENTIFIER ::= { 1 3 6 1 4 1 19348 2 1 344 }
id-at-zimbraPrefMailPollingInterval OBJECT IDENTIFIER ::= { 1 3 6 1 4 1 19348 2 1 111 }
id-at-zimbraPrefMailRequestReadReceipts OBJECT IDENTIFIER ::= { 1 3 6 1 4 1 19348 2 1 1217 }
id-at-zimbraPrefMailSMIMECertificate OBJECT IDENTIFIER ::= { 1 3 6 1 4 1 19348 2 1 1172 }
id-at-zimbraPrefMailSelectAfterDelete OBJECT IDENTIFIER ::= { 1 3 6 1 4 1 19348 2 1 1046 }
id-at-zimbraPrefMailSendReadReceipts OBJECT IDENTIFIER ::= { 1 3 6 1 4 1 19348 2 1 822 }
id-at-zimbraPrefMailSignature OBJECT IDENTIFIER ::= { 1 3 6 1 4 1 19348 2 1 17 }
id-at-zimbraPrefMailSignatureContactId OBJECT IDENTIFIER ::= { 1 3 6 1 4 1 19348 2 1 1129 }
id-at-zimbraPrefMailSignatureEnabled OBJECT IDENTIFIER ::= { 1 3 6 1 4 1 19348 2 1 18 }
id-at-zimbraPrefMailSignatureHTML OBJECT IDENTIFIER ::= { 1 3 6 1 4 1 19348 2 1 516 }
id-at-zimbraPrefMailSignatureStyle OBJECT IDENTIFIER ::= { 1 3 6 1 4 1 19348 2 1 156 }
id-at-zimbraPrefMailSoundsEnabled OBJECT IDENTIFIER ::= { 1 3 6 1 4 1 19348 2 1 666 }
id-at-zimbraPrefMailToasterEnabled OBJECT IDENTIFIER ::= { 1 3 6 1 4 1 19348 2 1 812 }
id-at-zimbraPrefMailTrustedSenderList OBJECT IDENTIFIER ::= { 1 3 6 1 4 1 19348 2 1 1138 }
id-at-zimbraPrefMandatorySpellCheckEnabled OBJECT IDENTIFIER ::= { 1 3 6 1 4 1 19348 2 1 749 }
id-at-zimbraPrefMarkMsgRead OBJECT IDENTIFIER ::= { 1 3 6 1 4 1 19348 2 1 650 }
id-at-zimbraPrefMessageIdDedupingEnabled OBJECT IDENTIFIER ::= { 1 3 6 1 4 1 19348 2 1 1198 }
id-at-zimbraPrefMessageViewHtmlPreferred OBJECT IDENTIFIER ::= { 1 3 6 1 4 1 19348 2 1 145 }
id-at-zimbraPrefNewMailNotificationAddress OBJECT IDENTIFIER ::= { 1 3 6 1 4 1 19348 2 1 127 }
id-at-zimbraPrefNewMailNotificationEnabled OBJECT IDENTIFIER ::= { 1 3 6 1 4 1 19348 2 1 126 }
id-at-zimbraPrefOpenMailInNewWindow OBJECT IDENTIFIER ::= { 1 3 6 1 4 1 19348 2 1 500 }
id-at-zimbraPrefOutOfOfficeCacheDuration OBJECT IDENTIFIER ::= { 1 3 6 1 4 1 19348 2 1 386 }
id-at-zimbraPrefOutOfOfficeDirectAddress OBJECT IDENTIFIER ::= { 1 3 6 1 4 1 19348 2 1 387 }
id-at-zimbraPrefOutOfOfficeExternalReply OBJECT IDENTIFIER ::= { 1 3 6 1 4 1 19348 2 1 1317 }
id-at-zimbraPrefOutOfOfficeExternalReplyEnabled OBJECT IDENTIFIER ::= { 1 3 6 1 4 1 19348 2 1 1318 }
id-at-zimbraPrefOutOfOfficeFreeBusyStatus OBJECT IDENTIFIER ::= { 1 3 6 1 4 1 19348 2 1 1334 }
id-at-zimbraPrefOutOfOfficeFromDate OBJECT IDENTIFIER ::= { 1 3 6 1 4 1 19348 2 1 384 }
id-at-zimbraPrefOutOfOfficeReply OBJECT IDENTIFIER ::= { 1 3 6 1 4 1 19348 2 1 58 }
id-at-zimbraPrefOutOfOfficeReplyEnabled OBJECT IDENTIFIER ::= { 1 3 6 1 4 1 19348 2 1 59 }
id-at-zimbraPrefOutOfOfficeStatusAlertOnLogin OBJECT IDENTIFIER ::= { 1 3 6 1 4 1 19348 2 1 1245 }
id-at-zimbraPrefOutOfOfficeSuppressExternalReply OBJECT IDENTIFIER ::= { 1 3 6 1 4 1 19348 2 1 1576 }
id-at-zimbraPrefOutOfOfficeUntilDate OBJECT IDENTIFIER ::= { 1 3 6 1 4 1 19348 2 1 385 }
id-at-zimbraPrefPop3DeleteOption OBJECT IDENTIFIER ::= { 1 3 6 1 4 1 19348 2 1 1165 }
id-at-zimbraPrefPop3DownloadSince OBJECT IDENTIFIER ::= { 1 3 6 1 4 1 19348 2 1 653 }
id-at-zimbraPrefPop3IncludeSpam OBJECT IDENTIFIER ::= { 1 3 6 1 4 1 19348 2 1 1166 }
id-at-zimbraPrefQuickCommand OBJECT IDENTIFIER ::= { 1 3 6 1 4 1 19348 2 1 1211 }
id-at-zimbraPrefReadReceiptsToAddress OBJECT IDENTIFIER ::= { 1 3 6 1 4 1 19348 2 1 823 }
id-at-zimbraPrefReadingPaneEnabled OBJECT IDENTIFIER ::= { 1 3 6 1 4 1 19348 2 1 394 }
id-at-zimbraPrefReadingPaneLocation OBJECT IDENTIFIER ::= { 1 3 6 1 4 1 19348 2 1 804 }
id-at-zimbraPrefReplyIncludeOriginalText OBJECT IDENTIFIER ::= { 1 3 6 1 4 1 19348 2 1 133 }
id-at-zimbraPrefReplyToAddress OBJECT IDENTIFIER ::= { 1 3 6 1 4 1 19348 2 1 60 }
id-at-zimbraPrefReplyToDisplay OBJECT IDENTIFIER ::= { 1 3 6 1 4 1 19348 2 1 404 }
id-at-zimbraPrefReplyToEnabled OBJECT IDENTIFIER ::= { 1 3 6 1 4 1 19348 2 1 405 }
id-at-zimbraPrefSaveToSent OBJECT IDENTIFIER ::= { 1 3 6 1 4 1 19348 2 1 22 }
id-at-zimbraPrefSearchTreeOpen OBJECT IDENTIFIER ::= { 1 3 6 1 4 1 19348 2 1 634 }
id-at-zimbraPrefSentLifetime OBJECT IDENTIFIER ::= { 1 3 6 1 4 1 19348 2 1 539 }
id-at-zimbraPrefSentMailFolder OBJECT IDENTIFIER ::= { 1 3 6 1 4 1 19348 2 1 103 }
id-at-zimbraPrefSharedAddrBookAutoCompleteEnabled OBJECT IDENTIFIER ::= { 1 3 6 1 4 1 19348 2 1 759 }
id-at-zimbraPrefShortEmailAddress OBJECT IDENTIFIER ::= { 1 3 6 1 4 1 19348 2 1 1173 }
id-at-zimbraPrefShortcuts OBJECT IDENTIFIER ::= { 1 3 6 1 4 1 19348 2 1 396 }
id-at-zimbraPrefShowCalendarWeek OBJECT IDENTIFIER ::= { 1 3 6 1 4 1 19348 2 1 1045 }
id-at-zimbraPrefShowComposeDirection OBJECT IDENTIFIER ::= { 1 3 6 1 4 1 19348 2 1 1274 }
id-at-zimbraPrefShowFragments OBJECT IDENTIFIER ::= { 1 3 6 1 4 1 19348 2 1 192 }
id-at-zimbraPrefShowSearchString OBJECT IDENTIFIER ::= { 1 3 6 1 4 1 19348 2 1 222 }
id-at-zimbraPrefShowSelectionCheckbox OBJECT IDENTIFIER ::= { 1 3 6 1 4 1 19348 2 1 471 }
id-at-zimbraPrefSkin OBJECT IDENTIFIER ::= { 1 3 6 1 4 1 19348 2 1 355 }
id-at-zimbraPrefSortOrder OBJECT IDENTIFIER ::= { 1 3 6 1 4 1 19348 2 1 1188 }
id-at-zimbraPrefSpellDictionary OBJECT IDENTIFIER ::= { 1 3 6 1 4 1 19348 2 1 1041 }
id-at-zimbraPrefSpellIgnoreAllCaps OBJECT IDENTIFIER ::= { 1 3 6 1 4 1 19348 2 1 1207 }
id-at-zimbraPrefSpellIgnorePattern OBJECT IDENTIFIER ::= { 1 3 6 1 4 1 19348 2 1 1432 }
id-at-zimbraPrefSpellIgnoreWord OBJECT IDENTIFIER ::= { 1 3 6 1 4 1 19348 2 1 1073 }
id-at-zimbraPrefStandardClientAccessibilityMode OBJECT IDENTIFIER ::= { 1 3 6 1 4 1 19348 2 1 689 }
id-at-zimbraPrefTagTreeOpen OBJECT IDENTIFIER ::= { 1 3 6 1 4 1 19348 2 1 633 }
id-at-zimbraPrefTasksFilterBy OBJECT IDENTIFIER ::= { 1 3 6 1 4 1 19348 2 1 1323 }
id-at-zimbraPrefTasksReadingPaneLocation OBJECT IDENTIFIER ::= { 1 3 6 1 4 1 19348 2 1 1151 }
id-at-zimbraPrefTimeZoneId OBJECT IDENTIFIER ::= { 1 3 6 1 4 1 19348 2 1 235 }
id-at-zimbraPrefTrashLifetime OBJECT IDENTIFIER ::= { 1 3 6 1 4 1 19348 2 1 541 }
id-at-zimbraPrefUseDefaultIdentitySettings OBJECT IDENTIFIER ::= { 1 3 6 1 4 1 19348 2 1 410 }
id-at-zimbraPrefUseKeyboardShortcuts OBJECT IDENTIFIER ::= { 1 3 6 1 4 1 19348 2 1 61 }
id-at-zimbraPrefUseRfc2231 OBJECT IDENTIFIER ::= { 1 3 6 1 4 1 19348 2 1 395 }
id-at-zimbraPrefUseSendMsgShortcut OBJECT IDENTIFIER ::= { 1 3 6 1 4 1 19348 2 1 1650 }
id-at-zimbraPrefUseTimeZoneListInCalendar OBJECT IDENTIFIER ::= { 1 3 6 1 4 1 19348 2 1 236 }
id-at-zimbraPrefVoiceItemsPerPage OBJECT IDENTIFIER ::= { 1 3 6 1 4 1 19348 2 1 526 }
id-at-zimbraPrefWarnOnExit OBJECT IDENTIFIER ::= { 1 3 6 1 4 1 19348 2 1 456 }
id-at-zimbraPrefWebClientOfflineBrowserKey OBJECT IDENTIFIER ::= { 1 3 6 1 4 1 19348 2 1 1571 }
id-at-zimbraPrefWhenInFolderIds OBJECT IDENTIFIER ::= { 1 3 6 1 4 1 19348 2 1 409 }
id-at-zimbraPrefWhenInFoldersEnabled OBJECT IDENTIFIER ::= { 1 3 6 1 4 1 19348 2 1 408 }
id-at-zimbraPrefWhenSentToAddresses OBJECT IDENTIFIER ::= { 1 3 6 1 4 1 19348 2 1 407 }
id-at-zimbraPrefWhenSentToEnabled OBJECT IDENTIFIER ::= { 1 3 6 1 4 1 19348 2 1 406 }
id-at-zimbraPrefZimletTreeOpen OBJECT IDENTIFIER ::= { 1 3 6 1 4 1 19348 2 1 638 }
id-at-zimbraPrefZimlets OBJECT IDENTIFIER ::= { 1 3 6 1 4 1 19348 2 1 765 }
id-at-zimbraPrevFoldersToTrackMax OBJECT IDENTIFIER ::= { 1 3 6 1 4 1 19348 2 1 1592 }
id-at-zimbraProduct OBJECT IDENTIFIER ::= { 1 3 6 1 4 1 19348 2 1 1392 }
id-at-zimbraProxyAllowedDomains OBJECT IDENTIFIER ::= { 1 3 6 1 4 1 19348 2 1 294 }
id-at-zimbraProxyCacheableContentTypes OBJECT IDENTIFIER ::= { 1 3 6 1 4 1 19348 2 1 303 }
id-at-zimbraPublicServiceHostname OBJECT IDENTIFIER ::= { 1 3 6 1 4 1 19348 2 1 377 }
id-at-zimbraPublicServicePort OBJECT IDENTIFIER ::= { 1 3 6 1 4 1 19348 2 1 699 }
id-at-zimbraPublicServiceProtocol OBJECT IDENTIFIER ::= { 1 3 6 1 4 1 19348 2 1 698 }
id-at-zimbraPublicShareLifetime OBJECT IDENTIFIER ::= { 1 3 6 1 4 1 19348 2 1 1355 }
id-at-zimbraPublicSharingEnabled OBJECT IDENTIFIER ::= { 1 3 6 1 4 1 19348 2 1 1351 }
id-at-zimbraQuotaLastWarnTime OBJECT IDENTIFIER ::= { 1 3 6 1 4 1 19348 2 1 484 }
id-at-zimbraQuotaWarnInterval OBJECT IDENTIFIER ::= { 1 3 6 1 4 1 19348 2 1 485 }
id-at-zimbraQuotaWarnMessage OBJECT IDENTIFIER ::= { 1 3 6 1 4 1 19348 2 1 486 }
id-at-zimbraQuotaWarnPercent OBJECT IDENTIFIER ::= { 1 3 6 1 4 1 19348 2 1 483 }
id-at-zimbraRedoLogArchiveDir OBJECT IDENTIFIER ::= { 1 3 6 1 4 1 19348 2 1 76 }
id-at-zimbraRedoLogCrashRecoveryLookbackSec OBJECT IDENTIFIER ::= { 1 3 6 1 4 1 19348 2 1 1009 }
id-at-zimbraRedoLogDeleteOnRollover OBJECT IDENTIFIER ::= { 1 3 6 1 4 1 19348 2 1 251 }
id-at-zimbraRedoLogEnabled OBJECT IDENTIFIER ::= { 1 3 6 1 4 1 19348 2 1 74 }
id-at-zimbraRedoLogFsyncIntervalMS OBJECT IDENTIFIER ::= { 1 3 6 1 4 1 19348 2 1 79 }
id-at-zimbraRedoLogLogPath OBJECT IDENTIFIER ::= { 1 3 6 1 4 1 19348 2 1 75 }
id-at-zimbraRedoLogProvider OBJECT IDENTIFIER ::= { 1 3 6 1 4 1 19348 2 1 225 }
id-at-zimbraRedoLogRolloverFileSizeKB OBJECT IDENTIFIER ::= { 1 3 6 1 4 1 19348 2 1 78 }
id-at-zimbraRedoLogRolloverHardMaxFileSizeKB OBJECT IDENTIFIER ::= { 1 3 6 1 4 1 19348 2 1 1021 }
id-at-zimbraRedoLogRolloverMinFileAge OBJECT IDENTIFIER ::= { 1 3 6 1 4 1 19348 2 1 1020 }
id-at-zimbraRegexMaxAccessesWhenMatching OBJECT IDENTIFIER ::= { 1 3 6 1 4 1 19348 2 1 1643 }
id-at-zimbraRemoteManagementCommand OBJECT IDENTIFIER ::= { 1 3 6 1 4 1 19348 2 1 336 }
id-at-zimbraRemoteManagementPort OBJECT IDENTIFIER ::= { 1 3 6 1 4 1 19348 2 1 339 }
id-at-zimbraRemoteManagementPrivateKeyPath OBJECT IDENTIFIER ::= { 1 3 6 1 4 1 19348 2 1 338 }
id-at-zimbraRemoteManagementUser OBJECT IDENTIFIER ::= { 1 3 6 1 4 1 19348 2 1 337 }
id-at-zimbraResponseHeader OBJECT IDENTIFIER ::= { 1 3 6 1 4 1 19348 2 1 1074 }
id-at-zimbraReverseProxyAcceptMutex OBJECT IDENTIFIER ::= { 1 3 6 1 4 1 19348 2 1 1594 }
id-at-zimbraReverseProxyAdminEnabled OBJECT IDENTIFIER ::= { 1 3 6 1 4 1 19348 2 1 1321 }
id-at-zimbraReverseProxyAdminIPAddress OBJECT IDENTIFIER ::= { 1 3 6 1 4 1 19348 2 1 697 }
id-at-zimbraReverseProxyAdminPortAttribute OBJECT IDENTIFIER ::= { 1 3 6 1 4 1 19348 2 1 700 }
id-at-zimbraReverseProxyAuthWaitInterval OBJECT IDENTIFIER ::= { 1 3 6 1 4 1 19348 2 1 569 }
id-at-zimbraReverseProxyAvailableLookupTargets OBJECT IDENTIFIER ::= { 1 3 6 1 4 1 19348 2 1 1379 }
id-at-zimbraReverseProxyCacheEntryTTL OBJECT IDENTIFIER ::= { 1 3 6 1 4 1 19348 2 1 732 }
id-at-zimbraReverseProxyCacheFetchTimeout OBJECT IDENTIFIER ::= { 1 3 6 1 4 1 19348 2 1 731 }
id-at-zimbraReverseProxyCacheReconnectInterval OBJECT IDENTIFIER ::= { 1 3 6 1 4 1 19348 2 1 730 }
id-at-zimbraReverseProxyClientCertCA OBJECT IDENTIFIER ::= { 1 3 6 1 4 1 19348 2 1 1201 }
id-at-zimbraReverseProxyClientCertMode OBJECT IDENTIFIER ::= { 1 3 6 1 4 1 19348 2 1 1200 }
id-at-zimbraReverseProxyConnectTimeout OBJECT IDENTIFIER ::= { 1 3 6 1 4 1 19348 2 1 797 }
id-at-zimbraReverseProxyDefaultRealm OBJECT IDENTIFIER ::= { 1 3 6 1 4 1 19348 2 1 703 }
id-at-zimbraReverseProxyDnsLookupInServerEnabled OBJECT IDENTIFIER ::= { 1 3 6 1 4 1 19348 2 1 1384 }
id-at-zimbraReverseProxyDomainNameAttribute OBJECT IDENTIFIER ::= { 1 3 6 1 4 1 19348 2 1 547 }
id-at-zimbraReverseProxyDomainNameQuery OBJECT IDENTIFIER ::= { 1 3 6 1 4 1 19348 2 1 545 }
id-at-zimbraReverseProxyDomainNameSearchBase OBJECT IDENTIFIER ::= { 1 3 6 1 4 1 19348 2 1 546 }
id-at-zimbraReverseProxyErrorHandlerURL OBJECT IDENTIFIER ::= { 1 3 6 1 4 1 19348 2 1 1332 }
id-at-zimbraReverseProxyExactServerVersionCheck OBJECT IDENTIFIER ::= { 1 3 6 1 4 1 19348 2 1 1616 }
id-at-zimbraReverseProxyExternalRouteIncludeOriginalAuthusername OBJECT IDENTIFIER ::= { 1 3 6 1 4 1 19348 2 1 1454 }
id-at-zimbraReverseProxyGenConfigPerVirtualHostname OBJECT IDENTIFIER ::= { 1 3 6 1 4 1 19348 2 1 1374 }
id-at-zimbraReverseProxyHttpEnabled OBJECT IDENTIFIER ::= { 1 3 6 1 4 1 19348 2 1 628 }
id-at-zimbraReverseProxyHttpPortAttribute OBJECT IDENTIFIER ::= { 1 3 6 1 4 1 19348 2 1 632 }
id-at-zimbraReverseProxyHttpSSLPortAttribute OBJECT IDENTIFIER ::= { 1 3 6 1 4 1 19348 2 1 1359 }
id-at-zimbraReverseProxyIPLoginLimit OBJECT IDENTIFIER ::= { 1 3 6 1 4 1 19348 2 1 622 }
id-at-zimbraReverseProxyIPLoginLimitTime OBJECT IDENTIFIER ::= { 1 3 6 1 4 1 19348 2 1 623 }
id-at-zimbraReverseProxyImapEnabledCapability OBJECT IDENTIFIER ::= { 1 3 6 1 4 1 19348 2 1 719 }
id-at-zimbraReverseProxyImapExposeVersionOnBanner OBJECT IDENTIFIER ::= { 1 3 6 1 4 1 19348 2 1 713 }
id-at-zimbraReverseProxyImapPortAttribute OBJECT IDENTIFIER ::= { 1 3 6 1 4 1 19348 2 1 479 }
id-at-zimbraReverseProxyImapSSLPortAttribute OBJECT IDENTIFIER ::= { 1 3 6 1 4 1 19348 2 1 480 }
id-at-zimbraReverseProxyImapSaslGssapiEnabled OBJECT IDENTIFIER ::= { 1 3 6 1 4 1 19348 2 1 643 }
id-at-zimbraReverseProxyImapSaslPlainEnabled OBJECT IDENTIFIER ::= { 1 3 6 1 4 1 19348 2 1 728 }
id-at-zimbraReverseProxyImapStartTlsMode OBJECT IDENTIFIER ::= { 1 3 6 1 4 1 19348 2 1 641 }
id-at-zimbraReverseProxyInactivityTimeout OBJECT IDENTIFIER ::= { 1 3 6 1 4 1 19348 2 1 735 }
id-at-zimbraReverseProxyIpThrottleMsg OBJECT IDENTIFIER ::= { 1 3 6 1 4 1 19348 2 1 727 }
id-at-zimbraReverseProxyLogLevel OBJECT IDENTIFIER ::= { 1 3 6 1 4 1 19348 2 1 723 }
id-at-zimbraReverseProxyLookupTarget OBJECT IDENTIFIER ::= { 1 3 6 1 4 1 19348 2 1 504 }
id-at-zimbraReverseProxyMailEnabled OBJECT IDENTIFIER ::= { 1 3 6 1 4 1 19348 2 1 629 }
id-at-zimbraReverseProxyMailHostAttribute OBJECT IDENTIFIER ::= { 1 3 6 1 4 1 19348 2 1 474 }
id-at-zimbraReverseProxyMailHostQuery OBJECT IDENTIFIER ::= { 1 3 6 1 4 1 19348 2 1 472 }
id-at-zimbraReverseProxyMailHostSearchBase OBJECT IDENTIFIER ::= { 1 3 6 1 4 1 19348 2 1 473 }
id-at-zimbraReverseProxyMailImapEnabled OBJECT IDENTIFIER ::= { 1 3 6 1 4 1 19348 2 1 1621 }
id-at-zimbraReverseProxyMailImapsEnabled OBJECT IDENTIFIER ::= { 1 3 6 1 4 1 19348 2 1 1622 }
id-at-zimbraReverseProxyMailMode OBJECT IDENTIFIER ::= { 1 3 6 1 4 1 19348 2 1 685 }
id-at-zimbraReverseProxyMailPop3Enabled OBJECT IDENTIFIER ::= { 1 3 6 1 4 1 19348 2 1 1623 }
id-at-zimbraReverseProxyMailPop3sEnabled OBJECT IDENTIFIER ::= { 1 3 6 1 4 1 19348 2 1 1624 }
id-at-zimbraReverseProxyPassErrors OBJECT IDENTIFIER ::= { 1 3 6 1 4 1 19348 2 1 736 }
id-at-zimbraReverseProxyPop3EnabledCapability OBJECT IDENTIFIER ::= { 1 3 6 1 4 1 19348 2 1 721 }
id-at-zimbraReverseProxyPop3ExposeVersionOnBanner OBJECT IDENTIFIER ::= { 1 3 6 1 4 1 19348 2 1 712 }
id-at-zimbraReverseProxyPop3PortAttribute OBJECT IDENTIFIER ::= { 1 3 6 1 4 1 19348 2 1 477 }
id-at-zimbraReverseProxyPop3SSLPortAttribute OBJECT IDENTIFIER ::= { 1 3 6 1 4 1 19348 2 1 478 }
id-at-zimbraReverseProxyPop3SaslGssapiEnabled OBJECT IDENTIFIER ::= { 1 3 6 1 4 1 19348 2 1 644 }
id-at-zimbraReverseProxyPop3SaslPlainEnabled OBJECT IDENTIFIER ::= { 1 3 6 1 4 1 19348 2 1 729 }
id-at-zimbraReverseProxyPop3StartTlsMode OBJECT IDENTIFIER ::= { 1 3 6 1 4 1 19348 2 1 642 }
id-at-zimbraReverseProxyPortQuery OBJECT IDENTIFIER ::= { 1 3 6 1 4 1 19348 2 1 475 }
id-at-zimbraReverseProxyPortSearchBase OBJECT IDENTIFIER ::= { 1 3 6 1 4 1 19348 2 1 476 }
id-at-zimbraReverseProxyRouteLookupTimeout OBJECT IDENTIFIER ::= { 1 3 6 1 4 1 19348 2 1 745 }
id-at-zimbraReverseProxyRouteLookupTimeoutCache OBJECT IDENTIFIER ::= { 1 3 6 1 4 1 19348 2 1 778 }
id-at-zimbraReverseProxySSLCiphers OBJECT IDENTIFIER ::= { 1 3 6 1 4 1 19348 2 1 640 }
id-at-zimbraReverseProxySSLECDHCurve OBJECT IDENTIFIER ::= { 1 3 6 1 4 1 19348 2 1 1626 }
id-at-zimbraReverseProxySSLProtocols OBJECT IDENTIFIER ::= { 1 3 6 1 4 1 19348 2 1 1653 }
id-at-zimbraReverseProxySSLToUpstreamEnabled OBJECT IDENTIFIER ::= { 1 3 6 1 4 1 19348 2 1 1360 }
id-at-zimbraReverseProxySendImapId OBJECT IDENTIFIER ::= { 1 3 6 1 4 1 19348 2 1 588 }
id-at-zimbraReverseProxySendPop3Xoip OBJECT IDENTIFIER ::= { 1 3 6 1 4 1 19348 2 1 587 }
id-at-zimbraReverseProxyUpstreamConnectTimeout OBJECT IDENTIFIER ::= { 1 3 6 1 4 1 19348 2 1 1440 }
id-at-zimbraReverseProxyUpstreamEwsServers OBJECT IDENTIFIER ::= { 1 3 6 1 4 1 19348 2 1 1595 }
id-at-zimbraReverseProxyUpstreamLoginServers OBJECT IDENTIFIER ::= { 1 3 6 1 4 1 19348 2 1 1603 }
id-at-zimbraReverseProxyUpstreamPollingTimeout OBJECT IDENTIFIER ::= { 1 3 6 1 4 1 19348 2 1 1337 }
id-at-zimbraReverseProxyUpstreamReadTimeout OBJECT IDENTIFIER ::= { 1 3 6 1 4 1 19348 2 1 1335 }
id-at-zimbraReverseProxyUpstreamSendTimeout OBJECT IDENTIFIER ::= { 1 3 6 1 4 1 19348 2 1 1336 }
id-at-zimbraReverseProxyUpstreamServers OBJECT IDENTIFIER ::= { 1 3 6 1 4 1 19348 2 1 1378 }
id-at-zimbraReverseProxyUseExternalRoute OBJECT IDENTIFIER ::= { 1 3 6 1 4 1 19348 2 1 779 }
id-at-zimbraReverseProxyUseExternalRouteIfAccountNotExist OBJECT IDENTIFIER ::= { 1 3 6 1 4 1 19348 2 1 1132 }
id-at-zimbraReverseProxyUserLoginLimit OBJECT IDENTIFIER ::= { 1 3 6 1 4 1 19348 2 1 624 }
id-at-zimbraReverseProxyUserLoginLimitTime OBJECT IDENTIFIER ::= { 1 3 6 1 4 1 19348 2 1 625 }
id-at-zimbraReverseProxyUserNameAttribute OBJECT IDENTIFIER ::= { 1 3 6 1 4 1 19348 2 1 572 }
id-at-zimbraReverseProxyUserThrottleMsg OBJECT IDENTIFIER ::= { 1 3 6 1 4 1 19348 2 1 726 }
id-at-zimbraReverseProxyWorkerConnections OBJECT IDENTIFIER ::= { 1 3 6 1 4 1 19348 2 1 725 }
id-at-zimbraReverseProxyWorkerProcesses OBJECT IDENTIFIER ::= { 1 3 6 1 4 1 19348 2 1 724 }
id-at-zimbraSMIMELdapAttribute OBJECT IDENTIFIER ::= { 1 3 6 1 4 1 19348 2 1 1182 }
id-at-zimbraSMIMELdapBindDn OBJECT IDENTIFIER ::= { 1 3 6 1 4 1 19348 2 1 1178 }
id-at-zimbraSMIMELdapBindPassword OBJECT IDENTIFIER ::= { 1 3 6 1 4 1 19348 2 1 1179 }
id-at-zimbraSMIMELdapDiscoverSearchBaseEnabled OBJECT IDENTIFIER ::= { 1 3 6 1 4 1 19348 2 1 1209 }
id-at-zimbraSMIMELdapFilter OBJECT IDENTIFIER ::= { 1 3 6 1 4 1 19348 2 1 1181 }
id-at-zimbraSMIMELdapSearchBase OBJECT IDENTIFIER ::= { 1 3 6 1 4 1 19348 2 1 1180 }
id-at-zimbraSMIMELdapStartTlsEnabled OBJECT IDENTIFIER ::= { 1 3 6 1 4 1 19348 2 1 1177 }
id-at-zimbraSMIMELdapURL OBJECT IDENTIFIER ::= { 1 3 6 1 4 1 19348 2 1 1176 }
id-at-zimbraSSLCertificate OBJECT IDENTIFIER ::= { 1 3 6 1 4 1 19348 2 1 563 }
id-at-zimbraSSLExcludeCipherSuites OBJECT IDENTIFIER ::= { 1 3 6 1 4 1 19348 2 1 639 }
id-at-zimbraSSLIncludeCipherSuites OBJECT IDENTIFIER ::= { 1 3 6 1 4 1 19348 2 1 1604 }
id-at-zimbraSSLPrivateKey OBJECT IDENTIFIER ::= { 1 3 6 1 4 1 19348 2 1 564 }
id-at-zimbraSaslGssapiRequiresTls OBJECT IDENTIFIER ::= { 1 3 6 1 4 1 19348 2 1 1068 }
id-at-zimbraScheduledTaskNumThreads OBJECT IDENTIFIER ::= { 1 3 6 1 4 1 19348 2 1 522 }
id-at-zimbraServerExtraObjectClass OBJECT IDENTIFIER ::= { 1 3 6 1 4 1 19348 2 1 756 }
id-at-zimbraServerId OBJECT IDENTIFIER ::= { 1 3 6 1 4 1 19348 2 1 742 }
id-at-zimbraServerInheritedAttr OBJECT IDENTIFIER ::= { 1 3 6 1 4 1 19348 2 1 62 }
id-at-zimbraServerVersion OBJECT IDENTIFIER ::= { 1 3 6 1 4 1 19348 2 1 1598 }
id-at-zimbraServerVersionBuild OBJECT IDENTIFIER ::= { 1 3 6 1 4 1 19348 2 1 1602 }
id-at-zimbraServerVersionMajor OBJECT IDENTIFIER ::= { 1 3 6 1 4 1 19348 2 1 1599 }
id-at-zimbraServerVersionMicro OBJECT IDENTIFIER ::= { 1 3 6 1 4 1 19348 2 1 1601 }
id-at-zimbraServerVersionMinor OBJECT IDENTIFIER ::= { 1 3 6 1 4 1 19348 2 1 1600 }
id-at-zimbraServerVersionType OBJECT IDENTIFIER ::= { 1 3 6 1 4 1 19348 2 1 1605 }
id-at-zimbraServiceEnabled OBJECT IDENTIFIER ::= { 1 3 6 1 4 1 19348 2 1 220 }
id-at-zimbraServiceHostname OBJECT IDENTIFIER ::= { 1 3 6 1 4 1 19348 2 1 65 }
id-at-zimbraServiceInstalled OBJECT IDENTIFIER ::= { 1 3 6 1 4 1 19348 2 1 221 }
id-at-zimbraShareInfo OBJECT IDENTIFIER ::= { 1 3 6 1 4 1 19348 2 1 357 }
id-at-zimbraShareLifetime OBJECT IDENTIFIER ::= { 1 3 6 1 4 1 19348 2 1 1348 }
id-at-zimbraShareNotificationMtaAuthAccount OBJECT IDENTIFIER ::= { 1 3 6 1 4 1 19348 2 1 1343 }
id-at-zimbraShareNotificationMtaAuthPassword OBJECT IDENTIFIER ::= { 1 3 6 1 4 1 19348 2 1 1344 }
id-at-zimbraShareNotificationMtaAuthRequired OBJECT IDENTIFIER ::= { 1 3 6 1 4 1 19348 2 1 1346 }
id-at-zimbraShareNotificationMtaConnectionType OBJECT IDENTIFIER ::= { 1 3 6 1 4 1 19348 2 1 1345 }
id-at-zimbraShareNotificationMtaEnabled OBJECT IDENTIFIER ::= { 1 3 6 1 4 1 19348 2 1 1361 }
id-at-zimbraShareNotificationMtaHostname OBJECT IDENTIFIER ::= { 1 3 6 1 4 1 19348 2 1 1341 }
id-at-zimbraShareNotificationMtaPort OBJECT IDENTIFIER ::= { 1 3 6 1 4 1 19348 2 1 1342 }
id-at-zimbraShareOwnerAccountId OBJECT IDENTIFIER ::= { 1 3 6 1 4 1 19348 2 1 1375 }
id-at-zimbraSharedItem OBJECT IDENTIFIER ::= { 1 3 6 1 4 1 19348 2 1 1219 }
id-at-zimbraSharingUpdatePublishInterval OBJECT IDENTIFIER ::= { 1 3 6 1 4 1 19348 2 1 1220 }
id-at-zimbraSignatureId OBJECT IDENTIFIER ::= { 1 3 6 1 4 1 19348 2 1 490 }
id-at-zimbraSignatureMaxNumEntries OBJECT IDENTIFIER ::= { 1 3 6 1 4 1 19348 2 1 493 }
id-at-zimbraSignatureMinNumEntries OBJECT IDENTIFIER ::= { 1 3 6 1 4 1 19348 2 1 523 }
id-at-zimbraSignatureName OBJECT IDENTIFIER ::= { 1 3 6 1 4 1 19348 2 1 491 }
id-at-zimbraSkinBackgroundColor OBJECT IDENTIFIER ::= { 1 3 6 1 4 1 19348 2 1 648 }
id-at-zimbraSkinFavicon OBJECT IDENTIFIER ::= { 1 3 6 1 4 1 19348 2 1 800 }
id-at-zimbraSkinForegroundColor OBJECT IDENTIFIER ::= { 1 3 6 1 4 1 19348 2 1 647 }
id-at-zimbraSkinLogoAppBanner OBJECT IDENTIFIER ::= { 1 3 6 1 4 1 19348 2 1 671 }
id-at-zimbraSkinLogoLoginBanner OBJECT IDENTIFIER ::= { 1 3 6 1 4 1 19348 2 1 670 }
id-at-zimbraSkinLogoURL OBJECT IDENTIFIER ::= { 1 3 6 1 4 1 19348 2 1 649 }
id-at-zimbraSkinSecondaryColor OBJECT IDENTIFIER ::= { 1 3 6 1 4 1 19348 2 1 668 }
id-at-zimbraSkinSelectionColor OBJECT IDENTIFIER ::= { 1 3 6 1 4 1 19348 2 1 669 }
id-at-zimbraSmtpEnableTrace OBJECT IDENTIFIER ::= { 1 3 6 1 4 1 19348 2 1 793 }
id-at-zimbraSmtpHostname OBJECT IDENTIFIER ::= { 1 3 6 1 4 1 19348 2 1 97 }
id-at-zimbraSmtpPort OBJECT IDENTIFIER ::= { 1 3 6 1 4 1 19348 2 1 98 }
id-at-zimbraSmtpRestrictEnvelopeFrom OBJECT IDENTIFIER ::= { 1 3 6 1 4 1 19348 2 1 1077 }
id-at-zimbraSmtpSendAddAuthenticatedUser OBJECT IDENTIFIER ::= { 1 3 6 1 4 1 19348 2 1 747 }
id-at-zimbraSmtpSendAddMailer OBJECT IDENTIFIER ::= { 1 3 6 1 4 1 19348 2 1 636 }
id-at-zimbraSmtpSendAddOriginatingIP OBJECT IDENTIFIER ::= { 1 3 6 1 4 1 19348 2 1 435 }
id-at-zimbraSmtpSendPartial OBJECT IDENTIFIER ::= { 1 3 6 1 4 1 19348 2 1 249 }
id-at-zimbraSmtpTimeout OBJECT IDENTIFIER ::= { 1 3 6 1 4 1 19348 2 1 99 }
id-at-zimbraSoapExposeVersion OBJECT IDENTIFIER ::= { 1 3 6 1 4 1 19348 2 1 708 }
id-at-zimbraSoapRequestMaxSize OBJECT IDENTIFIER ::= { 1 3 6 1 4 1 19348 2 1 557 }
id-at-zimbraSocialcastURL OBJECT IDENTIFIER ::= { 1 3 6 1 4 1 19348 2 1 1389 }
id-at-zimbraSpamApplyUserFilters OBJECT IDENTIFIER ::= { 1 3 6 1 4 1 19348 2 1 604 }
id-at-zimbraSpamCheckEnabled OBJECT IDENTIFIER ::= { 1 3 6 1 4 1 19348 2 1 201 }
id-at-zimbraSpamHeader OBJECT IDENTIFIER ::= { 1 3 6 1 4 1 19348 2 1 210 }
id-at-zimbraSpamHeaderValue OBJECT IDENTIFIER ::= { 1 3 6 1 4 1 19348 2 1 211 }
id-at-zimbraSpamIsNotSpamAccount OBJECT IDENTIFIER ::= { 1 3 6 1 4 1 19348 2 1 245 }
id-at-zimbraSpamIsSpamAccount OBJECT IDENTIFIER ::= { 1 3 6 1 4 1 19348 2 1 244 }
id-at-zimbraSpamKillPercent OBJECT IDENTIFIER ::= { 1 3 6 1 4 1 19348 2 1 202 }
id-at-zimbraSpamReportEnvelopeFrom OBJECT IDENTIFIER ::= { 1 3 6 1 4 1 19348 2 1 1049 }
id-at-zimbraSpamReportSenderHeader OBJECT IDENTIFIER ::= { 1 3 6 1 4 1 19348 2 1 465 }
id-at-zimbraSpamReportTypeHam OBJECT IDENTIFIER ::= { 1 3 6 1 4 1 19348 2 1 468 }
id-at-zimbraSpamReportTypeHeader OBJECT IDENTIFIER ::= { 1 3 6 1 4 1 19348 2 1 466 }
id-at-zimbraSpamReportTypeSpam OBJECT IDENTIFIER ::= { 1 3 6 1 4 1 19348 2 1 467 }
id-at-zimbraSpamSubjectTag OBJECT IDENTIFIER ::= { 1 3 6 1 4 1 19348 2 1 203 }
id-at-zimbraSpamTagPercent OBJECT IDENTIFIER ::= { 1 3 6 1 4 1 19348 2 1 204 }
id-at-zimbraSpamTrashAlias OBJECT IDENTIFIER ::= { 1 3 6 1 4 1 19348 2 1 1167 }
id-at-zimbraSpamWhitelistHeader OBJECT IDENTIFIER ::= { 1 3 6 1 4 1 19348 2 1 1257 }
id-at-zimbraSpamWhitelistHeaderValue OBJECT IDENTIFIER ::= { 1 3 6 1 4 1 19348 2 1 1258 }
id-at-zimbraSpellAvailableDictionary OBJECT IDENTIFIER ::= { 1 3 6 1 4 1 19348 2 1 1042 }
id-at-zimbraSpellCheckURL OBJECT IDENTIFIER ::= { 1 3 6 1 4 1 19348 2 1 267 }
id-at-zimbraSpnegoAuthEnabled OBJECT IDENTIFIER ::= { 1 3 6 1 4 1 19348 2 1 1118 }
id-at-zimbraSpnegoAuthErrorURL OBJECT IDENTIFIER ::= { 1 3 6 1 4 1 19348 2 1 1124 }
id-at-zimbraSpnegoAuthPrincipal OBJECT IDENTIFIER ::= { 1 3 6 1 4 1 19348 2 1 1122 }
id-at-zimbraSpnegoAuthRealm OBJECT IDENTIFIER ::= { 1 3 6 1 4 1 19348 2 1 1119 }
id-at-zimbraSpnegoAuthTargetName OBJECT IDENTIFIER ::= { 1 3 6 1 4 1 19348 2 1 1123 }
id-at-zimbraSshPublicKey OBJECT IDENTIFIER ::= { 1 3 6 1 4 1 19348 2 1 262 }
id-at-zimbraSslCaCert OBJECT IDENTIFIER ::= { 1 3 6 1 4 1 19348 2 1 277 }
id-at-zimbraSslCaKey OBJECT IDENTIFIER ::= { 1 3 6 1 4 1 19348 2 1 278 }
id-at-zimbraStandardClientCustomPrefTab OBJECT IDENTIFIER ::= { 1 3 6 1 4 1 19348 2 1 1267 }
id-at-zimbraStandardClientCustomPrefTabsEnabled OBJECT IDENTIFIER ::= { 1 3 6 1 4 1 19348 2 1 1266 }
id-at-zimbraStatThreadNamePrefix OBJECT IDENTIFIER ::= { 1 3 6 1 4 1 19348 2 1 792 }
id-at-zimbraSyncWindowSize OBJECT IDENTIFIER ::= { 1 3 6 1 4 1 19348 2 1 437 }
id-at-zimbraTableMaintenanceGrowthFactor OBJECT IDENTIFIER ::= { 1 3 6 1 4 1 19348 2 1 171 }
id-at-zimbraTableMaintenanceMaxRows OBJECT IDENTIFIER ::= { 1 3 6 1 4 1 19348 2 1 169 }
id-at-zimbraTableMaintenanceMinRows OBJECT IDENTIFIER ::= { 1 3 6 1 4 1 19348 2 1 168 }
id-at-zimbraTableMaintenanceOperation OBJECT IDENTIFIER ::= { 1 3 6 1 4 1 19348 2 1 170 }
id-at-zimbraTextAnalyzer OBJECT IDENTIFIER ::= { 1 3 6 1 4 1 19348 2 1 393 }
id-at-zimbraThreadMonitorEnabled OBJECT IDENTIFIER ::= { 1 3 6 1 4 1 19348 2 1 1583 }
id-at-zimbraThrottleSafeHosts OBJECT IDENTIFIER ::= { 1 3 6 1 4 1 19348 2 1 1383 }
id-at-zimbraThrottleWhitelist OBJECT IDENTIFIER ::= { 1 3 6 1 4 1 19348 2 1 1449 }
id-at-zimbraTimeZoneDaylightDtStart OBJECT IDENTIFIER ::= { 1 3 6 1 4 1 19348 2 1 232 }
id-at-zimbraTimeZoneDaylightOffset OBJECT IDENTIFIER ::= { 1 3 6 1 4 1 19348 2 1 233 }
id-at-zimbraTimeZoneDaylightRRule OBJECT IDENTIFIER ::= { 1 3 6 1 4 1 19348 2 1 234 }
id-at-zimbraTimeZoneStandardDtStart OBJECT IDENTIFIER ::= { 1 3 6 1 4 1 19348 2 1 229 }
id-at-zimbraTimeZoneStandardOffset OBJECT IDENTIFIER ::= { 1 3 6 1 4 1 19348 2 1 230 }
id-at-zimbraTimeZoneStandardRRule OBJECT IDENTIFIER ::= { 1 3 6 1 4 1 19348 2 1 231 }
id-at-zimbraTouchJSErrorTrackingEnabled OBJECT IDENTIFIER ::= { 1 3 6 1 4 1 19348 2 1 1433 }
id-at-zimbraTouchJSErrorTrackingKey OBJECT IDENTIFIER ::= { 1 3 6 1 4 1 19348 2 1 1434 }
id-at-zimbraUCCallControlURL OBJECT IDENTIFIER ::= { 1 3 6 1 4 1 19348 2 1 1405 }
id-at-zimbraUCPassword OBJECT IDENTIFIER ::= { 1 3 6 1 4 1 19348 2 1 1409 }
id-at-zimbraUCPresenceSessionId OBJECT IDENTIFIER ::= { 1 3 6 1 4 1 19348 2 1 1407 }
id-at-zimbraUCPresenceURL OBJECT IDENTIFIER ::= { 1 3 6 1 4 1 19348 2 1 1406 }
id-at-zimbraUCProvider OBJECT IDENTIFIER ::= { 1 3 6 1 4 1 19348 2 1 1402 }
id-at-zimbraUCProviderEnabled OBJECT IDENTIFIER ::= { 1 3 6 1 4 1 19348 2 1 1410 }
id-at-zimbraUCServiceId OBJECT IDENTIFIER ::= { 1 3 6 1 4 1 19348 2 1 1401 }
id-at-zimbraUCUserURL OBJECT IDENTIFIER ::= { 1 3 6 1 4 1 19348 2 1 1403 }
id-at-zimbraUCUsername OBJECT IDENTIFIER ::= { 1 3 6 1 4 1 19348 2 1 1408 }
id-at-zimbraUCVoicemailURL OBJECT IDENTIFIER ::= { 1 3 6 1 4 1 19348 2 1 1404 }
id-at-zimbraUserServicesEnabled OBJECT IDENTIFIER ::= { 1 3 6 1 4 1 19348 2 1 146 }
id-at-zimbraVersion OBJECT IDENTIFIER ::= { 1 3 6 1 4 1 19348 2 1 399 }
id-at-zimbraVersionCheckInterval OBJECT IDENTIFIER ::= { 1 3 6 1 4 1 19348 2 1 1059 }
id-at-zimbraVersionCheckLastAttempt OBJECT IDENTIFIER ::= { 1 3 6 1 4 1 19348 2 1 1056 }
id-at-zimbraVersionCheckLastResponse OBJECT IDENTIFIER ::= { 1 3 6 1 4 1 19348 2 1 1058 }
id-at-zimbraVersionCheckLastSuccess OBJECT IDENTIFIER ::= { 1 3 6 1 4 1 19348 2 1 1057 }
id-at-zimbraVersionCheckNotificationBody OBJECT IDENTIFIER ::= { 1 3 6 1 4 1 19348 2 1 1066 }
id-at-zimbraVersionCheckNotificationEmail OBJECT IDENTIFIER ::= { 1 3 6 1 4 1 19348 2 1 1063 }
id-at-zimbraVersionCheckNotificationEmailFrom OBJECT IDENTIFIER ::= { 1 3 6 1 4 1 19348 2 1 1064 }
id-at-zimbraVersionCheckNotificationSubject OBJECT IDENTIFIER ::= { 1 3 6 1 4 1 19348 2 1 1065 }
id-at-zimbraVersionCheckSendNotifications OBJECT IDENTIFIER ::= { 1 3 6 1 4 1 19348 2 1 1062 }
id-at-zimbraVersionCheckServer OBJECT IDENTIFIER ::= { 1 3 6 1 4 1 19348 2 1 1060 }
id-at-zimbraVersionCheckURL OBJECT IDENTIFIER ::= { 1 3 6 1 4 1 19348 2 1 1061 }
id-at-zimbraVirtualAccountInitialPasswordSet OBJECT IDENTIFIER ::= { 1 3 6 1 4 1 19348 2 1 1414 }
id-at-zimbraVirtualHostname OBJECT IDENTIFIER ::= { 1 3 6 1 4 1 19348 2 1 352 }
id-at-zimbraVirtualIPAddress OBJECT IDENTIFIER ::= { 1 3 6 1 4 1 19348 2 1 562 }
id-at-zimbraVirusBlockEncryptedArchive OBJECT IDENTIFIER ::= { 1 3 6 1 4 1 19348 2 1 205 }
id-at-zimbraVirusCheckEnabled OBJECT IDENTIFIER ::= { 1 3 6 1 4 1 19348 2 1 206 }
id-at-zimbraVirusDefinitionsUpdateFrequency OBJECT IDENTIFIER ::= { 1 3 6 1 4 1 19348 2 1 191 }
id-at-zimbraVirusWarnAdmin OBJECT IDENTIFIER ::= { 1 3 6 1 4 1 19348 2 1 207 }
id-at-zimbraVirusWarnRecipient OBJECT IDENTIFIER ::= { 1 3 6 1 4 1 19348 2 1 208 }
id-at-zimbraWebClientAdminReference OBJECT IDENTIFIER ::= { 1 3 6 1 4 1 19348 2 1 701 }
id-at-zimbraWebClientLoginURL OBJECT IDENTIFIER ::= { 1 3 6 1 4 1 19348 2 1 506 }
id-at-zimbraWebClientLoginURLAllowedIP OBJECT IDENTIFIER ::= { 1 3 6 1 4 1 19348 2 1 1352 }
id-at-zimbraWebClientLoginURLAllowedUA OBJECT IDENTIFIER ::= { 1 3 6 1 4 1 19348 2 1 1141 }
id-at-zimbraWebClientLogoutURL OBJECT IDENTIFIER ::= { 1 3 6 1 4 1 19348 2 1 507 }
id-at-zimbraWebClientLogoutURLAllowedIP OBJECT IDENTIFIER ::= { 1 3 6 1 4 1 19348 2 1 1353 }
id-at-zimbraWebClientLogoutURLAllowedUA OBJECT IDENTIFIER ::= { 1 3 6 1 4 1 19348 2 1 1142 }
id-at-zimbraWebClientMaxInputBufferLength OBJECT IDENTIFIER ::= { 1 3 6 1 4 1 19348 2 1 1339 }
id-at-zimbraWebClientOfflineSyncMaxDays OBJECT IDENTIFIER ::= { 1 3 6 1 4 1 19348 2 1 1452 }
id-at-zimbraWebClientShowOfflineLink OBJECT IDENTIFIER ::= { 1 3 6 1 4 1 19348 2 1 1047 }
id-at-zimbraWebClientURL OBJECT IDENTIFIER ::= { 1 3 6 1 4 1 19348 2 1 1445 }
id-at-zimbraWebGzipEnabled OBJECT IDENTIFIER ::= { 1 3 6 1 4 1 19348 2 1 1468 }
id-at-zimbraXMPPComponentCategory OBJECT IDENTIFIER ::= { 1 3 6 1 4 1 19348 2 1 737 }
id-at-zimbraXMPPComponentClassName OBJECT IDENTIFIER ::= { 1 3 6 1 4 1 19348 2 1 763 }
id-at-zimbraXMPPComponentFeatures OBJECT IDENTIFIER ::= { 1 3 6 1 4 1 19348 2 1 739 }
id-at-zimbraXMPPComponentName OBJECT IDENTIFIER ::= { 1 3 6 1 4 1 19348 2 1 740 }
id-at-zimbraXMPPComponentType OBJECT IDENTIFIER ::= { 1 3 6 1 4 1 19348 2 1 738 }
id-at-zimbraXMPPEnabled OBJECT IDENTIFIER ::= { 1 3 6 1 4 1 19348 2 1 397 }
id-at-zimbraXMPPServerDialbackKey OBJECT IDENTIFIER ::= { 1 3 6 1 4 1 19348 2 1 695 }
id-at-zimbraYahooId OBJECT IDENTIFIER ::= { 1 3 6 1 4 1 19348 2 1 658 }
id-at-zimbraZimletAvailableZimlets OBJECT IDENTIFIER ::= { 1 3 6 1 4 1 19348 2 1 291 }
id-at-zimbraZimletContentObject OBJECT IDENTIFIER ::= { 1 3 6 1 4 1 19348 2 1 288 }
id-at-zimbraZimletDataSensitiveInMixedModeDisabled OBJECT IDENTIFIER ::= { 1 3 6 1 4 1 19348 2 1 1269 }
id-at-zimbraZimletDescription OBJECT IDENTIFIER ::= { 1 3 6 1 4 1 19348 2 1 283 }
id-at-zimbraZimletDomainAvailableZimlets OBJECT IDENTIFIER ::= { 1 3 6 1 4 1 19348 2 1 710 }
id-at-zimbraZimletEnabled OBJECT IDENTIFIER ::= { 1 3 6 1 4 1 19348 2 1 301 }
id-at-zimbraZimletHandlerClass OBJECT IDENTIFIER ::= { 1 3 6 1 4 1 19348 2 1 286 }
id-at-zimbraZimletHandlerConfig OBJECT IDENTIFIER ::= { 1 3 6 1 4 1 19348 2 1 287 }
id-at-zimbraZimletIndexingEnabled OBJECT IDENTIFIER ::= { 1 3 6 1 4 1 19348 2 1 284 }
id-at-zimbraZimletIsExtension OBJECT IDENTIFIER ::= { 1 3 6 1 4 1 19348 2 1 304 }
id-at-zimbraZimletJspEnabled OBJECT IDENTIFIER ::= { 1 3 6 1 4 1 19348 2 1 1575 }
id-at-zimbraZimletKeyword OBJECT IDENTIFIER ::= { 1 3 6 1 4 1 19348 2 1 281 }
id-at-zimbraZimletLoadSynchronously OBJECT IDENTIFIER ::= { 1 3 6 1 4 1 19348 2 1 1391 }
id-at-zimbraZimletPanelItem OBJECT IDENTIFIER ::= { 1 3 6 1 4 1 19348 2 1 289 }
id-at-zimbraZimletPriority OBJECT IDENTIFIER ::= { 1 3 6 1 4 1 19348 2 1 302 }
id-at-zimbraZimletScript OBJECT IDENTIFIER ::= { 1 3 6 1 4 1 19348 2 1 290 }
id-at-zimbraZimletServerIndexRegex OBJECT IDENTIFIER ::= { 1 3 6 1 4 1 19348 2 1 292 }
id-at-zimbraZimletStoreMatched OBJECT IDENTIFIER ::= { 1 3 6 1 4 1 19348 2 1 285 }
id-at-zimbraZimletTarget OBJECT IDENTIFIER ::= { 1 3 6 1 4 1 19348 2 1 606 }
id-at-zimbraZimletUserProperties OBJECT IDENTIFIER ::= { 1 3 6 1 4 1 19348 2 1 296 }
id-at-zimbraZimletVersion OBJECT IDENTIFIER ::= { 1 3 6 1 4 1 19348 2 1 282 }
id-at-zimbraZookeeperClientServerList OBJECT IDENTIFIER ::= { 1 3 6 1 4 1 19348 2 1 1447 }
id-oc-zimbraMailRecipient OBJECT IDENTIFIER ::= { 1 3 6 1 4 1 19348 2 2 7 }
id-oc-zimbraAccount OBJECT IDENTIFIER ::= { 1 3 6 1 4 1 19348 2 2 1 }
id-oc-zimbraAlias OBJECT IDENTIFIER ::= { 1 3 6 1 4 1 19348 2 2 11 }
id-oc-zimbraDistributionList OBJECT IDENTIFIER ::= { 1 3 6 1 4 1 19348 2 2 6 }
id-oc-zimbraCOS OBJECT IDENTIFIER ::= { 1 3 6 1 4 1 19348 2 2 3 }
id-oc-zimbraGlobalConfig OBJECT IDENTIFIER ::= { 1 3 6 1 4 1 19348 2 2 9 }
id-oc-zimbraDomain OBJECT IDENTIFIER ::= { 1 3 6 1 4 1 19348 2 2 4 }
id-oc-zimbraSecurityGroup OBJECT IDENTIFIER ::= { 1 3 6 1 4 1 19348 2 2 5 }
id-oc-zimbraServer OBJECT IDENTIFIER ::= { 1 3 6 1 4 1 19348 2 2 8 }
id-oc-zimbraAlwaysOnCluster OBJECT IDENTIFIER ::= { 1 3 6 1 4 1 19348 2 2 32 }
id-oc-zimbraUCService OBJECT IDENTIFIER ::= { 1 3 6 1 4 1 19348 2 2 31 }
id-oc-zimbraMimeEntry OBJECT IDENTIFIER ::= { 1 3 6 1 4 1 19348 2 2 12 }
id-oc-zimbraObjectEntry OBJECT IDENTIFIER ::= { 1 3 6 1 4 1 19348 2 2 13 }
id-oc-zimbraTimeZone OBJECT IDENTIFIER ::= { 1 3 6 1 4 1 19348 2 2 14 }
id-oc-zimbraZimletEntry OBJECT IDENTIFIER ::= { 1 3 6 1 4 1 19348 2 2 15 }
id-oc-zimbraCalendarResource OBJECT IDENTIFIER ::= { 1 3 6 1 4 1 19348 2 2 16 }
id-oc-zimbraIdentity OBJECT IDENTIFIER ::= { 1 3 6 1 4 1 19348 2 2 17 }
id-oc-zimbraDataSource OBJECT IDENTIFIER ::= { 1 3 6 1 4 1 19348 2 2 18 }
id-oc-zimbraPop3DataSource OBJECT IDENTIFIER ::= { 1 3 6 1 4 1 19348 2 2 19 }
id-oc-zimbraImapDataSource OBJECT IDENTIFIER ::= { 1 3 6 1 4 1 19348 2 2 20 }
id-oc-zimbraRssDataSource OBJECT IDENTIFIER ::= { 1 3 6 1 4 1 19348 2 2 24 }
id-oc-zimbraLiveDataSource OBJECT IDENTIFIER ::= { 1 3 6 1 4 1 19348 2 2 25 }
id-oc-zimbraGalDataSource OBJECT IDENTIFIER ::= { 1 3 6 1 4 1 19348 2 2 26 }
id-oc-zimbraSignature OBJECT IDENTIFIER ::= { 1 3 6 1 4 1 19348 2 2 21 }
id-oc-zimbraXMPPComponent OBJECT IDENTIFIER ::= { 1 3 6 1 4 1 19348 2 2 22 }
id-oc-zimbraAclTarget OBJECT IDENTIFIER ::= { 1 3 6 1 4 1 19348 2 2 23 }
id-oc-zimbraGroup OBJECT IDENTIFIER ::= { 1 3 6 1 4 1 19348 2 2 27 }
id-oc-zimbraGroupDynamicUnit OBJECT IDENTIFIER ::= { 1 3 6 1 4 1 19348 2 2 28 }
id-oc-zimbraGroupStaticUnit OBJECT IDENTIFIER ::= { 1 3 6 1 4 1 19348 2 2 29 }
id-oc-zimbraShareLocator OBJECT IDENTIFIER ::= { 1 3 6 1 4 1 19348 2 2 30 }

-- Attribute types

zimbraACE ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraACE"}
  LDAP-DESC                 "Zimbra access control list"
  ID                        id-at-zimbraACE }

-- LDAP syntax length {32} rendered as DirectoryString{32}.
zimbraAccountCalendarUserType ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraAccountCalendarUserType"}
  LDAP-DESC                 "calendar user type - USER (default) or RESOURCE"
  ID                        id-at-zimbraAccountCalendarUserType }

-- LDAP syntax length {1024} rendered as DirectoryString{1024}.
zimbraAccountClientAttr ATTRIBUTE ::= {
  WITH SYNTAX               DirectoryString{1024}
  EQUALITY MATCHING RULE    caseIgnoreMatch
  SUBSTRINGS MATCHING RULE  caseIgnoreSubstringsMatch
  LDAP-SYNTAX               directoryString.&id
  LDAP-NAME                 {"zimbraAccountClientAttr"}
  LDAP-DESC                 "Deprecated since: 5.0. deprecated in favor of the accountInfo flag. Orig desc: additional account attrs that get returned to a client"
  ID                        id-at-zimbraAccountClientAttr }

-- LDAP syntax length {256} rendered as DirectoryString{256}.
zimbraAccountExtraObjectClass ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraAccountExtraObjectClass"}
  LDAP-DESC                 "Object classes to add when creating a zimbra account object. Useful if you want to add sambaSamAccount etc to zimbra accounts."
  ID                        id-at-zimbraAccountExtraObjectClass }

-- LDAP syntax length {32} rendered as DirectoryString{32}.
zimbraAccountStatus ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraAccountStatus"}
  LDAP-DESC                 "account status. active - active lockout - no login until lockout duration is over, mail delivery OK. locked - no login, mail delivery OK. maintenance - no login, no delivery(lmtp server returns 4.x.x Persistent Transient Failure). pending - no login, no delivery(lmtp server returns 5.x.x Permanent Failure), Account behavior is like closed, except that when the status is being set to pending, account addresses are not removed from distribution lists. The use case is for hosted. New account creation based on invites that are not completed until user accepts TOS on account creation confirmation page. closed - no login, no delivery(lmtp server returns 5.x.x Permanent Failure), all addresses (account main email and all aliases) of the account are removed from all distribution lists."
  ID                        id-at-zimbraAccountStatus }

-- LDAP syntax length {32} rendered as DirectoryString{32}.
zimbraAdminAccessControlMech ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraAdminAccessControlMech"}
  LDAP-DESC                 "access control mechanism for admin access acl: ACL based access control (a.k.a. delegated admin). global: allows only global admins."
  ID                        id-at-zimbraAdminAccessControlMech }

zimbraAdminAuthTokenLifetime ATTRIBUTE ::= {
  WITH SYNTAX               IA5String(SIZE (1..32))
  EQUALITY MATCHING RULE    caseIgnoreIA5Match
  SINGLE VALUE              TRUE
  LDAP-SYNTAX               ia5String.&id
  LDAP-NAME                 {"zimbraAdminAuthTokenLifetime"}
  LDAP-DESC                 "lifetime of newly created admin auth tokens. Must be in valid duration format: {digits}{time-unit}. digits: 0-9, time-unit: [hmsd]|ms. h - hours, m - minutes, s - seconds, d - days, ms - milliseconds. If time unit is not specified, the default is s(seconds)."
  ID                        id-at-zimbraAdminAuthTokenLifetime }

-- LDAP syntax length {128} rendered as DirectoryString{128}.
zimbraAdminBindAddress ATTRIBUTE ::= {
  WITH SYNTAX               DirectoryString{128}
  EQUALITY MATCHING RULE    caseIgnoreMatch
  SUBSTRINGS MATCHING RULE  caseIgnoreSubstringsMatch
  SINGLE VALUE              TRUE
  LDAP-SYNTAX               directoryString.&id
  LDAP-NAME                 {"zimbraAdminBindAddress"}
  LDAP-DESC                 "interface address on which Admin HTTPS server should listen; if empty, binds to all interfaces"
  ID                        id-at-zimbraAdminBindAddress }

zimbraAdminConsoleCatchAllAddressEnabled ATTRIBUTE ::= {
  WITH SYNTAX               BOOLEAN
  EQUALITY MATCHING RULE    booleanMatch
  SINGLE VALUE              TRUE
  LDAP-SYNTAX               boolean.&id
  LDAP-NAME                 {"zimbraAdminConsoleCatchAllAddressEnabled"}
  LDAP-DESC                 "whether to show catchall addresses in admin console"
  ID                        id-at-zimbraAdminConsoleCatchAllAddressEnabled }

zimbraAdminConsoleDNSCheckEnabled ATTRIBUTE ::= {
  WITH SYNTAX               BOOLEAN
  EQUALITY MATCHING RULE    booleanMatch
  SINGLE VALUE              TRUE
  LDAP-SYNTAX               boolean.&id
  LDAP-NAME                 {"zimbraAdminConsoleDNSCheckEnabled"}
  LDAP-DESC                 "enable MX check feature for domain"
  ID                        id-at-zimbraAdminConsoleDNSCheckEnabled }

zimbraAdminConsoleLDAPAuthEnabled ATTRIBUTE ::= {
  WITH SYNTAX               BOOLEAN
  EQUALITY MATCHING RULE    booleanMatch
  SINGLE VALUE              TRUE
  LDAP-SYNTAX               boolean.&id
  LDAP-NAME                 {"zimbraAdminConsoleLDAPAuthEnabled"}
  LDAP-DESC                 "whether configuring external LDAP auth is enabled in admin console"
  ID                        id-at-zimbraAdminConsoleLDAPAuthEnabled }

zimbraAdminConsoleLoginMessage ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraAdminConsoleLoginMessage"}
  LDAP-DESC                 "admin console login message"
  ID                        id-at-zimbraAdminConsoleLoginMessage }

-- LDAP syntax length {256} rendered as DirectoryString{256}.
zimbraAdminConsoleLoginURL ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraAdminConsoleLoginURL"}
  LDAP-DESC                 "login URL for admin console to send the user to upon explicit logging in"
  ID                        id-at-zimbraAdminConsoleLoginURL }

-- LDAP syntax length {256} rendered as DirectoryString{256}.
zimbraAdminConsoleLogoutURL ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraAdminConsoleLogoutURL"}
  LDAP-DESC                 "logout URL for admin console to send the user to upon explicit logging out"
  ID                        id-at-zimbraAdminConsoleLogoutURL }

zimbraAdminConsoleSkinEnabled ATTRIBUTE ::= {
  WITH SYNTAX               BOOLEAN
  EQUALITY MATCHING RULE    booleanMatch
  SINGLE VALUE              TRUE
  LDAP-SYNTAX               boolean.&id
  LDAP-NAME                 {"zimbraAdminConsoleSkinEnabled"}
  LDAP-DESC                 "whether to allow skin management in admin console"
  ID                        id-at-zimbraAdminConsoleSkinEnabled }

zimbraAdminConsoleUIComponents ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraAdminConsoleUIComponents"}
  LDAP-DESC                 "UI components available for the authed admin in admin console"
  ID                        id-at-zimbraAdminConsoleUIComponents }

zimbraAdminExtDisableUIUndeploy ATTRIBUTE ::= {
  WITH SYNTAX               BOOLEAN
  EQUALITY MATCHING RULE    booleanMatch
  SINGLE VALUE              TRUE
  LDAP-SYNTAX               boolean.&id
  LDAP-NAME                 {"zimbraAdminExtDisableUIUndeploy"}
  LDAP-DESC                 "Zimlet Util will set this attribute based on the value in zimlet definition XML file"
  ID                        id-at-zimbraAdminExtDisableUIUndeploy }

zimbraAdminImapImportNumThreads ATTRIBUTE ::= {
  WITH SYNTAX               INTEGER
  EQUALITY MATCHING RULE    integerMatch
  SINGLE VALUE              TRUE
  LDAP-SYNTAX               integer.&id
  LDAP-NAME                 {"zimbraAdminImapImportNumThreads"}
  LDAP-DESC                 "number of admin initiated imap import handler threads"
  ID                        id-at-zimbraAdminImapImportNumThreads }

zimbraAdminLocalBind ATTRIBUTE ::= {
  WITH SYNTAX               BOOLEAN
  EQUALITY MATCHING RULE    booleanMatch
  SINGLE VALUE              TRUE
  LDAP-SYNTAX               boolean.&id
  LDAP-NAME                 {"zimbraAdminLocalBind"}
  LDAP-DESC                 "Specifies whether the admin server should bound to localhost or not. This is an immutable property and is generated based on zimbraAdminBindAddress."
  ID                        id-at-zimbraAdminLocalBind }

zimbraAdminPort ATTRIBUTE ::= {
  WITH SYNTAX               INTEGER
  EQUALITY MATCHING RULE    integerMatch
  SINGLE VALUE              TRUE
  LDAP-SYNTAX               integer.&id
  LDAP-NAME                 {"zimbraAdminPort"}
  LDAP-DESC                 "SSL port for admin UI"
  ID                        id-at-zimbraAdminPort }

zimbraAdminProxyPort ATTRIBUTE ::= {
  WITH SYNTAX               INTEGER
  EQUALITY MATCHING RULE    integerMatch
  SINGLE VALUE              TRUE
  LDAP-SYNTAX               integer.&id
  LDAP-NAME                 {"zimbraAdminProxyPort"}
  LDAP-DESC                 "SSL proxy port for admin console UI"
  ID                        id-at-zimbraAdminProxyPort }

-- LDAP syntax length {512} rendered as DirectoryString{512}.
zimbraAdminSavedSearches ATTRIBUTE ::= {
  WITH SYNTAX               DirectoryString{512}
  EQUALITY MATCHING RULE    caseIgnoreMatch
  SUBSTRINGS MATCHING RULE  caseIgnoreSubstringsMatch
  LDAP-SYNTAX               directoryString.&id
  LDAP-NAME                 {"zimbraAdminSavedSearches"}
  LDAP-DESC                 "admin saved searches"
  ID                        id-at-zimbraAdminSavedSearches }

-- LDAP syntax length {1024} rendered as DirectoryString{1024}.
zimbraAdminURL ATTRIBUTE ::= {
  WITH SYNTAX               DirectoryString{1024}
  EQUALITY MATCHING RULE    caseIgnoreMatch
  SUBSTRINGS MATCHING RULE  caseIgnoreSubstringsMatch
  SINGLE VALUE              TRUE
  LDAP-SYNTAX               directoryString.&id
  LDAP-NAME                 {"zimbraAdminURL"}
  LDAP-DESC                 "URL prefix for where the zimbraAdmin app resides on this server"
  ID                        id-at-zimbraAdminURL }

zimbraAggregateQuotaLastUsage ATTRIBUTE ::= {
  WITH SYNTAX               INTEGER
  EQUALITY MATCHING RULE    integerMatch
  SINGLE VALUE              TRUE
  LDAP-SYNTAX               integer.&id
  LDAP-NAME                 {"zimbraAggregateQuotaLastUsage"}
  LDAP-DESC                 "last calculated aggregate quota usage for the domain in bytes"
  ID                        id-at-zimbraAggregateQuotaLastUsage }

-- LDAP syntax length {256} rendered as DirectoryString{256}.
zimbraAliasTargetId ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraAliasTargetId"}
  LDAP-DESC                 "zimbraId of alias target"
  ID                        id-at-zimbraAliasTargetId }

zimbraAllowAnyFromAddress ATTRIBUTE ::= {
  WITH SYNTAX               BOOLEAN
  EQUALITY MATCHING RULE    booleanMatch
  SINGLE VALUE              TRUE
  LDAP-SYNTAX               boolean.&id
  LDAP-NAME                 {"zimbraAllowAnyFromAddress"}
  LDAP-DESC                 "Whether this account can use any from address. Not changeable by domain admin to allow arbitrary addresses"
  ID                        id-at-zimbraAllowAnyFromAddress }

zimbraAllowFromAddress ATTRIBUTE ::= {
  WITH SYNTAX               IA5String(SIZE (1..256))
  EQUALITY MATCHING RULE    caseIgnoreIA5Match
  SUBSTRINGS MATCHING RULE  caseIgnoreSubstringsMatch
  LDAP-SYNTAX               ia5String.&id
  LDAP-NAME                 {"zimbraAllowFromAddress"}
  LDAP-DESC                 "Addresses that this account can as from address if arbitrary-addresses-allowed setting is not set"
  ID                        id-at-zimbraAllowFromAddress }

zimbraAllowNonLDHCharsInDomain ATTRIBUTE ::= {
  WITH SYNTAX               BOOLEAN
  EQUALITY MATCHING RULE    booleanMatch
  SINGLE VALUE              TRUE
  LDAP-SYNTAX               boolean.&id
  LDAP-NAME                 {"zimbraAllowNonLDHCharsInDomain"}
  LDAP-DESC                 "whether creating domains, and renaming domains to a name, containing non-LDH (letter, digit, hyphen) characters is allowed"
  ID                        id-at-zimbraAllowNonLDHCharsInDomain }

zimbraAlwaysOnClusterId ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraAlwaysOnClusterId"}
  LDAP-DESC                 "AlwaysOn cluster-id to which this server belongs to. If empty, it's not part of AlwaysOn and is a stand-alone server."
  ID                        id-at-zimbraAlwaysOnClusterId }

zimbraAmavisDSPAMEnabled ATTRIBUTE ::= {
  WITH SYNTAX               BOOLEAN
  EQUALITY MATCHING RULE    booleanMatch
  SINGLE VALUE              TRUE
  LDAP-SYNTAX               boolean.&id
  LDAP-NAME                 {"zimbraAmavisDSPAMEnabled"}
  LDAP-DESC                 "Whether or not Amavis should use DSPAM as an additional score factor for SPAM. Defaults to FALSE"
  ID                        id-at-zimbraAmavisDSPAMEnabled }

zimbraAmavisDomainDisclaimerHTML ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraAmavisDomainDisclaimerHTML"}
  LDAP-DESC                 "domain mandatory mail html signature"
  ID                        id-at-zimbraAmavisDomainDisclaimerHTML }

zimbraAmavisDomainDisclaimerText ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraAmavisDomainDisclaimerText"}
  LDAP-DESC                 "domain mandatory mail plain text signature"
  ID                        id-at-zimbraAmavisDomainDisclaimerText }

zimbraAmavisEnableDKIMVerification ATTRIBUTE ::= {
  WITH SYNTAX               BOOLEAN
  EQUALITY MATCHING RULE    booleanMatch
  SINGLE VALUE              TRUE
  LDAP-SYNTAX               boolean.&id
  LDAP-NAME                 {"zimbraAmavisEnableDKIMVerification"}
  LDAP-DESC                 "Whether or not Amavis should verify DKIM keys. Defaults to TRUE"
  ID                        id-at-zimbraAmavisEnableDKIMVerification }

-- LDAP syntax length {32} rendered as DirectoryString{32}.
zimbraAmavisFinalSpamDestiny ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraAmavisFinalSpamDestiny"}
  LDAP-DESC                 "Amavis final destination for Spam. Default is to discard it"
  ID                        id-at-zimbraAmavisFinalSpamDestiny }

zimbraAmavisLogLevel ATTRIBUTE ::= {
  WITH SYNTAX               INTEGER
  EQUALITY MATCHING RULE    integerMatch
  SINGLE VALUE              TRUE
  LDAP-SYNTAX               integer.&id
  LDAP-NAME                 {"zimbraAmavisLogLevel"}
  LDAP-DESC                 "Loglevel for Amavis. Defaults to 1. Valid range is 0-5"
  ID                        id-at-zimbraAmavisLogLevel }

zimbraAmavisMaxServers ATTRIBUTE ::= {
  WITH SYNTAX               INTEGER
  EQUALITY MATCHING RULE    integerMatch
  SINGLE VALUE              TRUE
  LDAP-SYNTAX               integer.&id
  LDAP-NAME                 {"zimbraAmavisMaxServers"}
  LDAP-DESC                 "Maximum number of Amavis servers to run. Default is 10"
  ID                        id-at-zimbraAmavisMaxServers }

zimbraAmavisOriginatingBypassSA ATTRIBUTE ::= {
  WITH SYNTAX               BOOLEAN
  EQUALITY MATCHING RULE    booleanMatch
  SINGLE VALUE              TRUE
  LDAP-SYNTAX               boolean.&id
  LDAP-NAME                 {"zimbraAmavisOriginatingBypassSA"}
  LDAP-DESC                 "Whether or not Amavis should Bypass SpamAsassin for originating email. Defaults to FALSE"
  ID                        id-at-zimbraAmavisOriginatingBypassSA }

zimbraAmavisOutboundDisclaimersOnly ATTRIBUTE ::= {
  WITH SYNTAX               BOOLEAN
  EQUALITY MATCHING RULE    booleanMatch
  SINGLE VALUE              TRUE
  LDAP-SYNTAX               boolean.&id
  LDAP-NAME                 {"zimbraAmavisOutboundDisclaimersOnly"}
  LDAP-DESC                 "Whether or not Amavis disclaimers should only be attached to outbound emails. Defaults to FALSE (Always attach a disclaimer)"
  ID                        id-at-zimbraAmavisOutboundDisclaimersOnly }

zimbraAmavisQuarantineAccount ATTRIBUTE ::= {
  WITH SYNTAX               IA5String(SIZE (1..256))
  EQUALITY MATCHING RULE    caseIgnoreIA5Match
  SUBSTRINGS MATCHING RULE  caseIgnoreSubstringsMatch
  SINGLE VALUE              TRUE
  LDAP-SYNTAX               ia5String.&id
  LDAP-NAME                 {"zimbraAmavisQuarantineAccount"}
  LDAP-DESC                 "When a virus is detected quarantine message to this account"
  ID                        id-at-zimbraAmavisQuarantineAccount }

zimbraAmavisSALogLevel ATTRIBUTE ::= {
  WITH SYNTAX               INTEGER
  EQUALITY MATCHING RULE    integerMatch
  SINGLE VALUE              TRUE
  LDAP-SYNTAX               integer.&id
  LDAP-NAME                 {"zimbraAmavisSALogLevel"}
  LDAP-DESC                 "Loglevel for SpamAssassin when called via Amavis. Defaults to 0 (info). Can be 0 or 1 (info, all)"
  ID                        id-at-zimbraAmavisSALogLevel }

zimbraAntispamExtractionBatchDelay ATTRIBUTE ::= {
  WITH SYNTAX               INTEGER
  EQUALITY MATCHING RULE    integerMatch
  SINGLE VALUE              TRUE
  LDAP-SYNTAX               integer.&id
  LDAP-NAME                 {"zimbraAntispamExtractionBatchDelay"}
  LDAP-DESC                 "delay between each batch for zmspamextract"
  ID                        id-at-zimbraAntispamExtractionBatchDelay }

zimbraAntispamExtractionBatchSize ATTRIBUTE ::= {
  WITH SYNTAX               INTEGER
  EQUALITY MATCHING RULE    integerMatch
  SINGLE VALUE              TRUE
  LDAP-SYNTAX               integer.&id
  LDAP-NAME                 {"zimbraAntispamExtractionBatchSize"}
  LDAP-DESC                 "batch size for zmspamextract"
  ID                        id-at-zimbraAntispamExtractionBatchSize }

zimbraArchiveAccount ATTRIBUTE ::= {
  WITH SYNTAX               IA5String(SIZE (1..256))
  EQUALITY MATCHING RULE    caseIgnoreIA5Match
  SUBSTRINGS MATCHING RULE  caseIgnoreSubstringsMatch
  LDAP-SYNTAX               ia5String.&id
  LDAP-NAME                 {"zimbraArchiveAccount"}
  LDAP-DESC                 "Mailboxes in which the current account in archived. Multi-value attr with eg values { user-2006@example.com.archive, user-2007@example.com.archive } that tells us that user@example.com has been archived into those two mailboxes."
  ID                        id-at-zimbraArchiveAccount }

-- LDAP syntax length {256} rendered as DirectoryString{256}.
zimbraArchiveAccountDateTemplate ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraArchiveAccountDateTemplate"}
  LDAP-DESC                 "An account or CoS setting that works with the name template that allows you to dictate the date format used in the name template. This is a Java SimpleDateFormat specifier. The default is an LDAP generalized time format:"
  ID                        id-at-zimbraArchiveAccountDateTemplate }

-- LDAP syntax length {256} rendered as DirectoryString{256}.
zimbraArchiveAccountNameTemplate ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraArchiveAccountNameTemplate"}
  LDAP-DESC                 "An account or CoS setting - typically only in CoS - that tells the archiving system how to derive the archive mailbox name. ID, USER, DATE, and DOMAIN are expanded."
  ID                        id-at-zimbraArchiveAccountNameTemplate }

zimbraArchiveEnabled ATTRIBUTE ::= {
  WITH SYNTAX               BOOLEAN
  EQUALITY MATCHING RULE    booleanMatch
  SINGLE VALUE              TRUE
  LDAP-SYNTAX               boolean.&id
  LDAP-NAME                 {"zimbraArchiveEnabled"}
  LDAP-DESC                 "whether account archiving is enabled"
  ID                        id-at-zimbraArchiveEnabled }

zimbraArchiveMailFrom ATTRIBUTE ::= {
  WITH SYNTAX               IA5String(SIZE (1..256))
  EQUALITY MATCHING RULE    caseIgnoreIA5Match
  SUBSTRINGS MATCHING RULE  caseIgnoreSubstringsMatch
  SINGLE VALUE              TRUE
  LDAP-SYNTAX               ia5String.&id
  LDAP-NAME                 {"zimbraArchiveMailFrom"}
  LDAP-DESC                 "Address to which archive message bounces should be sent. Typically could be an admin account. This is global across all domains."
  ID                        id-at-zimbraArchiveMailFrom }

zimbraAttachmentsBlocked ATTRIBUTE ::= {
  WITH SYNTAX               BOOLEAN
  EQUALITY MATCHING RULE    booleanMatch
  SINGLE VALUE              TRUE
  LDAP-SYNTAX               boolean.&id
  LDAP-NAME                 {"zimbraAttachmentsBlocked"}
  LDAP-DESC                 "block all attachment downloading"
  ID                        id-at-zimbraAttachmentsBlocked }

zimbraAttachmentsIndexedTextLimit ATTRIBUTE ::= {
  WITH SYNTAX               INTEGER
  EQUALITY MATCHING RULE    integerMatch
  SINGLE VALUE              TRUE
  LDAP-SYNTAX               integer.&id
  LDAP-NAME                 {"zimbraAttachmentsIndexedTextLimit"}
  LDAP-DESC                 "Maximum number of characters that will be indexed for a given MIME part."
  ID                        id-at-zimbraAttachmentsIndexedTextLimit }

zimbraAttachmentsIndexingEnabled ATTRIBUTE ::= {
  WITH SYNTAX               BOOLEAN
  EQUALITY MATCHING RULE    booleanMatch
  SINGLE VALUE              TRUE
  LDAP-SYNTAX               boolean.&id
  LDAP-NAME                 {"zimbraAttachmentsIndexingEnabled"}
  LDAP-DESC                 "whether or not to index attachments"
  ID                        id-at-zimbraAttachmentsIndexingEnabled }

-- LDAP syntax length {256} rendered as DirectoryString{256}.
zimbraAttachmentsScanClass ATTRIBUTE ::= {
  WITH SYNTAX               DirectoryString{256}
  EQUALITY MATCHING RULE    caseExactMatch
  SUBSTRINGS MATCHING RULE  caseExactSubstringsMatch
  SINGLE VALUE              TRUE
  LDAP-SYNTAX               directoryString.&id
  LDAP-NAME                 {"zimbraAttachmentsScanClass"}
  LDAP-DESC                 "Class to use to scan attachments during compose"
  ID                        id-at-zimbraAttachmentsScanClass }

zimbraAttachmentsScanEnabled ATTRIBUTE ::= {
  WITH SYNTAX               BOOLEAN
  EQUALITY MATCHING RULE    booleanMatch
  SINGLE VALUE              TRUE
  LDAP-SYNTAX               boolean.&id
  LDAP-NAME                 {"zimbraAttachmentsScanEnabled"}
  LDAP-DESC                 "Whether to scan attachments during compose"
  ID                        id-at-zimbraAttachmentsScanEnabled }

-- LDAP syntax length {256} rendered as DirectoryString{256}.
zimbraAttachmentsScanURL ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraAttachmentsScanURL"}
  LDAP-DESC                 "Data for class that scans attachments during compose"
  ID                        id-at-zimbraAttachmentsScanURL }

zimbraAttachmentsViewInHtmlOnly ATTRIBUTE ::= {
  WITH SYNTAX               BOOLEAN
  EQUALITY MATCHING RULE    booleanMatch
  SINGLE VALUE              TRUE
  LDAP-SYNTAX               boolean.&id
  LDAP-NAME                 {"zimbraAttachmentsViewInHtmlOnly"}
  LDAP-DESC                 "view all attachments in html only"
  ID                        id-at-zimbraAttachmentsViewInHtmlOnly }

zimbraAuthFallbackToLocal ATTRIBUTE ::= {
  WITH SYNTAX               BOOLEAN
  EQUALITY MATCHING RULE    booleanMatch
  SINGLE VALUE              TRUE
  LDAP-SYNTAX               boolean.&id
  LDAP-NAME                 {"zimbraAuthFallbackToLocal"}
  LDAP-DESC                 "fallback to local auth if external mech fails"
  ID                        id-at-zimbraAuthFallbackToLocal }

-- LDAP syntax length {1024} rendered as DirectoryString{1024}.
zimbraAuthKerberos5Realm ATTRIBUTE ::= {
  WITH SYNTAX               DirectoryString{1024}
  EQUALITY MATCHING RULE    caseIgnoreMatch
  SUBSTRINGS MATCHING RULE  caseIgnoreSubstringsMatch
  SINGLE VALUE              TRUE
  LDAP-SYNTAX               directoryString.&id
  LDAP-NAME                 {"zimbraAuthKerberos5Realm"}
  LDAP-DESC                 "kerberos5 realm for kerberos5 auth mech"
  ID                        id-at-zimbraAuthKerberos5Realm }

-- LDAP syntax length {256} rendered as DirectoryString{256}.
zimbraAuthLdapBindDn ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraAuthLdapBindDn"}
  LDAP-DESC                 "LDAP bind dn for ldap auth mech"
  ID                        id-at-zimbraAuthLdapBindDn }

-- LDAP syntax length {256} rendered as DirectoryString{256}.
zimbraAuthLdapExternalDn ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraAuthLdapExternalDn"}
  LDAP-DESC                 "explicit mapping to an external LDAP dn for a given account"
  ID                        id-at-zimbraAuthLdapExternalDn }

-- LDAP syntax length {256} rendered as DirectoryString{256}.
zimbraAuthLdapSearchBase ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraAuthLdapSearchBase"}
  LDAP-DESC                 "LDAP search base for ldap auth mech"
  ID                        id-at-zimbraAuthLdapSearchBase }

-- LDAP syntax length {256} rendered as DirectoryString{256}.
zimbraAuthLdapSearchBindDn ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraAuthLdapSearchBindDn"}
  LDAP-DESC                 "LDAP search bind dn for ldap auth mech"
  ID                        id-at-zimbraAuthLdapSearchBindDn }

-- LDAP syntax length {256} rendered as DirectoryString{256}.
zimbraAuthLdapSearchBindPassword ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraAuthLdapSearchBindPassword"}
  LDAP-DESC                 "LDAP search bind password for ldap auth mech"
  ID                        id-at-zimbraAuthLdapSearchBindPassword }

-- LDAP syntax length {256} rendered as DirectoryString{256}.
zimbraAuthLdapSearchFilter ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraAuthLdapSearchFilter"}
  LDAP-DESC                 "LDAP search filter for ldap auth mech"
  ID                        id-at-zimbraAuthLdapSearchFilter }

zimbraAuthLdapStartTlsEnabled ATTRIBUTE ::= {
  WITH SYNTAX               BOOLEAN
  EQUALITY MATCHING RULE    booleanMatch
  SINGLE VALUE              TRUE
  LDAP-SYNTAX               boolean.&id
  LDAP-NAME                 {"zimbraAuthLdapStartTlsEnabled"}
  LDAP-DESC                 "whether to use startTLS for external LDAP auth"
  ID                        id-at-zimbraAuthLdapStartTlsEnabled }

-- LDAP syntax length {256} rendered as DirectoryString{256}.
zimbraAuthLdapURL ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraAuthLdapURL"}
  LDAP-DESC                 "LDAP URL for ldap auth mech"
  ID                        id-at-zimbraAuthLdapURL }

-- LDAP syntax length {512} rendered as DirectoryString{512}.
zimbraAuthMech ATTRIBUTE ::= {
  WITH SYNTAX               DirectoryString{512}
  EQUALITY MATCHING RULE    caseIgnoreMatch
  SUBSTRINGS MATCHING RULE  caseIgnoreSubstringsMatch
  SINGLE VALUE              TRUE
  LDAP-SYNTAX               directoryString.&id
  LDAP-NAME                 {"zimbraAuthMech"}
  LDAP-DESC                 "mechanism to use for verifying password. Valid values are zimbra, ldap, ad, kerberos5, custom:{handler-name} [arg1 arg2 ...]"
  ID                        id-at-zimbraAuthMech }

-- LDAP syntax length {512} rendered as DirectoryString{512}.
zimbraAuthMechAdmin ATTRIBUTE ::= {
  WITH SYNTAX               DirectoryString{512}
  EQUALITY MATCHING RULE    caseIgnoreMatch
  SUBSTRINGS MATCHING RULE  caseIgnoreSubstringsMatch
  SINGLE VALUE              TRUE
  LDAP-SYNTAX               directoryString.&id
  LDAP-NAME                 {"zimbraAuthMechAdmin"}
  LDAP-DESC                 "mechanism to use for verifying password for admin. See zimbraAuthMech"
  ID                        id-at-zimbraAuthMechAdmin }

zimbraAuthTokenKey ATTRIBUTE ::= {
  WITH SYNTAX               OCTET STRING (SIZE (1..128))
  EQUALITY MATCHING RULE    octetStringMatch
  LDAP-SYNTAX               octetString.&id
  LDAP-NAME                 {"zimbraAuthTokenKey"}
  LDAP-DESC                 "auth token secret key"
  ID                        id-at-zimbraAuthTokenKey }

zimbraAuthTokenLifetime ATTRIBUTE ::= {
  WITH SYNTAX               IA5String(SIZE (1..32))
  EQUALITY MATCHING RULE    caseIgnoreIA5Match
  SINGLE VALUE              TRUE
  LDAP-SYNTAX               ia5String.&id
  LDAP-NAME                 {"zimbraAuthTokenLifetime"}
  LDAP-DESC                 "lifetime of newly created auth tokens. Must be in valid duration format: {digits}{time-unit}. digits: 0-9, time-unit: [hmsd]|ms. h - hours, m - minutes, s - seconds, d - days, ms - milliseconds. If time unit is not specified, the default is s(seconds)."
  ID                        id-at-zimbraAuthTokenLifetime }

zimbraAuthTokenNotificationInterval ATTRIBUTE ::= {
  WITH SYNTAX               INTEGER
  EQUALITY MATCHING RULE    integerMatch
  SINGLE VALUE              TRUE
  LDAP-SYNTAX               integer.&id
  LDAP-NAME                 {"zimbraAuthTokenNotificationInterval"}
  LDAP-DESC                 "This attribute is used to configure the interval with which servers will send a list of invalidated tokens to each other. When an account logs out of a server, the account's authtoken is added to a queue of invalidated tokens on the server. Each server will send it's queue of invalidated tokens to all other servers with frequency configurable by this attribute. See zimbraLogOutFromAllServers for more info on configuring authtoken invalidation on Accounts and Classes of Service. Set to higher value to reduce network chatter. Set to lower value to decrease the window during which a stolen cookie may be reused to access an account."
  ID                        id-at-zimbraAuthTokenNotificationInterval }

zimbraAuthTokenValidityValue ATTRIBUTE ::= {
  WITH SYNTAX               INTEGER
  EQUALITY MATCHING RULE    integerMatch
  SINGLE VALUE              TRUE
  LDAP-SYNTAX               integer.&id
  LDAP-NAME                 {"zimbraAuthTokenValidityValue"}
  LDAP-DESC                 "if set, this value gets stored in the auth token and compared on every request. Changing it will invalidate all outstanding auth tokens. It also gets changed when an account password is changed."
  ID                        id-at-zimbraAuthTokenValidityValue }

zimbraAuthTokenValidityValueEnabled ATTRIBUTE ::= {
  WITH SYNTAX               BOOLEAN
  EQUALITY MATCHING RULE    booleanMatch
  SINGLE VALUE              TRUE
  LDAP-SYNTAX               boolean.&id
  LDAP-NAME                 {"zimbraAuthTokenValidityValueEnabled"}
  LDAP-DESC                 "Whether auth token validity value checking should be performed during auth token validation. See description for zimbraAuthTokenValidityValue."
  ID                        id-at-zimbraAuthTokenValidityValueEnabled }

zimbraAuthTokens ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraAuthTokens"}
  LDAP-DESC                 "list of currently active auth tokens"
  ID                        id-at-zimbraAuthTokens }

-- LDAP syntax length {256} rendered as DirectoryString{256}.
zimbraAutoProvAccountNameMap ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraAutoProvAccountNameMap"}
  LDAP-DESC                 "EAGER mode: optional LAZY mode: optional MANUAL mode: optional Attribute name in the external directory that contains localpart of the account name. If not specified, localpart of the account name is the principal user used to authenticated to Zimbra."
  ID                        id-at-zimbraAutoProvAccountNameMap }

-- LDAP syntax length {256} rendered as DirectoryString{256}.
zimbraAutoProvAttrMap ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraAutoProvAttrMap"}
  LDAP-DESC                 "EAGER mode: optional LAZY mode: optional MANUAL mode: optional Attribute map for mapping attribute values from the external entry to Zimbra account attributes. Values are in the format of {external attribute}={zimbra attribute}. If not set, no attributes from the external directory will be populated in Zimbra directory. Invalid mapping configuration will cause the account creation to fail. Examples of bad mapping: - invalid external attribute name. - invalid Zimbra attribute name. - external attribute has multiple values but the zimbra attribute is single-valued. - syntax violation. e.g. Value on the external attribute is a String but the Zimbra attribute is declared an integer."
  ID                        id-at-zimbraAutoProvAttrMap }

-- LDAP syntax length {32} rendered as DirectoryString{32}.
zimbraAutoProvAuthMech ATTRIBUTE ::= {
  WITH SYNTAX               DirectoryString{32}
  EQUALITY MATCHING RULE    caseIgnoreMatch
  SUBSTRINGS MATCHING RULE  caseIgnoreSubstringsMatch
  LDAP-SYNTAX               directoryString.&id
  LDAP-NAME                 {"zimbraAutoProvAuthMech"}
  LDAP-DESC                 "EAGER mode: N/A LAZY mode: required MANUAL mode: N/A Auth mechanisms enabled for auto provision in LAZY mode. When a user authenticates via one of the external auth mechanisms enabled in this attribute, and when the user account does not yet exist in Zimbra directory, an account entry will be automatically created in Zimbra directory."
  ID                        id-at-zimbraAutoProvAuthMech }

zimbraAutoProvBatchSize ATTRIBUTE ::= {
  WITH SYNTAX               INTEGER
  EQUALITY MATCHING RULE    integerMatch
  SINGLE VALUE              TRUE
  LDAP-SYNTAX               integer.&id
  LDAP-NAME                 {"zimbraAutoProvBatchSize"}
  LDAP-DESC                 "EAGER mode: required LAZY mode: N/A MANUAL mode: N/A Max number of accounts to process in each interval for EAGER auto provision."
  ID                        id-at-zimbraAutoProvBatchSize }

zimbraAutoProvLastPolledTimestamp ATTRIBUTE ::= {
  WITH SYNTAX               GeneralizedTime
  EQUALITY MATCHING RULE    generalizedTimeMatch
  ORDERING MATCHING RULE    generalizedTimeOrderingMatch
  SINGLE VALUE              TRUE
  LDAP-SYNTAX               generalizedTime.&id
  LDAP-NAME                 {"zimbraAutoProvLastPolledTimestamp"}
  LDAP-DESC                 "EAGER mode: for Zimbra internal use only - do not change it. LAZY mode: N/A MANUAL mode: N/A Timestamp when the external domain is last polled for EAGER auto provision. The poll (LDAP search) for the next iteration will fetch external entries with create timestamp later than the timestamp recorded from the previous iteration."
  ID                        id-at-zimbraAutoProvLastPolledTimestamp }

-- LDAP syntax length {256} rendered as DirectoryString{256}.
zimbraAutoProvLdapAdminBindDn ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraAutoProvLdapAdminBindDn"}
  LDAP-DESC                 "EAGER mode: required LAZY mode: required (if using zimbraAutoProvLdapSearchFilter) MANUAL mode: required LDAP search bind DN for auto provision."
  ID                        id-at-zimbraAutoProvLdapAdminBindDn }

-- LDAP syntax length {256} rendered as DirectoryString{256}.
zimbraAutoProvLdapAdminBindPassword ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraAutoProvLdapAdminBindPassword"}
  LDAP-DESC                 "EAGER mode: required LAZY mode: required MANUAL mode: required LDAP search bind password for auto provision."
  ID                        id-at-zimbraAutoProvLdapAdminBindPassword }

-- LDAP syntax length {256} rendered as DirectoryString{256}.
zimbraAutoProvLdapBindDn ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraAutoProvLdapBindDn"}
  LDAP-DESC                 "EAGER mode: required LAZY mode: optional (if not using zimbraAutoProvLdapSearchFilter) MANUAL mode: optional (if not using zimbraAutoProvLdapSearchFilter) LDAP external DN template for account auto provisioning. For LAZY and MANUAL modes, either zimbraAutoProvLdapSearchFilter or zimbraAutoProvLdapBindDn has to be set. If both are set, zimbraAutoProvLdapSearchFilter will take precedence. Supported place holders: %n = username with @ (or without, if no @ was specified) %u = username with @ removed %d = domain as foo.com %D = domain as dc=foo,dc=com"
  ID                        id-at-zimbraAutoProvLdapBindDn }

-- LDAP syntax length {256} rendered as DirectoryString{256}.
zimbraAutoProvLdapSearchBase ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraAutoProvLdapSearchBase"}
  LDAP-DESC                 "EAGER mode: required LAZY mode: required (if using zimbraAutoProvLdapSearchFilter), MANUAL mode: required LDAP search base for auto provision, used in conjunction with zimbraAutoProvLdapSearchFilter. If not set, LDAP root DSE will be used."
  ID                        id-at-zimbraAutoProvLdapSearchBase }

-- LDAP syntax length {256} rendered as DirectoryString{256}.
zimbraAutoProvLdapSearchFilter ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraAutoProvLdapSearchFilter"}
  LDAP-DESC                 "EAGER mode: required LAZY mode: optional (if not using zimbraAutoProvLdapBindDn) MANUAL mode: optional (if not using zimbraAutoProvLdapBindDn) LDAP search filter template for account auto provisioning. For LAZY and MANUAL modes, either zimbraAutoProvLdapSearchFilter or zimbraAutoProvLdapBindDn has to be set. If both are set, zimbraAutoProvLdapSearchFilter will take precedence. Supported place holders: %n = username with @ (or without, if no @ was specified) %u = username with @ removed %d = domain as foo.com %D = domain as dc=foo,dc=com"
  ID                        id-at-zimbraAutoProvLdapSearchFilter }

zimbraAutoProvLdapStartTlsEnabled ATTRIBUTE ::= {
  WITH SYNTAX               BOOLEAN
  EQUALITY MATCHING RULE    booleanMatch
  SINGLE VALUE              TRUE
  LDAP-SYNTAX               boolean.&id
  LDAP-NAME                 {"zimbraAutoProvLdapStartTlsEnabled"}
  LDAP-DESC                 "EAGER mode: optional LAZY mode: optional MANUAL mode: optional Default is FALSE. Whether to use startTLS when accessing the external LDAP server for auto provision."
  ID                        id-at-zimbraAutoProvLdapStartTlsEnabled }

-- LDAP syntax length {256} rendered as DirectoryString{256}.
zimbraAutoProvLdapURL ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraAutoProvLdapURL"}
  LDAP-DESC                 "EAGER mode: required LAZY mode: required MANUAL mode: required LDAP URL of the external LDAP source for auto provision."
  ID                        id-at-zimbraAutoProvLdapURL }

-- LDAP syntax length {1024} rendered as DirectoryString{1024}.
zimbraAutoProvListenerClass ATTRIBUTE ::= {
  WITH SYNTAX               DirectoryString{1024}
  EQUALITY MATCHING RULE    caseIgnoreMatch
  SUBSTRINGS MATCHING RULE  caseIgnoreSubstringsMatch
  SINGLE VALUE              TRUE
  LDAP-SYNTAX               directoryString.&id
  LDAP-NAME                 {"zimbraAutoProvListenerClass"}
  LDAP-DESC                 "EAGER mode: optional LAZY mode: optional MANUAL mode: optional Class name of auto provision listener. The class must implement the com.zimbra.cs.account.Account.AutoProvisionListener interface. The singleton listener instance is invoked after each account is auto created in Zimbra. Listener can be plugged in as a server extension to handle tasks like updating the account auto provision status in the external LDAP directory. At each eager provision interval, ZCS does an LDAP search based on the value configured in zimbraAutoProvLdapSearchFilter. Returned entries from this search are candidates to be auto provisioned in this batch. The zimbraAutoProvLdapSearchFilter should include an assertion that will only hit entries in the external directory that have not yet been provisioned in ZCS, otherwise it's likely the same entries will be repeated pulled in to ZCS. After an account is auto provisioned in ZCS, com.zimbra.cs.account.Account.AutoProvisionListener.postCreate(Domain domain, Account acct, String externalDN) will be called by the auto provisioning framework. Customer can implement the AutoProvisionListener interface in a ZCS server extension and get their AutoProvisionListener.postCreate() get called. The implementation of customer's postCreate method can be, for example, setting an attribute in the external directory on the account just provisioned in ZCS. The attribute can be included as a condition in the zimbraAutoProvLdapSearchFilter, so the entry won't be returned again by the LDAP search in the next interval."
  ID                        id-at-zimbraAutoProvListenerClass }

zimbraAutoProvLock ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraAutoProvLock"}
  LDAP-DESC                 "EAGER mode: for Zimbra internal use only - do not change it. LAZY mode: N/A MANUAL mode: N/A For EAGER auto provision, a domain can be scheduled on multiple server. To avoid conflict, only one server can perform provisioning for a domain at one time. This attribute servers a lock for the test-and-set LDAP operation to synchronize EAGER auto provision attempts between servers."
  ID                        id-at-zimbraAutoProvLock }

-- LDAP syntax length {32} rendered as DirectoryString{32}.
zimbraAutoProvMode ATTRIBUTE ::= {
  WITH SYNTAX               DirectoryString{32}
  EQUALITY MATCHING RULE    caseIgnoreMatch
  SUBSTRINGS MATCHING RULE  caseIgnoreSubstringsMatch
  LDAP-SYNTAX               directoryString.&id
  LDAP-NAME                 {"zimbraAutoProvMode"}
  LDAP-DESC                 "Auto provision modes enabled. Multiple modes can be enabled on a domain. EAGER: A server maintenance thread automatically polls the configured external auto provision LDAP source at a configured interval for entries due to be auto provisioned in Zimbra, and then auto creates the accounts in Zimbra directory. LAZY: auto creates the Zimbra account when user first login via one of the external auth mechanisms enabled for auto provisioning. Auth mechanisms enabled for auto provisioning are configured in zimbraAutoProvAuthMech. MANUAL: admin to search from the configured external auto provision LDAP source and select an entry from the search result to create the corresponding Zimbra account for the external entry. In all cases, localpart of the Zimbra account is mapped from an attribute on the external entry based on zimbraAutoProvAccountNameMap. The Zimbra account is populated with attributes mapped from the external entry based on zimbraAutoProvAttrMap."
  ID                        id-at-zimbraAutoProvMode }

zimbraAutoProvNotificationBody ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraAutoProvNotificationBody"}
  LDAP-DESC                 "Template used to construct the subject of the notification message sent to the user when the user's account is auto provisioned. Supported variables: ,"
  ID                        id-at-zimbraAutoProvNotificationBody }

-- LDAP syntax length {256} rendered as DirectoryString{256}.
zimbraAutoProvNotificationFromAddress ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraAutoProvNotificationFromAddress"}
  LDAP-DESC                 "EAGER mode: optional LAZY mode: optional MANUAL mode: optional Email address to put in the From header for the notification email to the newly created account. If not set, no notification email will sent to the newly created account."
  ID                        id-at-zimbraAutoProvNotificationFromAddress }

zimbraAutoProvNotificationSubject ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraAutoProvNotificationSubject"}
  LDAP-DESC                 "Template used to construct the subject of the notification message sent to the user when the user's account is auto provisioned. Supported variables: ,"
  ID                        id-at-zimbraAutoProvNotificationSubject }

zimbraAutoProvPollingInterval ATTRIBUTE ::= {
  WITH SYNTAX               IA5String(SIZE (1..32))
  EQUALITY MATCHING RULE    caseIgnoreIA5Match
  SINGLE VALUE              TRUE
  LDAP-SYNTAX               ia5String.&id
  LDAP-NAME                 {"zimbraAutoProvPollingInterval"}
  LDAP-DESC                 "EAGER mode: required LAZY mode: N/A MANUAL mode: N/A Interval between successive polling and provisioning accounts in EAGER mode. The actual interval may take longer since it can be affected by two other factors: zimbraAutoProvBatchSize and number of domains configured in zimbraAutoProvScheduledDomains. At each interval, the auto provision thread iterates through all domains in zimbraAutoProvScheduledDomains and auto creates up to domain.zimbraAutoProvBatchSize accounts. If that process takes longer than zimbraAutoProvPollingInterval then the next iteration will start immediately instead of waiting for zimbraAutoProvPollingInterval amount of time. If set to 0 when server starts up, the auto provision thread will not start. If changed from a non-0 value to 0 while server is running, the auto provision thread will be shutdown. If changed from 0 to a non-0 value while server is running, the auto provision thread will be started. . Must be in valid duration format: {digits}{time-unit}. digits: 0-9, time-unit: [hmsd]|ms. h - hours, m - minutes, s - seconds, d - days, ms - milliseconds. If time unit is not specified, the default is s(seconds)."
  ID                        id-at-zimbraAutoProvPollingInterval }

zimbraAutoProvScheduledDomains ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraAutoProvScheduledDomains"}
  LDAP-DESC                 "EAGER mode: required LAZY mode: N/A MANUAL mode: N/A Domain scheduled for eager auto provision on this server. Scheduled domains must have EAGER mode enabled in zimbraAutoProvMode. Multiple domains can be scheduled on a server for EAGER auto provision. Also, a domain can be scheduled on multiple servers for EAGER auto provision."
  ID                        id-at-zimbraAutoProvScheduledDomains }

zimbraAutoSubmittedNullReturnPath ATTRIBUTE ::= {
  WITH SYNTAX               BOOLEAN
  EQUALITY MATCHING RULE    booleanMatch
  SINGLE VALUE              TRUE
  LDAP-SYNTAX               boolean.&id
  LDAP-NAME                 {"zimbraAutoSubmittedNullReturnPath"}
  LDAP-DESC                 "Use null return path for envelope MAIL FROM when sending out of office and new mail notifications. If false, use account address for envelope"
  ID                        id-at-zimbraAutoSubmittedNullReturnPath }

-- LDAP syntax length {80} rendered as DirectoryString{80}.
zimbraAvailableLocale ATTRIBUTE ::= {
  WITH SYNTAX               DirectoryString{80}
  EQUALITY MATCHING RULE    caseIgnoreMatch
  SUBSTRINGS MATCHING RULE  caseIgnoreSubstringsMatch
  LDAP-SYNTAX               directoryString.&id
  LDAP-NAME                 {"zimbraAvailableLocale"}
  LDAP-DESC                 "Locales available for this account"
  ID                        id-at-zimbraAvailableLocale }

-- LDAP syntax length {80} rendered as DirectoryString{80}.
zimbraAvailableSkin ATTRIBUTE ::= {
  WITH SYNTAX               DirectoryString{80}
  EQUALITY MATCHING RULE    caseIgnoreMatch
  SUBSTRINGS MATCHING RULE  caseIgnoreSubstringsMatch
  LDAP-SYNTAX               directoryString.&id
  LDAP-NAME                 {"zimbraAvailableSkin"}
  LDAP-DESC                 "Skins available for this account. Fallback order is: 1. the normal account/cos inheritance 2. if not set on account/cos, use the value on the domain of the account"
  ID                        id-at-zimbraAvailableSkin }

zimbraBackupAutoGroupedInterval ATTRIBUTE ::= {
  WITH SYNTAX               IA5String(SIZE (1..256))
  EQUALITY MATCHING RULE    caseIgnoreIA5Match
  SUBSTRINGS MATCHING RULE  caseIgnoreSubstringsMatch
  SINGLE VALUE              TRUE
  LDAP-SYNTAX               ia5String.&id
  LDAP-NAME                 {"zimbraBackupAutoGroupedInterval"}
  LDAP-DESC                 "length of each interval in auto-grouped backup"
  ID                        id-at-zimbraBackupAutoGroupedInterval }

zimbraBackupAutoGroupedNumGroups ATTRIBUTE ::= {
  WITH SYNTAX               INTEGER
  EQUALITY MATCHING RULE    integerMatch
  SINGLE VALUE              TRUE
  LDAP-SYNTAX               integer.&id
  LDAP-NAME                 {"zimbraBackupAutoGroupedNumGroups"}
  LDAP-DESC                 "number of groups to auto-group backups over"
  ID                        id-at-zimbraBackupAutoGroupedNumGroups }

zimbraBackupAutoGroupedThrottled ATTRIBUTE ::= {
  WITH SYNTAX               BOOLEAN
  EQUALITY MATCHING RULE    booleanMatch
  SINGLE VALUE              TRUE
  LDAP-SYNTAX               boolean.&id
  LDAP-NAME                 {"zimbraBackupAutoGroupedThrottled"}
  LDAP-DESC                 "if true, limit the number of mailboxes in auto-grouped backup to total mailboxes divided by auto-group days"
  ID                        id-at-zimbraBackupAutoGroupedThrottled }

zimbraBackupMinFreeSpace ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraBackupMinFreeSpace"}
  LDAP-DESC                 "Minimum percentage or TB/GB/MB/KB/bytes of free space on backup target to allow a full or auto-grouped backup to start; 0 = no minimum is enforced. Examples: 25%, 10GB"
  ID                        id-at-zimbraBackupMinFreeSpace }

-- LDAP syntax length {32} rendered as DirectoryString{32}.
zimbraBackupMode ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraBackupMode"}
  LDAP-DESC                 "backup mode"
  ID                        id-at-zimbraBackupMode }

zimbraBackupReportEmailRecipients ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraBackupReportEmailRecipients"}
  LDAP-DESC                 "Backup report email recipients"
  ID                        id-at-zimbraBackupReportEmailRecipients }

zimbraBackupReportEmailSender ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraBackupReportEmailSender"}
  LDAP-DESC                 "Backup report email From address"
  ID                        id-at-zimbraBackupReportEmailSender }

zimbraBackupReportEmailSubjectPrefix ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraBackupReportEmailSubjectPrefix"}
  LDAP-DESC                 "Backup report email subject prefix"
  ID                        id-at-zimbraBackupReportEmailSubjectPrefix }

zimbraBackupSkipBlobs ATTRIBUTE ::= {
  WITH SYNTAX               BOOLEAN
  EQUALITY MATCHING RULE    booleanMatch
  SINGLE VALUE              TRUE
  LDAP-SYNTAX               boolean.&id
  LDAP-NAME                 {"zimbraBackupSkipBlobs"}
  LDAP-DESC                 "if true, do not backup blobs (HSM or not) during a full backup"
  ID                        id-at-zimbraBackupSkipBlobs }

zimbraBackupSkipHsmBlobs ATTRIBUTE ::= {
  WITH SYNTAX               BOOLEAN
  EQUALITY MATCHING RULE    booleanMatch
  SINGLE VALUE              TRUE
  LDAP-SYNTAX               boolean.&id
  LDAP-NAME                 {"zimbraBackupSkipHsmBlobs"}
  LDAP-DESC                 "if true, do not backup blobs on secondary (HSM) volumes during a full backup"
  ID                        id-at-zimbraBackupSkipHsmBlobs }

zimbraBackupSkipSearchIndex ATTRIBUTE ::= {
  WITH SYNTAX               BOOLEAN
  EQUALITY MATCHING RULE    booleanMatch
  SINGLE VALUE              TRUE
  LDAP-SYNTAX               boolean.&id
  LDAP-NAME                 {"zimbraBackupSkipSearchIndex"}
  LDAP-DESC                 "if true, do not backup search index during a full backup"
  ID                        id-at-zimbraBackupSkipSearchIndex }

zimbraBackupTarget ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraBackupTarget"}
  LDAP-DESC                 "Default backup target path"
  ID                        id-at-zimbraBackupTarget }

-- LDAP syntax length {256} rendered as DirectoryString{256}.
zimbraBasicAuthRealm ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraBasicAuthRealm"}
  LDAP-DESC                 "Realm for the basic auth challenge (WWW-Authenticate) header"
  ID                        id-at-zimbraBasicAuthRealm }

zimbraBatchedIndexingSize ATTRIBUTE ::= {
  WITH SYNTAX               INTEGER
  EQUALITY MATCHING RULE    integerMatch
  SINGLE VALUE              TRUE
  LDAP-SYNTAX               integer.&id
  LDAP-NAME                 {"zimbraBatchedIndexingSize"}
  LDAP-DESC                 "Batch size to use when indexing data"
  ID                        id-at-zimbraBatchedIndexingSize }

zimbraCBPolicydAccessControlEnabled ATTRIBUTE ::= {
  WITH SYNTAX               BOOLEAN
  EQUALITY MATCHING RULE    booleanMatch
  SINGLE VALUE              TRUE
  LDAP-SYNTAX               boolean.&id
  LDAP-NAME                 {"zimbraCBPolicydAccessControlEnabled"}
  LDAP-DESC                 "Whether or not to enable CBPolicyd Access Control module. Defaults to FALSE"
  ID                        id-at-zimbraCBPolicydAccessControlEnabled }

zimbraCBPolicydAccountingEnabled ATTRIBUTE ::= {
  WITH SYNTAX               BOOLEAN
  EQUALITY MATCHING RULE    booleanMatch
  SINGLE VALUE              TRUE
  LDAP-SYNTAX               boolean.&id
  LDAP-NAME                 {"zimbraCBPolicydAccountingEnabled"}
  LDAP-DESC                 "Whether or not to enable CBPolicyd Accounting module. Defaults to FALSE"
  ID                        id-at-zimbraCBPolicydAccountingEnabled }

zimbraCBPolicydAmavisEnabled ATTRIBUTE ::= {
  WITH SYNTAX               BOOLEAN
  EQUALITY MATCHING RULE    booleanMatch
  SINGLE VALUE              TRUE
  LDAP-SYNTAX               boolean.&id
  LDAP-NAME                 {"zimbraCBPolicydAmavisEnabled"}
  LDAP-DESC                 "Whether or not to enable CBPolicyd Amavis module. Defaults to FALSE"
  ID                        id-at-zimbraCBPolicydAmavisEnabled }

zimbraCBPolicydBindPort ATTRIBUTE ::= {
  WITH SYNTAX               INTEGER
  EQUALITY MATCHING RULE    integerMatch
  SINGLE VALUE              TRUE
  LDAP-SYNTAX               integer.&id
  LDAP-NAME                 {"zimbraCBPolicydBindPort"}
  LDAP-DESC                 "Port for CBPolicyd to bind to. Defaults to 10031"
  ID                        id-at-zimbraCBPolicydBindPort }

-- LDAP syntax length {32} rendered as DirectoryString{32}.
zimbraCBPolicydBypassMode ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraCBPolicydBypassMode"}
  LDAP-DESC                 "Bypass fail mode. Default is tempfail"
  ID                        id-at-zimbraCBPolicydBypassMode }

zimbraCBPolicydBypassTimeout ATTRIBUTE ::= {
  WITH SYNTAX               INTEGER
  EQUALITY MATCHING RULE    integerMatch
  SINGLE VALUE              TRUE
  LDAP-SYNTAX               integer.&id
  LDAP-NAME                 {"zimbraCBPolicydBypassTimeout"}
  LDAP-DESC                 "Bypass timeout. Defaults to 30 seconds"
  ID                        id-at-zimbraCBPolicydBypassTimeout }

zimbraCBPolicydCheckHeloEnabled ATTRIBUTE ::= {
  WITH SYNTAX               BOOLEAN
  EQUALITY MATCHING RULE    booleanMatch
  SINGLE VALUE              TRUE
  LDAP-SYNTAX               boolean.&id
  LDAP-NAME                 {"zimbraCBPolicydCheckHeloEnabled"}
  LDAP-DESC                 "Whether or not to enable CBPolicyd Check Helo module. Defaults to FALSE"
  ID                        id-at-zimbraCBPolicydCheckHeloEnabled }

zimbraCBPolicydCheckSPFEnabled ATTRIBUTE ::= {
  WITH SYNTAX               BOOLEAN
  EQUALITY MATCHING RULE    booleanMatch
  SINGLE VALUE              TRUE
  LDAP-SYNTAX               boolean.&id
  LDAP-NAME                 {"zimbraCBPolicydCheckSPFEnabled"}
  LDAP-DESC                 "Whether or not to enable CBPolicyd CheckSPF module. Defaults to FALSE"
  ID                        id-at-zimbraCBPolicydCheckSPFEnabled }

zimbraCBPolicydGreylistingBlacklistMsg ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraCBPolicydGreylistingBlacklistMsg"}
  LDAP-DESC                 "Message to give when client is on blacklist. Default is Greylisting in effect, sending server blacklisted"
  ID                        id-at-zimbraCBPolicydGreylistingBlacklistMsg }

zimbraCBPolicydGreylistingDeferMsg ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraCBPolicydGreylistingDeferMsg"}
  LDAP-DESC                 "Message to give when deferring email. Default is Greylisting in effect, please come back later"
  ID                        id-at-zimbraCBPolicydGreylistingDeferMsg }

zimbraCBPolicydGreylistingEnabled ATTRIBUTE ::= {
  WITH SYNTAX               BOOLEAN
  EQUALITY MATCHING RULE    booleanMatch
  SINGLE VALUE              TRUE
  LDAP-SYNTAX               boolean.&id
  LDAP-NAME                 {"zimbraCBPolicydGreylistingEnabled"}
  LDAP-DESC                 "Whether or not to enable CBPolicyd Greylisting module. Defaults to FALSE"
  ID                        id-at-zimbraCBPolicydGreylistingEnabled }

zimbraCBPolicydGreylistingTrainingEnabled ATTRIBUTE ::= {
  WITH SYNTAX               BOOLEAN
  EQUALITY MATCHING RULE    booleanMatch
  SINGLE VALUE              TRUE
  LDAP-SYNTAX               boolean.&id
  LDAP-NAME                 {"zimbraCBPolicydGreylistingTrainingEnabled"}
  LDAP-DESC                 "Whether or not to put CBPolicyd Greylisting module in training only mode. Defaults to FALSE"
  ID                        id-at-zimbraCBPolicydGreylistingTrainingEnabled }

zimbraCBPolicydLogLevel ATTRIBUTE ::= {
  WITH SYNTAX               INTEGER
  EQUALITY MATCHING RULE    integerMatch
  SINGLE VALUE              TRUE
  LDAP-SYNTAX               integer.&id
  LDAP-NAME                 {"zimbraCBPolicydLogLevel"}
  LDAP-DESC                 "Logging level for CBPolicyd. Defaults to 3. Valid range is 0-4"
  ID                        id-at-zimbraCBPolicydLogLevel }

zimbraCBPolicydMaxRequests ATTRIBUTE ::= {
  WITH SYNTAX               INTEGER
  EQUALITY MATCHING RULE    integerMatch
  SINGLE VALUE              TRUE
  LDAP-SYNTAX               integer.&id
  LDAP-NAME                 {"zimbraCBPolicydMaxRequests"}
  LDAP-DESC                 "Maximum number of requests to process per server. Defaults to 1000"
  ID                        id-at-zimbraCBPolicydMaxRequests }

zimbraCBPolicydMaxServers ATTRIBUTE ::= {
  WITH SYNTAX               INTEGER
  EQUALITY MATCHING RULE    integerMatch
  SINGLE VALUE              TRUE
  LDAP-SYNTAX               integer.&id
  LDAP-NAME                 {"zimbraCBPolicydMaxServers"}
  LDAP-DESC                 "Maximum number of servers to allow. Defaults to 25"
  ID                        id-at-zimbraCBPolicydMaxServers }

zimbraCBPolicydMaxSpareServers ATTRIBUTE ::= {
  WITH SYNTAX               INTEGER
  EQUALITY MATCHING RULE    integerMatch
  SINGLE VALUE              TRUE
  LDAP-SYNTAX               integer.&id
  LDAP-NAME                 {"zimbraCBPolicydMaxSpareServers"}
  LDAP-DESC                 "Maximum number of spare servers to have on hand that are idle. Defaults to 12"
  ID                        id-at-zimbraCBPolicydMaxSpareServers }

zimbraCBPolicydMinServers ATTRIBUTE ::= {
  WITH SYNTAX               INTEGER
  EQUALITY MATCHING RULE    integerMatch
  SINGLE VALUE              TRUE
  LDAP-SYNTAX               integer.&id
  LDAP-NAME                 {"zimbraCBPolicydMinServers"}
  LDAP-DESC                 "Minimum number of CBPolicyd servers to have running. Defaults to 4"
  ID                        id-at-zimbraCBPolicydMinServers }

zimbraCBPolicydMinSpareServers ATTRIBUTE ::= {
  WITH SYNTAX               INTEGER
  EQUALITY MATCHING RULE    integerMatch
  SINGLE VALUE              TRUE
  LDAP-SYNTAX               integer.&id
  LDAP-NAME                 {"zimbraCBPolicydMinSpareServers"}
  LDAP-DESC                 "Minimum number of spare servers to have on hand. Defaults to 4"
  ID                        id-at-zimbraCBPolicydMinSpareServers }

zimbraCBPolicydQuotasEnabled ATTRIBUTE ::= {
  WITH SYNTAX               BOOLEAN
  EQUALITY MATCHING RULE    booleanMatch
  SINGLE VALUE              TRUE
  LDAP-SYNTAX               boolean.&id
  LDAP-NAME                 {"zimbraCBPolicydQuotasEnabled"}
  LDAP-DESC                 "Whether or not to enable CBPolicyd Quotas module. Defaults to TRUE"
  ID                        id-at-zimbraCBPolicydQuotasEnabled }

zimbraCBPolicydTimeoutBusy ATTRIBUTE ::= {
  WITH SYNTAX               INTEGER
  EQUALITY MATCHING RULE    integerMatch
  SINGLE VALUE              TRUE
  LDAP-SYNTAX               integer.&id
  LDAP-NAME                 {"zimbraCBPolicydTimeoutBusy"}
  LDAP-DESC                 "Timeout when talking to clients and servers are busy. Defaults to 120 seconds"
  ID                        id-at-zimbraCBPolicydTimeoutBusy }

zimbraCBPolicydTimeoutIdle ATTRIBUTE ::= {
  WITH SYNTAX               INTEGER
  EQUALITY MATCHING RULE    integerMatch
  SINGLE VALUE              TRUE
  LDAP-SYNTAX               integer.&id
  LDAP-NAME                 {"zimbraCBPolicydTimeoutIdle"}
  LDAP-DESC                 "Timeout when talking to clients and servers are idle. Defaults to 1020 seconds"
  ID                        id-at-zimbraCBPolicydTimeoutIdle }

-- LDAP syntax length {256} rendered as DirectoryString{256}.
zimbraCOSId ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraCOSId"}
  LDAP-DESC                 "COS zimbraID"
  ID                        id-at-zimbraCOSId }

-- LDAP syntax length {1024} rendered as DirectoryString{1024}.
zimbraCOSInheritedAttr ATTRIBUTE ::= {
  WITH SYNTAX               DirectoryString{1024}
  EQUALITY MATCHING RULE    caseIgnoreMatch
  SUBSTRINGS MATCHING RULE  caseIgnoreSubstringsMatch
  LDAP-SYNTAX               directoryString.&id
  LDAP-NAME                 {"zimbraCOSInheritedAttr"}
  LDAP-DESC                 "Deprecated since: 5.0. deprecated in favor of the accountInherited flag. Orig desc: zimbraCOS attrs that get inherited in a zimbraAccount"
  ID                        id-at-zimbraCOSInheritedAttr }

zimbraCalResAutoAcceptDecline ATTRIBUTE ::= {
  WITH SYNTAX               BOOLEAN
  EQUALITY MATCHING RULE    booleanMatch
  SINGLE VALUE              TRUE
  LDAP-SYNTAX               boolean.&id
  LDAP-NAME                 {"zimbraCalResAutoAcceptDecline"}
  LDAP-DESC                 "Whether this calendar resource accepts/declines meeting invites automatically; default TRUE"
  ID                        id-at-zimbraCalResAutoAcceptDecline }

zimbraCalResAutoDeclineIfBusy ATTRIBUTE ::= {
  WITH SYNTAX               BOOLEAN
  EQUALITY MATCHING RULE    booleanMatch
  SINGLE VALUE              TRUE
  LDAP-SYNTAX               boolean.&id
  LDAP-NAME                 {"zimbraCalResAutoDeclineIfBusy"}
  LDAP-DESC                 "Whether this calendar resource declines invite if already busy; default TRUE"
  ID                        id-at-zimbraCalResAutoDeclineIfBusy }

zimbraCalResAutoDeclineRecurring ATTRIBUTE ::= {
  WITH SYNTAX               BOOLEAN
  EQUALITY MATCHING RULE    booleanMatch
  SINGLE VALUE              TRUE
  LDAP-SYNTAX               boolean.&id
  LDAP-NAME                 {"zimbraCalResAutoDeclineRecurring"}
  LDAP-DESC                 "Whether this calendar resource declines invites to recurring appointments; default FALSE"
  ID                        id-at-zimbraCalResAutoDeclineRecurring }

-- LDAP syntax length {32} rendered as DirectoryString{32}.
zimbraCalResBuilding ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraCalResBuilding"}
  LDAP-DESC                 "building number or name"
  ID                        id-at-zimbraCalResBuilding }

zimbraCalResCapacity ATTRIBUTE ::= {
  WITH SYNTAX               INTEGER
  EQUALITY MATCHING RULE    integerMatch
  ORDERING MATCHING RULE    integerOrderingMatch
  SINGLE VALUE              TRUE
  LDAP-SYNTAX               integer.&id
  LDAP-NAME                 {"zimbraCalResCapacity"}
  LDAP-DESC                 "capacity"
  ID                        id-at-zimbraCalResCapacity }

zimbraCalResContactEmail ATTRIBUTE ::= {
  WITH SYNTAX               IA5String(SIZE (1..256))
  EQUALITY MATCHING RULE    caseIgnoreIA5Match
  SUBSTRINGS MATCHING RULE  caseIgnoreSubstringsMatch
  SINGLE VALUE              TRUE
  LDAP-SYNTAX               ia5String.&id
  LDAP-NAME                 {"zimbraCalResContactEmail"}
  LDAP-DESC                 "email of contact in charge of resource"
  ID                        id-at-zimbraCalResContactEmail }

-- LDAP syntax length {256} rendered as DirectoryString{256}.
zimbraCalResContactName ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraCalResContactName"}
  LDAP-DESC                 "name of contact in charge of resource"
  ID                        id-at-zimbraCalResContactName }

-- LDAP syntax length {32} kept as a comment only; it is an encoded-length hint, not a value constraint.
zimbraCalResContactPhone ATTRIBUTE ::= {
  WITH SYNTAX               TelephoneNumber
  EQUALITY MATCHING RULE    telephoneNumberMatch
  SUBSTRINGS MATCHING RULE  telephoneNumberSubstringsMatch
  SINGLE VALUE              TRUE
  LDAP-SYNTAX               telephoneNr.&id
  LDAP-NAME                 {"zimbraCalResContactPhone"}
  LDAP-DESC                 "phone number of contact in charge of resource"
  ID                        id-at-zimbraCalResContactPhone }

-- LDAP syntax length {32} rendered as DirectoryString{32}.
zimbraCalResFloor ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraCalResFloor"}
  LDAP-DESC                 "floor number or name"
  ID                        id-at-zimbraCalResFloor }

-- LDAP syntax length {256} rendered as DirectoryString{256}.
zimbraCalResLocationDisplayName ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraCalResLocationDisplayName"}
  LDAP-DESC                 "display name for resource location"
  ID                        id-at-zimbraCalResLocationDisplayName }

zimbraCalResMaxNumConflictsAllowed ATTRIBUTE ::= {
  WITH SYNTAX               INTEGER
  EQUALITY MATCHING RULE    integerMatch
  SINGLE VALUE              TRUE
  LDAP-SYNTAX               integer.&id
  LDAP-NAME                 {"zimbraCalResMaxNumConflictsAllowed"}
  LDAP-DESC                 "Maximum number of conflicting instances allowed before declining schedule request for a recurring appointments; default 0 (means decline on any conflict)"
  ID                        id-at-zimbraCalResMaxNumConflictsAllowed }

zimbraCalResMaxPercentConflictsAllowed ATTRIBUTE ::= {
  WITH SYNTAX               INTEGER
  EQUALITY MATCHING RULE    integerMatch
  SINGLE VALUE              TRUE
  LDAP-SYNTAX               integer.&id
  LDAP-NAME                 {"zimbraCalResMaxPercentConflictsAllowed"}
  LDAP-DESC                 "Maximum percent of conflicting instances allowed before declining schedule request for a recurring appointment; default 0 (means decline on any conflict)"
  ID                        id-at-zimbraCalResMaxPercentConflictsAllowed }

-- LDAP syntax length {32} rendered as DirectoryString{32}.
zimbraCalResRoom ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraCalResRoom"}
  LDAP-DESC                 "room number or name"
  ID                        id-at-zimbraCalResRoom }

-- LDAP syntax length {32} rendered as DirectoryString{32}.
zimbraCalResSite ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraCalResSite"}
  LDAP-DESC                 "site name"
  ID                        id-at-zimbraCalResSite }

-- LDAP syntax length {32} rendered as DirectoryString{32}.
zimbraCalResType ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraCalResType"}
  LDAP-DESC                 "calendar resource type - Location or Equipment"
  ID                        id-at-zimbraCalResType }

zimbraCalendarCalDavAlternateCalendarHomeSet ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraCalendarCalDavAlternateCalendarHomeSet"}
  LDAP-DESC                 "alternate location for calendar and task folders"
  ID                        id-at-zimbraCalendarCalDavAlternateCalendarHomeSet }

zimbraCalendarCalDavCalendarAutoScheduleEnabled ATTRIBUTE ::= {
  WITH SYNTAX               BOOLEAN
  EQUALITY MATCHING RULE    booleanMatch
  SINGLE VALUE              TRUE
  LDAP-SYNTAX               boolean.&id
  LDAP-NAME                 {"zimbraCalendarCalDavCalendarAutoScheduleEnabled"}
  LDAP-DESC                 "Enable support for the the ""calendar-auto-schedule"" feature of CalDAV - see RFC6638. If FALSE, the ""calendar-schedule"" feature of CalDAV is advertised instead - see draft-desruisseaux-caldav-sched-03. Note that the value of ""zimbraCalendarCalDavDisableScheduling"" takes precedence over this attribute."
  ID                        id-at-zimbraCalendarCalDavCalendarAutoScheduleEnabled }

zimbraCalendarCalDavClearTextPasswordEnabled ATTRIBUTE ::= {
  WITH SYNTAX               BOOLEAN
  EQUALITY MATCHING RULE    booleanMatch
  SINGLE VALUE              TRUE
  LDAP-SYNTAX               boolean.&id
  LDAP-NAME                 {"zimbraCalendarCalDavClearTextPasswordEnabled"}
  LDAP-DESC                 "Whether to allow password sent to non-secured port from CalDAV clients. If it set to TRUE the server will allow access from CalDAV client to zimbraMailPort. If it set to FALSE the server will return an error if a request is made from CalDAV client to zimbraMailPort."
  ID                        id-at-zimbraCalendarCalDavClearTextPasswordEnabled }

zimbraCalendarCalDavDefaultCalendarId ATTRIBUTE ::= {
  WITH SYNTAX               INTEGER
  EQUALITY MATCHING RULE    integerMatch
  SINGLE VALUE              TRUE
  LDAP-SYNTAX               integer.&id
  LDAP-NAME                 {"zimbraCalendarCalDavDefaultCalendarId"}
  LDAP-DESC                 "Id of calendar folder to advertise as the default calendar to CalDAV client."
  ID                        id-at-zimbraCalendarCalDavDefaultCalendarId }

zimbraCalendarCalDavDisableFreebusy ATTRIBUTE ::= {
  WITH SYNTAX               BOOLEAN
  EQUALITY MATCHING RULE    booleanMatch
  SINGLE VALUE              TRUE
  LDAP-SYNTAX               boolean.&id
  LDAP-NAME                 {"zimbraCalendarCalDavDisableFreebusy"}
  LDAP-DESC                 "set true to turn off handling free/busy lookup for CalDAV"
  ID                        id-at-zimbraCalendarCalDavDisableFreebusy }

zimbraCalendarCalDavDisableScheduling ATTRIBUTE ::= {
  WITH SYNTAX               BOOLEAN
  EQUALITY MATCHING RULE    booleanMatch
  SINGLE VALUE              TRUE
  LDAP-SYNTAX               boolean.&id
  LDAP-NAME                 {"zimbraCalendarCalDavDisableScheduling"}
  LDAP-DESC                 "set true to turn off handling scheduling message for CalDAV"
  ID                        id-at-zimbraCalendarCalDavDisableScheduling }

zimbraCalendarCalDavSharedFolderCacheDuration ATTRIBUTE ::= {
  WITH SYNTAX               IA5String(SIZE (1..32))
  EQUALITY MATCHING RULE    caseIgnoreIA5Match
  SINGLE VALUE              TRUE
  LDAP-SYNTAX               ia5String.&id
  LDAP-NAME                 {"zimbraCalendarCalDavSharedFolderCacheDuration"}
  LDAP-DESC                 "CalDAV shared folder cache duration. Must be in valid duration format: {digits}{time-unit}. digits: 0-9, time-unit: [hmsd]|ms. h - hours, m - minutes, s - seconds, d - days, ms - milliseconds. If time unit is not specified, the default is s(seconds)."
  ID                        id-at-zimbraCalendarCalDavSharedFolderCacheDuration }

zimbraCalendarCalDavSyncEnd ATTRIBUTE ::= {
  WITH SYNTAX               IA5String(SIZE (1..32))
  EQUALITY MATCHING RULE    caseIgnoreIA5Match
  SINGLE VALUE              TRUE
  LDAP-SYNTAX               ia5String.&id
  LDAP-NAME                 {"zimbraCalendarCalDavSyncEnd"}
  LDAP-DESC                 "see description of zimbraCalendarCalDavSyncStart. Must be in valid duration format: {digits}{time-unit}. digits: 0-9, time-unit: [hmsd]|ms. h - hours, m - minutes, s - seconds, d - days, ms - milliseconds. If time unit is not specified, the default is s(seconds)."
  ID                        id-at-zimbraCalendarCalDavSyncEnd }

zimbraCalendarCalDavSyncStart ATTRIBUTE ::= {
  WITH SYNTAX               IA5String(SIZE (1..32))
  EQUALITY MATCHING RULE    caseIgnoreIA5Match
  SINGLE VALUE              TRUE
  LDAP-SYNTAX               ia5String.&id
  LDAP-NAME                 {"zimbraCalendarCalDavSyncStart"}
  LDAP-DESC                 "zimbraCalendarCalDavSyncStart and zimbraCalendarCalDavSyncEnd limits the window of appointment data available via CalDAV. for example when zimbraCalendarCalDavSyncStart is set to 30 days, and zimbraCalendarCalDavSyncEnd is set to 1 years, then the appointments between (now - 30 days) and (now + 1 year) will be available via CalDAV. When they are unset all the appointments are available via CalDAV. . Must be in valid duration format: {digits}{time-unit}. digits: 0-9, time-unit: [hmsd]|ms. h - hours, m - minutes, s - seconds, d - days, ms - milliseconds. If time unit is not specified, the default is s(seconds)."
  ID                        id-at-zimbraCalendarCalDavSyncStart }

zimbraCalendarCalDavUseDistinctAppointmentAndToDoCollection ATTRIBUTE ::= {
  WITH SYNTAX               BOOLEAN
  EQUALITY MATCHING RULE    booleanMatch
  SINGLE VALUE              TRUE
  LDAP-SYNTAX               boolean.&id
  LDAP-NAME                 {"zimbraCalendarCalDavUseDistinctAppointmentAndToDoCollection"}
  LDAP-DESC                 "Deprecated since: 8.0.0. Deprecated per bug 69886.. Orig desc: When set to TRUE, Calendar folders and Todo folders in Zimbra will be advertised as Calendar only and Todo only via CalDAV. When set to FALSE, Calendar folders will be able to store both appointments and tasks, and Todo folders will not be advertised as CalDAV enabled."
  ID                        id-at-zimbraCalendarCalDavUseDistinctAppointmentAndToDoCollection }

-- LDAP syntax length {32} rendered as DirectoryString{32}.
zimbraCalendarCompatibilityMode ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraCalendarCompatibilityMode"}
  LDAP-DESC                 "compatibility mode for calendar server"
  ID                        id-at-zimbraCalendarCompatibilityMode }

zimbraCalendarKeepExceptionsOnSeriesTimeChange ATTRIBUTE ::= {
  WITH SYNTAX               BOOLEAN
  EQUALITY MATCHING RULE    booleanMatch
  SINGLE VALUE              TRUE
  LDAP-SYNTAX               boolean.&id
  LDAP-NAME                 {"zimbraCalendarKeepExceptionsOnSeriesTimeChange"}
  LDAP-DESC                 "whether to retain exception instances when the recurrence series is changed to new time; set to FALSE for Exchange compatibility"
  ID                        id-at-zimbraCalendarKeepExceptionsOnSeriesTimeChange }

zimbraCalendarLocationDisabledFields ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraCalendarLocationDisabledFields"}
  LDAP-DESC                 "list of disabled fields in calendar location web UI"
  ID                        id-at-zimbraCalendarLocationDisabledFields }

zimbraCalendarMaxRevisions ATTRIBUTE ::= {
  WITH SYNTAX               INTEGER
  EQUALITY MATCHING RULE    integerMatch
  SINGLE VALUE              TRUE
  LDAP-SYNTAX               integer.&id
  LDAP-NAME                 {"zimbraCalendarMaxRevisions"}
  LDAP-DESC                 "maximum number of revisions to keep for calendar items (appointments and tasks). 0 means unlimited."
  ID                        id-at-zimbraCalendarMaxRevisions }

zimbraCalendarRecurrenceDailyMaxDays ATTRIBUTE ::= {
  WITH SYNTAX               INTEGER
  EQUALITY MATCHING RULE    integerMatch
  SINGLE VALUE              TRUE
  LDAP-SYNTAX               integer.&id
  LDAP-NAME                 {"zimbraCalendarRecurrenceDailyMaxDays"}
  LDAP-DESC                 "Maximum number of days a DAILY recurrence rule can span; 0 means unlimited"
  ID                        id-at-zimbraCalendarRecurrenceDailyMaxDays }

zimbraCalendarRecurrenceMaxInstances ATTRIBUTE ::= {
  WITH SYNTAX               INTEGER
  EQUALITY MATCHING RULE    integerMatch
  SINGLE VALUE              TRUE
  LDAP-SYNTAX               integer.&id
  LDAP-NAME                 {"zimbraCalendarRecurrenceMaxInstances"}
  LDAP-DESC                 "Maximum number of instances expanded per recurrence rule; 0 means unlimited"
  ID                        id-at-zimbraCalendarRecurrenceMaxInstances }

zimbraCalendarRecurrenceMonthlyMaxMonths ATTRIBUTE ::= {
  WITH SYNTAX               INTEGER
  EQUALITY MATCHING RULE    integerMatch
  SINGLE VALUE              TRUE
  LDAP-SYNTAX               integer.&id
  LDAP-NAME                 {"zimbraCalendarRecurrenceMonthlyMaxMonths"}
  LDAP-DESC                 "Maximum number of months a MONTHLY recurrence rule can span; 0 means unlimited"
  ID                        id-at-zimbraCalendarRecurrenceMonthlyMaxMonths }

zimbraCalendarRecurrenceOtherFrequencyMaxYears ATTRIBUTE ::= {
  WITH SYNTAX               INTEGER
  EQUALITY MATCHING RULE    integerMatch
  SINGLE VALUE              TRUE
  LDAP-SYNTAX               integer.&id
  LDAP-NAME                 {"zimbraCalendarRecurrenceOtherFrequencyMaxYears"}
  LDAP-DESC                 "Maximum number of years a recurrence rule can span for frequencies other than DAILY/WEEKLY/MONTHLY/YEARLY; 0 means unlimited"
  ID                        id-at-zimbraCalendarRecurrenceOtherFrequencyMaxYears }

zimbraCalendarRecurrenceWeeklyMaxWeeks ATTRIBUTE ::= {
  WITH SYNTAX               INTEGER
  EQUALITY MATCHING RULE    integerMatch
  SINGLE VALUE              TRUE
  LDAP-SYNTAX               integer.&id
  LDAP-NAME                 {"zimbraCalendarRecurrenceWeeklyMaxWeeks"}
  LDAP-DESC                 "Maximum number of weeks a WEEKLY recurrence rule can span; 0 means unlimited"
  ID                        id-at-zimbraCalendarRecurrenceWeeklyMaxWeeks }

zimbraCalendarRecurrenceYearlyMaxYears ATTRIBUTE ::= {
  WITH SYNTAX               INTEGER
  EQUALITY MATCHING RULE    integerMatch
  SINGLE VALUE              TRUE
  LDAP-SYNTAX               integer.&id
  LDAP-NAME                 {"zimbraCalendarRecurrenceYearlyMaxYears"}
  LDAP-DESC                 "Maximum number of years a YEARLY recurrence rule can span; 0 means unlimited"
  ID                        id-at-zimbraCalendarRecurrenceYearlyMaxYears }

zimbraCalendarReminderDeviceEmail ATTRIBUTE ::= {
  WITH SYNTAX               IA5String(SIZE (1..256))
  EQUALITY MATCHING RULE    caseIgnoreIA5Match
  SUBSTRINGS MATCHING RULE  caseIgnoreSubstringsMatch
  SINGLE VALUE              TRUE
  LDAP-SYNTAX               ia5String.&id
  LDAP-NAME                 {"zimbraCalendarReminderDeviceEmail"}
  LDAP-DESC                 "email address identifying the default device for receiving reminders for appointments and tasks"
  ID                        id-at-zimbraCalendarReminderDeviceEmail }

zimbraCalendarResourceDoubleBookingAllowed ATTRIBUTE ::= {
  WITH SYNTAX               BOOLEAN
  EQUALITY MATCHING RULE    booleanMatch
  SINGLE VALUE              TRUE
  LDAP-SYNTAX               boolean.&id
  LDAP-NAME                 {"zimbraCalendarResourceDoubleBookingAllowed"}
  LDAP-DESC                 "whether calendar resources can be double booked"
  ID                        id-at-zimbraCalendarResourceDoubleBookingAllowed }

-- LDAP syntax length {256} rendered as DirectoryString{256}.
zimbraCalendarResourceExtraObjectClass ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraCalendarResourceExtraObjectClass"}
  LDAP-DESC                 "Object classes to add when creating a zimbra calendar resource object."
  ID                        id-at-zimbraCalendarResourceExtraObjectClass }

zimbraCalendarShowResourceTabs ATTRIBUTE ::= {
  WITH SYNTAX               BOOLEAN
  EQUALITY MATCHING RULE    booleanMatch
  SINGLE VALUE              TRUE
  LDAP-SYNTAX               boolean.&id
  LDAP-NAME                 {"zimbraCalendarShowResourceTabs"}
  LDAP-DESC                 "whether to show Find Locations and Find Resources tabs for editing appointments"
  ID                        id-at-zimbraCalendarShowResourceTabs }

zimbraCertAuthorityCertSelfSigned ATTRIBUTE ::= {
  WITH SYNTAX               IA5String(SIZE (1..2048))
  EQUALITY MATCHING RULE    caseIgnoreIA5Match
  SUBSTRINGS MATCHING RULE  caseIgnoreSubstringsMatch
  SINGLE VALUE              TRUE
  LDAP-SYNTAX               ia5String.&id
  LDAP-NAME                 {"zimbraCertAuthorityCertSelfSigned"}
  LDAP-DESC                 "When creating self-signed SSL certs during an install, we also create a local Certificate Authority (CA) to sign these SSL certs. This local CA-s own cert is then added to different applications ""trusted CA-s"" list/store. This attribute should not be used in a system with real certs issued by well known CAs."
  ID                        id-at-zimbraCertAuthorityCertSelfSigned }

zimbraCertAuthorityKeySelfSigned ATTRIBUTE ::= {
  WITH SYNTAX               IA5String(SIZE (1..2048))
  EQUALITY MATCHING RULE    caseIgnoreIA5Match
  SUBSTRINGS MATCHING RULE  caseIgnoreSubstringsMatch
  SINGLE VALUE              TRUE
  LDAP-SYNTAX               ia5String.&id
  LDAP-NAME                 {"zimbraCertAuthorityKeySelfSigned"}
  LDAP-DESC                 "Please see the documentation for the attribute zimbraCertAuthorityCertSelfSigned. In addition, please note that this attribute is provided at install for convenience during a test install without real certs issued by well known CAs. If you choose to create your own CA for your production uses, please note that it is a bad idea to store your CA-s private key in LDAP, as this data maybe read from zimbraGlobalConfig in the clear."
  ID                        id-at-zimbraCertAuthorityKeySelfSigned }

-- LDAP syntax length {256} rendered as DirectoryString{256}.
zimbraChangePasswordURL ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraChangePasswordURL"}
  LDAP-DESC                 "change password URL"
  ID                        id-at-zimbraChangePasswordURL }

-- LDAP syntax length {256} rendered as DirectoryString{256}.
zimbraChildAccount ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraChildAccount"}
  LDAP-DESC                 "Deprecated since: 8.5.0. family mailbox feature is deprecated. Orig desc: zimbraId of child accounts"
  ID                        id-at-zimbraChildAccount }

-- LDAP syntax length {256} rendered as DirectoryString{256}.
zimbraChildVisibleAccount ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraChildVisibleAccount"}
  LDAP-DESC                 "Deprecated since: 5.0.0. deprecated in favor of user-settable attribute zimbraPrefChildVisibleAccount . Orig desc: zimbraId of visible child accounts"
  ID                        id-at-zimbraChildVisibleAccount }

zimbraClamAVBindAddress ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraClamAVBindAddress"}
  LDAP-DESC                 "IP Address/hostname for ClamAV to bind to for attachment scanning. Default is localhost"
  ID                        id-at-zimbraClamAVBindAddress }

zimbraClamAVListenPort ATTRIBUTE ::= {
  WITH SYNTAX               INTEGER
  EQUALITY MATCHING RULE    integerMatch
  SINGLE VALUE              TRUE
  LDAP-SYNTAX               integer.&id
  LDAP-NAME                 {"zimbraClamAVListenPort"}
  LDAP-DESC                 "Port to bind to for attachment scanning. Default is 3310"
  ID                        id-at-zimbraClamAVListenPort }

zimbraClamAVMaxThreads ATTRIBUTE ::= {
  WITH SYNTAX               INTEGER
  EQUALITY MATCHING RULE    integerMatch
  SINGLE VALUE              TRUE
  LDAP-SYNTAX               integer.&id
  LDAP-NAME                 {"zimbraClamAVMaxThreads"}
  LDAP-DESC                 "Maximum number of ClamAV servers to run. Default is 10"
  ID                        id-at-zimbraClamAVMaxThreads }

-- LDAP syntax length {256} rendered as DirectoryString{256}.
zimbraClientTypeRegex ATTRIBUTE ::= {
  WITH SYNTAX               DirectoryString{256}
  EQUALITY MATCHING RULE    caseExactMatch
  SUBSTRINGS MATCHING RULE  caseExactSubstringsMatch
  LDAP-SYNTAX               directoryString.&id
  LDAP-NAME                 {"zimbraClientTypeRegex"}
  LDAP-DESC                 "Regex for identifying client types"
  ID                        id-at-zimbraClientTypeRegex }

-- LDAP syntax length {32} rendered as DirectoryString{32}.
zimbraClusterType ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraClusterType"}
  LDAP-DESC                 "Type of HA cluster software in use; ""none"" by default, ""RedHat"" for Red Hat cluster or ""Veritas"" for Veritas Cluster Server from Symantec"
  ID                        id-at-zimbraClusterType }

zimbraCommunityAPIClientID ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraCommunityAPIClientID"}
  LDAP-DESC                 "API Client ID for accessing with Zimbra Community API"
  ID                        id-at-zimbraCommunityAPIClientID }

zimbraCommunityAPIClientSecret ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraCommunityAPIClientSecret"}
  LDAP-DESC                 "API Client Secret for accessing with Zimbra Community API"
  ID                        id-at-zimbraCommunityAPIClientSecret }

zimbraCommunityBaseURL ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraCommunityBaseURL"}
  LDAP-DESC                 "Base URL where Zimbra Community is deployed. Do not include / symbol at the end"
  ID                        id-at-zimbraCommunityBaseURL }

zimbraCommunityHomeURL ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraCommunityHomeURL"}
  LDAP-DESC                 "URL to be loaded in Zimbra Community tab relative to zimbraCommunityBaseURL"
  ID                        id-at-zimbraCommunityHomeURL }

zimbraCommunityID ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraCommunityID"}
  LDAP-DESC                 "User's ID in Zimbra Community. When user IDs between Zimbra Collaboraiton and Zimbra Community are not synchronized use this attrribute to store the user's Zimbra Community ID. In order for this attribute to be used for SSO zimbraCommunityUsernameMapping has to be set to zimbraCommunityID."
  ID                        id-at-zimbraCommunityID }

zimbraCommunityUsernameMapping ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraCommunityUsernameMapping"}
  LDAP-DESC                 "Account attribute to be used as a username for Zimbra Community"
  ID                        id-at-zimbraCommunityUsernameMapping }

-- LDAP syntax length {64} rendered as DirectoryString{64}.
zimbraComponentAvailable ATTRIBUTE ::= {
  WITH SYNTAX               DirectoryString{64}
  EQUALITY MATCHING RULE    caseIgnoreMatch
  SUBSTRINGS MATCHING RULE  caseIgnoreSubstringsMatch
  LDAP-SYNTAX               directoryString.&id
  LDAP-NAME                 {"zimbraComponentAvailable"}
  LDAP-DESC                 "Names of additional components that have been installed"
  ID                        id-at-zimbraComponentAvailable }

zimbraConfiguredServerIDForBlobDirEnabled ATTRIBUTE ::= {
  WITH SYNTAX               BOOLEAN
  EQUALITY MATCHING RULE    booleanMatch
  SINGLE VALUE              TRUE
  LDAP-SYNTAX               boolean.&id
  LDAP-NAME                 {"zimbraConfiguredServerIDForBlobDirEnabled"}
  LDAP-DESC                 "Enabled using the configured server ID for blob dir"
  ID                        id-at-zimbraConfiguredServerIDForBlobDirEnabled }

zimbraConstraint ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraConstraint"}
  LDAP-DESC                 "attribute constraints TODO: fill all the constraints"
  ID                        id-at-zimbraConstraint }

-- LDAP syntax length {64} rendered as DirectoryString{64}.
zimbraContactAutoCompleteEmailFields ATTRIBUTE ::= {
  WITH SYNTAX               DirectoryString{64}
  EQUALITY MATCHING RULE    caseIgnoreMatch
  SUBSTRINGS MATCHING RULE  caseIgnoreSubstringsMatch
  SINGLE VALUE              TRUE
  LDAP-SYNTAX               directoryString.&id
  LDAP-NAME                 {"zimbraContactAutoCompleteEmailFields"}
  LDAP-DESC                 "Deprecated since: 6.0.7. deprecated in favor of zimbraContactEmailFields, for bug 45475. Orig desc: Comma separates list of attributes in contact object to search for email addresses when generating auto-complete contact list. The same set of fields are used for GAL contacts as well because LDAP attributes for GAL objects are mapped to Contact compatible attributes via zimbraGalLdapAttrMap."
  ID                        id-at-zimbraContactAutoCompleteEmailFields }

zimbraContactAutoCompleteMaxResults ATTRIBUTE ::= {
  WITH SYNTAX               INTEGER
  EQUALITY MATCHING RULE    integerMatch
  SINGLE VALUE              TRUE
  LDAP-SYNTAX               integer.&id
  LDAP-NAME                 {"zimbraContactAutoCompleteMaxResults"}
  LDAP-DESC                 "maximum number of contact entries to return from an auto complete"
  ID                        id-at-zimbraContactAutoCompleteMaxResults }

-- LDAP syntax length {4096} rendered as DirectoryString{4096}.
zimbraContactEmailFields ATTRIBUTE ::= {
  WITH SYNTAX               DirectoryString{4096}
  EQUALITY MATCHING RULE    caseIgnoreMatch
  SUBSTRINGS MATCHING RULE  caseIgnoreSubstringsMatch
  SINGLE VALUE              TRUE
  LDAP-SYNTAX               directoryString.&id
  LDAP-NAME                 {"zimbraContactEmailFields"}
  LDAP-DESC                 "Comma separates list of attributes in contact object to search for email addresses when generating auto-complete contact list. The same set of fields are used for GAL contacts as well because LDAP attributes for GAL objects are mapped to Contact compatible attributes via zimbraGalLdapAttrMap."
  ID                        id-at-zimbraContactEmailFields }

zimbraContactHiddenAttributes ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraContactHiddenAttributes"}
  LDAP-DESC                 "Comma separated list of Contact attributes that should be hidden from clients and export of contacts."
  ID                        id-at-zimbraContactHiddenAttributes }

zimbraContactMaxNumEntries ATTRIBUTE ::= {
  WITH SYNTAX               INTEGER
  EQUALITY MATCHING RULE    integerMatch
  SINGLE VALUE              TRUE
  LDAP-SYNTAX               integer.&id
  LDAP-NAME                 {"zimbraContactMaxNumEntries"}
  LDAP-DESC                 "Maximum number of contacts allowed in mailbox. 0 means no limit."
  ID                        id-at-zimbraContactMaxNumEntries }

zimbraContactRankingTableRefreshInterval ATTRIBUTE ::= {
  WITH SYNTAX               IA5String(SIZE (1..32))
  EQUALITY MATCHING RULE    caseIgnoreIA5Match
  SINGLE VALUE              TRUE
  LDAP-SYNTAX               ia5String.&id
  LDAP-NAME                 {"zimbraContactRankingTableRefreshInterval"}
  LDAP-DESC                 "Deprecated since: 6.0.6. Deprecated per bug 40081. Orig desc: How often do we refresh contact ranking table from address book and GAL to get friendly name for the email address. Use 0 to disable the refresh.. Must be in valid duration format: {digits}{time-unit}. digits: 0-9, time-unit: [hmsd]|ms. h - hours, m - minutes, s - seconds, d - days, ms - milliseconds. If time unit is not specified, the default is s(seconds)."
  ID                        id-at-zimbraContactRankingTableRefreshInterval }

zimbraContactRankingTableSize ATTRIBUTE ::= {
  WITH SYNTAX               INTEGER
  EQUALITY MATCHING RULE    integerMatch
  SINGLE VALUE              TRUE
  LDAP-SYNTAX               integer.&id
  LDAP-NAME                 {"zimbraContactRankingTableSize"}
  LDAP-DESC                 "Size of the contact ranking table. Ranking table is used to keep track of most heavily used contacts in outgoing email. Contacts in the ranking table are given the priority when generating the auto-complete contact list."
  ID                        id-at-zimbraContactRankingTableSize }

zimbraConvertdURL ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraConvertdURL"}
  LDAP-DESC                 "convertd URL"
  ID                        id-at-zimbraConvertdURL }

zimbraConverterHints ATTRIBUTE ::= {
  WITH SYNTAX               UnboundedDirectoryString
  EQUALITY MATCHING RULE    caseExactMatch
  SUBSTRINGS MATCHING RULE  caseExactSubstringsMatch
  LDAP-SYNTAX               directoryString.&id
  LDAP-NAME                 {"zimbraConverterHints"}
  LDAP-DESC                 "Allows converter hints to be supplied on the COS level. Can be used to enable or disable some converters"
  ID                        id-at-zimbraConverterHints }

-- LDAP syntax length {256} rendered as DirectoryString{256}.
zimbraCosExtraObjectClass ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraCosExtraObjectClass"}
  LDAP-DESC                 "Object classes to add when creating a zimbra cos object."
  ID                        id-at-zimbraCosExtraObjectClass }

zimbraCreateTimestamp ATTRIBUTE ::= {
  WITH SYNTAX               GeneralizedTime
  EQUALITY MATCHING RULE    generalizedTimeMatch
  ORDERING MATCHING RULE    generalizedTimeOrderingMatch
  SINGLE VALUE              TRUE
  LDAP-SYNTAX               generalizedTime.&id
  LDAP-NAME                 {"zimbraCreateTimestamp"}
  LDAP-DESC                 "time object was created"
  ID                        id-at-zimbraCreateTimestamp }

zimbraCsrfAllowedRefererHosts ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraCsrfAllowedRefererHosts"}
  LDAP-DESC                 "A list of hosts like www.abc.com, www.xyz.com. These are used while doing CSRF referer check."
  ID                        id-at-zimbraCsrfAllowedRefererHosts }

zimbraCsrfRefererCheckEnabled ATTRIBUTE ::= {
  WITH SYNTAX               BOOLEAN
  EQUALITY MATCHING RULE    booleanMatch
  SINGLE VALUE              TRUE
  LDAP-SYNTAX               boolean.&id
  LDAP-NAME                 {"zimbraCsrfRefererCheckEnabled"}
  LDAP-DESC                 "A flag to turn on or off CSRF referer related check. When set to FALSE no CSRF referer check happens. When set to true CSRF referer type check happens."
  ID                        id-at-zimbraCsrfRefererCheckEnabled }

zimbraCsrfTokenCheckEnabled ATTRIBUTE ::= {
  WITH SYNTAX               BOOLEAN
  EQUALITY MATCHING RULE    booleanMatch
  SINGLE VALUE              TRUE
  LDAP-SYNTAX               boolean.&id
  LDAP-NAME                 {"zimbraCsrfTokenCheckEnabled"}
  LDAP-DESC                 "A flag to turn on or off CSRF token related check. When set to FALSE no CSRF check happens. When set to true both CSRF referer and CSRF token change is effective."
  ID                        id-at-zimbraCsrfTokenCheckEnabled }

zimbraCsrfTokenData ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraCsrfTokenData"}
  LDAP-DESC                 "List of data associated with CSRF token for an account. The data format is CSRF token data:Auth token Key crumb:Auth Token Key expiration"
  ID                        id-at-zimbraCsrfTokenData }

zimbraCsrfTokenKey ATTRIBUTE ::= {
  WITH SYNTAX               OCTET STRING (SIZE (1..128))
  EQUALITY MATCHING RULE    octetStringMatch
  LDAP-SYNTAX               octetString.&id
  LDAP-NAME                 {"zimbraCsrfTokenKey"}
  LDAP-DESC                 "CSRF token secret key"
  ID                        id-at-zimbraCsrfTokenKey }

zimbraCustomMimeHeaderNameAllowed ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraCustomMimeHeaderNameAllowed"}
  LDAP-DESC                 "Custom RFC822 header names (case-sensitive) allowed to specify in SendMsgRequest"
  ID                        id-at-zimbraCustomMimeHeaderNameAllowed }

zimbraCustomerCareTier ATTRIBUTE ::= {
  WITH SYNTAX               INTEGER
  EQUALITY MATCHING RULE    integerMatch
  ORDERING MATCHING RULE    integerOrderingMatch
  SINGLE VALUE              TRUE
  LDAP-SYNTAX               integer.&id
  LDAP-NAME                 {"zimbraCustomerCareTier"}
  LDAP-DESC                 "set to 1 or 3 to specify customer care account tier level"
  ID                        id-at-zimbraCustomerCareTier }

-- LDAP syntax length {256} rendered as DirectoryString{256}.
zimbraDNSCheckHostname ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraDNSCheckHostname"}
  LDAP-DESC                 "This attribute is used for DNS check by customers that configure their MX to point at spam relays or other non-zimbra inbox smtp servers"
  ID                        id-at-zimbraDNSCheckHostname }

-- LDAP syntax length {256} rendered as DirectoryString{256}.
zimbraDNSMasterIP ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraDNSMasterIP"}
  LDAP-DESC                 "IP Address(es) of the root DNS servers to be used by the DNS cache service"
  ID                        id-at-zimbraDNSMasterIP }

-- LDAP syntax length {32} rendered as DirectoryString{32}.
zimbraDNSTCPUpstream ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraDNSTCPUpstream"}
  LDAP-DESC                 "For zimbra dnscache, whether or not to only use TCP when talking to the upstream Master DNS servers. Defaults to no"
  ID                        id-at-zimbraDNSTCPUpstream }

-- LDAP syntax length {32} rendered as DirectoryString{32}.
zimbraDNSUseTCP ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraDNSUseTCP"}
  LDAP-DESC                 "For zimbra dnscache, whether or not to use TCP. Defaults to yes"
  ID                        id-at-zimbraDNSUseTCP }

-- LDAP syntax length {32} rendered as DirectoryString{32}.
zimbraDNSUseUDP ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraDNSUseUDP"}
  LDAP-DESC                 "For zimbra dnscache, whether or not to use UDP. Defaults to yes"
  ID                        id-at-zimbraDNSUseUDP }

-- LDAP syntax length {256} rendered as DirectoryString{256}.
zimbraDataSourceAttribute ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraDataSourceAttribute"}
  LDAP-DESC                 "properties for data source"
  ID                        id-at-zimbraDataSourceAttribute }

-- LDAP syntax length {32} rendered as DirectoryString{32}.
zimbraDataSourceAuthMechanism ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraDataSourceAuthMechanism"}
  LDAP-DESC                 "Which SASL authentication mechanism to use for authenticating to IMAP server."
  ID                        id-at-zimbraDataSourceAuthMechanism }

zimbraDataSourceAuthorizationId ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraDataSourceAuthorizationId"}
  LDAP-DESC                 "authorizationId for SASL authentication"
  ID                        id-at-zimbraDataSourceAuthorizationId }

zimbraDataSourceCaldavPollingInterval ATTRIBUTE ::= {
  WITH SYNTAX               IA5String(SIZE (1..32))
  EQUALITY MATCHING RULE    caseIgnoreIA5Match
  SINGLE VALUE              TRUE
  LDAP-SYNTAX               ia5String.&id
  LDAP-NAME                 {"zimbraDataSourceCaldavPollingInterval"}
  LDAP-DESC                 "The time interval between automated data imports for a Caldav data source. If unset or 0, the data source will not be scheduled for automated polling. . Must be in valid duration format: {digits}{time-unit}. digits: 0-9, time-unit: [hmsd]|ms. h - hours, m - minutes, s - seconds, d - days, ms - milliseconds. If time unit is not specified, the default is s(seconds)."
  ID                        id-at-zimbraDataSourceCaldavPollingInterval }

zimbraDataSourceCalendarPollingInterval ATTRIBUTE ::= {
  WITH SYNTAX               IA5String(SIZE (1..32))
  EQUALITY MATCHING RULE    caseIgnoreIA5Match
  SINGLE VALUE              TRUE
  LDAP-SYNTAX               ia5String.&id
  LDAP-NAME                 {"zimbraDataSourceCalendarPollingInterval"}
  LDAP-DESC                 "The time interval between automated data imports for a remote calendar data source. If explicitly set to 0, the data source will not be scheduled for automated polling. . Must be in valid duration format: {digits}{time-unit}. digits: 0-9, time-unit: [hmsd]|ms. h - hours, m - minutes, s - seconds, d - days, ms - milliseconds. If time unit is not specified, the default is s(seconds)."
  ID                        id-at-zimbraDataSourceCalendarPollingInterval }

zimbraDataSourceConnectTimeout ATTRIBUTE ::= {
  WITH SYNTAX               INTEGER
  EQUALITY MATCHING RULE    integerMatch
  SINGLE VALUE              TRUE
  LDAP-SYNTAX               integer.&id
  LDAP-NAME                 {"zimbraDataSourceConnectTimeout"}
  LDAP-DESC                 "Connect timeout in seconds for the data source"
  ID                        id-at-zimbraDataSourceConnectTimeout }

-- LDAP syntax length {32} rendered as DirectoryString{32}.
zimbraDataSourceConnectionType ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraDataSourceConnectionType"}
  LDAP-DESC                 "Which security layer to use for connection (cleartext, ssl, tls, or tls if available). If not set on data source, fallback to the value on global config."
  ID                        id-at-zimbraDataSourceConnectionType }

-- LDAP syntax length {128} rendered as DirectoryString{128}.
zimbraDataSourceDomain ATTRIBUTE ::= {
  WITH SYNTAX               DirectoryString{128}
  EQUALITY MATCHING RULE    caseIgnoreMatch
  SUBSTRINGS MATCHING RULE  caseIgnoreSubstringsMatch
  SINGLE VALUE              TRUE
  LDAP-SYNTAX               directoryString.&id
  LDAP-NAME                 {"zimbraDataSourceDomain"}
  LDAP-DESC                 "domain name of data source"
  ID                        id-at-zimbraDataSourceDomain }

-- LDAP syntax length {128} rendered as DirectoryString{128}.
zimbraDataSourceEmailAddress ATTRIBUTE ::= {
  WITH SYNTAX               DirectoryString{128}
  EQUALITY MATCHING RULE    caseIgnoreMatch
  SUBSTRINGS MATCHING RULE  caseIgnoreSubstringsMatch
  SINGLE VALUE              TRUE
  LDAP-SYNTAX               directoryString.&id
  LDAP-NAME                 {"zimbraDataSourceEmailAddress"}
  LDAP-DESC                 "email address for the data source"
  ID                        id-at-zimbraDataSourceEmailAddress }

zimbraDataSourceEnableTrace ATTRIBUTE ::= {
  WITH SYNTAX               BOOLEAN
  EQUALITY MATCHING RULE    booleanMatch
  SINGLE VALUE              TRUE
  LDAP-SYNTAX               boolean.&id
  LDAP-NAME                 {"zimbraDataSourceEnableTrace"}
  LDAP-DESC                 "Whether to enable debug trace of this data source"
  ID                        id-at-zimbraDataSourceEnableTrace }

zimbraDataSourceEnabled ATTRIBUTE ::= {
  WITH SYNTAX               BOOLEAN
  EQUALITY MATCHING RULE    booleanMatch
  SINGLE VALUE              TRUE
  LDAP-SYNTAX               boolean.&id
  LDAP-NAME                 {"zimbraDataSourceEnabled"}
  LDAP-DESC                 "Whether or not the data source is enabled"
  ID                        id-at-zimbraDataSourceEnabled }

zimbraDataSourceFailingSince ATTRIBUTE ::= {
  WITH SYNTAX               GeneralizedTime
  EQUALITY MATCHING RULE    generalizedTimeMatch
  ORDERING MATCHING RULE    generalizedTimeOrderingMatch
  SINGLE VALUE              TRUE
  LDAP-SYNTAX               generalizedTime.&id
  LDAP-NAME                 {"zimbraDataSourceFailingSince"}
  LDAP-DESC                 "Timestamp of the first sync error for a data source. This value is unset after a successful sync."
  ID                        id-at-zimbraDataSourceFailingSince }

-- LDAP syntax length {128} rendered as DirectoryString{128}.
zimbraDataSourceFolderId ATTRIBUTE ::= {
  WITH SYNTAX               DirectoryString{128}
  EQUALITY MATCHING RULE    caseIgnoreMatch
  SUBSTRINGS MATCHING RULE  caseIgnoreSubstringsMatch
  SINGLE VALUE              TRUE
  LDAP-SYNTAX               directoryString.&id
  LDAP-NAME                 {"zimbraDataSourceFolderId"}
  LDAP-DESC                 "Local folder id to store retreived data in"
  ID                        id-at-zimbraDataSourceFolderId }

zimbraDataSourceGalPollingInterval ATTRIBUTE ::= {
  WITH SYNTAX               IA5String(SIZE (1..32))
  EQUALITY MATCHING RULE    caseIgnoreIA5Match
  SINGLE VALUE              TRUE
  LDAP-SYNTAX               ia5String.&id
  LDAP-NAME                 {"zimbraDataSourceGalPollingInterval"}
  LDAP-DESC                 "The time interval between automated data imports for a GAL data source. If unset or 0, the data source will not be scheduled for automated polling. . Must be in valid duration format: {digits}{time-unit}. digits: 0-9, time-unit: [hmsd]|ms. h - hours, m - minutes, s - seconds, d - days, ms - milliseconds. If time unit is not specified, the default is s(seconds)."
  ID                        id-at-zimbraDataSourceGalPollingInterval }

-- LDAP syntax length {128} rendered as DirectoryString{128}.
zimbraDataSourceHost ATTRIBUTE ::= {
  WITH SYNTAX               DirectoryString{128}
  EQUALITY MATCHING RULE    caseIgnoreMatch
  SUBSTRINGS MATCHING RULE  caseIgnoreSubstringsMatch
  SINGLE VALUE              TRUE
  LDAP-SYNTAX               directoryString.&id
  LDAP-NAME                 {"zimbraDataSourceHost"}
  LDAP-DESC                 "Host name of server"
  ID                        id-at-zimbraDataSourceHost }

-- LDAP syntax length {256} rendered as DirectoryString{256}.
zimbraDataSourceId ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraDataSourceId"}
  LDAP-DESC                 "Unique ID for a data source"
  ID                        id-at-zimbraDataSourceId }

zimbraDataSourceImapPollingInterval ATTRIBUTE ::= {
  WITH SYNTAX               IA5String(SIZE (1..32))
  EQUALITY MATCHING RULE    caseIgnoreIA5Match
  SINGLE VALUE              TRUE
  LDAP-SYNTAX               ia5String.&id
  LDAP-NAME                 {"zimbraDataSourceImapPollingInterval"}
  LDAP-DESC                 "The time interval between automated data imports for an Imap data source. If unset or 0, the data source will not be scheduled for automated polling. . Must be in valid duration format: {digits}{time-unit}. digits: 0-9, time-unit: [hmsd]|ms. h - hours, m - minutes, s - seconds, d - days, ms - milliseconds. If time unit is not specified, the default is s(seconds)."
  ID                        id-at-zimbraDataSourceImapPollingInterval }

-- LDAP syntax length {256} rendered as DirectoryString{256}.
zimbraDataSourceImportClassName ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraDataSourceImportClassName"}
  LDAP-DESC                 "DataImport class used by this data source object"
  ID                        id-at-zimbraDataSourceImportClassName }

zimbraDataSourceImportOnLogin ATTRIBUTE ::= {
  WITH SYNTAX               BOOLEAN
  EQUALITY MATCHING RULE    booleanMatch
  SINGLE VALUE              TRUE
  LDAP-SYNTAX               boolean.&id
  LDAP-NAME                 {"zimbraDataSourceImportOnLogin"}
  LDAP-DESC                 "whether to invoke data imports for all data sources owned by an account after successful user login from the login page"
  ID                        id-at-zimbraDataSourceImportOnLogin }

zimbraDataSourceImportOnly ATTRIBUTE ::= {
  WITH SYNTAX               BOOLEAN
  EQUALITY MATCHING RULE    booleanMatch
  SINGLE VALUE              TRUE
  LDAP-SYNTAX               boolean.&id
  LDAP-NAME                 {"zimbraDataSourceImportOnly"}
  LDAP-DESC                 "indicates that this datasource is used for one way (incoming) import vs. two-way sync"
  ID                        id-at-zimbraDataSourceImportOnly }

zimbraDataSourceIsInternal ATTRIBUTE ::= {
  WITH SYNTAX               BOOLEAN
  EQUALITY MATCHING RULE    booleanMatch
  SINGLE VALUE              TRUE
  LDAP-SYNTAX               boolean.&id
  LDAP-NAME                 {"zimbraDataSourceIsInternal"}
  LDAP-DESC                 "If TRUE, the data source is hidden from the UI."
  ID                        id-at-zimbraDataSourceIsInternal }

zimbraDataSourceLastError ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraDataSourceLastError"}
  LDAP-DESC                 "If the last data source sync failed, contains the error message. If the last data source sync succeeded, this attribute is unset."
  ID                        id-at-zimbraDataSourceLastError }

zimbraDataSourceLeaveOnServer ATTRIBUTE ::= {
  WITH SYNTAX               BOOLEAN
  EQUALITY MATCHING RULE    booleanMatch
  SINGLE VALUE              TRUE
  LDAP-SYNTAX               boolean.&id
  LDAP-NAME                 {"zimbraDataSourceLeaveOnServer"}
  LDAP-DESC                 "Specifies whether imported POP3 messages should be left on the server or deleted."
  ID                        id-at-zimbraDataSourceLeaveOnServer }

zimbraDataSourceLivePollingInterval ATTRIBUTE ::= {
  WITH SYNTAX               IA5String(SIZE (1..32))
  EQUALITY MATCHING RULE    caseIgnoreIA5Match
  SINGLE VALUE              TRUE
  LDAP-SYNTAX               ia5String.&id
  LDAP-NAME                 {"zimbraDataSourceLivePollingInterval"}
  LDAP-DESC                 "The time interval between automated data imports for a Live data source. If unset or 0, the data source will not be scheduled for automated polling. . Must be in valid duration format: {digits}{time-unit}. digits: 0-9, time-unit: [hmsd]|ms. h - hours, m - minutes, s - seconds, d - days, ms - milliseconds. If time unit is not specified, the default is s(seconds)."
  ID                        id-at-zimbraDataSourceLivePollingInterval }

zimbraDataSourceMaxNumEntries ATTRIBUTE ::= {
  WITH SYNTAX               INTEGER
  EQUALITY MATCHING RULE    integerMatch
  SINGLE VALUE              TRUE
  LDAP-SYNTAX               integer.&id
  LDAP-NAME                 {"zimbraDataSourceMaxNumEntries"}
  LDAP-DESC                 "Maximum number of data sources allowed on an account"
  ID                        id-at-zimbraDataSourceMaxNumEntries }

zimbraDataSourceMaxTraceSize ATTRIBUTE ::= {
  WITH SYNTAX               INTEGER
  EQUALITY MATCHING RULE    integerMatch
  SINGLE VALUE              TRUE
  LDAP-SYNTAX               integer.&id
  LDAP-NAME                 {"zimbraDataSourceMaxTraceSize"}
  LDAP-DESC                 "Message content data exceeding this size will not be included in IMAP trace file"
  ID                        id-at-zimbraDataSourceMaxTraceSize }

zimbraDataSourceMinPollingInterval ATTRIBUTE ::= {
  WITH SYNTAX               IA5String(SIZE (1..32))
  EQUALITY MATCHING RULE    caseIgnoreIA5Match
  SINGLE VALUE              TRUE
  LDAP-SYNTAX               ia5String.&id
  LDAP-NAME                 {"zimbraDataSourceMinPollingInterval"}
  LDAP-DESC                 "Shortest allowed duration for zimbraDataSourcePollingInterval.. Must be in valid duration format: {digits}{time-unit}. digits: 0-9, time-unit: [hmsd]|ms. h - hours, m - minutes, s - seconds, d - days, ms - milliseconds. If time unit is not specified, the default is s(seconds)."
  ID                        id-at-zimbraDataSourceMinPollingInterval }

-- LDAP syntax length {128} rendered as DirectoryString{128}.
zimbraDataSourceName ATTRIBUTE ::= {
  WITH SYNTAX               DirectoryString{128}
  EQUALITY MATCHING RULE    caseIgnoreMatch
  SUBSTRINGS MATCHING RULE  caseIgnoreSubstringsMatch
  SINGLE VALUE              TRUE
  LDAP-SYNTAX               directoryString.&id
  LDAP-NAME                 {"zimbraDataSourceName"}
  LDAP-DESC                 "Descriptive name of the data source"
  ID                        id-at-zimbraDataSourceName }

-- LDAP syntax length {128} rendered as DirectoryString{128}.
zimbraDataSourcePassword ATTRIBUTE ::= {
  WITH SYNTAX               DirectoryString{128}
  EQUALITY MATCHING RULE    caseIgnoreMatch
  SUBSTRINGS MATCHING RULE  caseIgnoreSubstringsMatch
  SINGLE VALUE              TRUE
  LDAP-SYNTAX               directoryString.&id
  LDAP-NAME                 {"zimbraDataSourcePassword"}
  LDAP-DESC                 "Password on server"
  ID                        id-at-zimbraDataSourcePassword }

zimbraDataSourcePollingInterval ATTRIBUTE ::= {
  WITH SYNTAX               IA5String(SIZE (1..32))
  EQUALITY MATCHING RULE    caseIgnoreIA5Match
  SINGLE VALUE              TRUE
  LDAP-SYNTAX               ia5String.&id
  LDAP-NAME                 {"zimbraDataSourcePollingInterval"}
  LDAP-DESC                 "Prior to 6.0.0: The time interval between automated data imports for a data source, or all data sources owned by an account. If unset or 0, the data source will not be scheduled for automated polling. Since 6.0.0: Deprecated on account/cos since 6.0.0. Values on account/cos are migrated to protocol specific zimbraDataSource{proto}PollingInterval attributes. 1. if zimbraDataSourcePollingInterval is set on data source, use it 2. otherwise use the zimbraDataSource{Proto}PollingInterval on account/cos 3. if zimbraDataSource{Proto}PollingInterval is not set on account/cos, use the attribute's default if one is specified. See individual attribute descriptions for defaults. . Must be in valid duration format: {digits}{time-unit}. digits: 0-9, time-unit: [hmsd]|ms. h - hours, m - minutes, s - seconds, d - days, ms - milliseconds. If time unit is not specified, the default is s(seconds)."
  ID                        id-at-zimbraDataSourcePollingInterval }

zimbraDataSourcePop3PollingInterval ATTRIBUTE ::= {
  WITH SYNTAX               IA5String(SIZE (1..32))
  EQUALITY MATCHING RULE    caseIgnoreIA5Match
  SINGLE VALUE              TRUE
  LDAP-SYNTAX               ia5String.&id
  LDAP-NAME                 {"zimbraDataSourcePop3PollingInterval"}
  LDAP-DESC                 "The time interval between automated data imports for a Pop3 data source. If unset or 0, the data source will not be scheduled for automated polling. . Must be in valid duration format: {digits}{time-unit}. digits: 0-9, time-unit: [hmsd]|ms. h - hours, m - minutes, s - seconds, d - days, ms - milliseconds. If time unit is not specified, the default is s(seconds)."
  ID                        id-at-zimbraDataSourcePop3PollingInterval }

zimbraDataSourcePort ATTRIBUTE ::= {
  WITH SYNTAX               INTEGER
  EQUALITY MATCHING RULE    integerMatch
  SINGLE VALUE              TRUE
  LDAP-SYNTAX               integer.&id
  LDAP-NAME                 {"zimbraDataSourcePort"}
  LDAP-DESC                 "Port number of server"
  ID                        id-at-zimbraDataSourcePort }

zimbraDataSourceReadTimeout ATTRIBUTE ::= {
  WITH SYNTAX               INTEGER
  EQUALITY MATCHING RULE    integerMatch
  SINGLE VALUE              TRUE
  LDAP-SYNTAX               integer.&id
  LDAP-NAME                 {"zimbraDataSourceReadTimeout"}
  LDAP-DESC                 "Read timeout in seconds"
  ID                        id-at-zimbraDataSourceReadTimeout }

zimbraDataSourceRssPollingInterval ATTRIBUTE ::= {
  WITH SYNTAX               IA5String(SIZE (1..32))
  EQUALITY MATCHING RULE    caseIgnoreIA5Match
  SINGLE VALUE              TRUE
  LDAP-SYNTAX               ia5String.&id
  LDAP-NAME                 {"zimbraDataSourceRssPollingInterval"}
  LDAP-DESC                 "The time interval between automated data imports for a Rss data source. If explicitly set to 0, the data source will not be scheduled for automated polling. . Must be in valid duration format: {digits}{time-unit}. digits: 0-9, time-unit: [hmsd]|ms. h - hours, m - minutes, s - seconds, d - days, ms - milliseconds. If time unit is not specified, the default is s(seconds)."
  ID                        id-at-zimbraDataSourceRssPollingInterval }

-- LDAP syntax length {256} rendered as DirectoryString{256}.
zimbraDataSourceType ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraDataSourceType"}
  LDAP-DESC                 "type of data source (pop3, imap, caldav, etc)"
  ID                        id-at-zimbraDataSourceType }

zimbraDataSourceUseAddressForForwardReply ATTRIBUTE ::= {
  WITH SYNTAX               BOOLEAN
  EQUALITY MATCHING RULE    booleanMatch
  SINGLE VALUE              TRUE
  LDAP-SYNTAX               boolean.&id
  LDAP-NAME                 {"zimbraDataSourceUseAddressForForwardReply"}
  LDAP-DESC                 "when forwarding or replying to messages sent to this data source, whether or not to use the email address of the data source for the from address and the designated signature/replyTo of the data source for the outgoing message."
  ID                        id-at-zimbraDataSourceUseAddressForForwardReply }

-- LDAP syntax length {128} rendered as DirectoryString{128}.
zimbraDataSourceUsername ATTRIBUTE ::= {
  WITH SYNTAX               DirectoryString{128}
  EQUALITY MATCHING RULE    caseIgnoreMatch
  SUBSTRINGS MATCHING RULE  caseIgnoreSubstringsMatch
  SINGLE VALUE              TRUE
  LDAP-SYNTAX               directoryString.&id
  LDAP-NAME                 {"zimbraDataSourceUsername"}
  LDAP-DESC                 "Username on server"
  ID                        id-at-zimbraDataSourceUsername }

zimbraDataSourceYabPollingInterval ATTRIBUTE ::= {
  WITH SYNTAX               IA5String(SIZE (1..32))
  EQUALITY MATCHING RULE    caseIgnoreIA5Match
  SINGLE VALUE              TRUE
  LDAP-SYNTAX               ia5String.&id
  LDAP-NAME                 {"zimbraDataSourceYabPollingInterval"}
  LDAP-DESC                 "The time interval between automated data imports for a Yahoo address book data source. If unset or 0, the data source will not be scheduled for automated polling. . Must be in valid duration format: {digits}{time-unit}. digits: 0-9, time-unit: [hmsd]|ms. h - hours, m - minutes, s - seconds, d - days, ms - milliseconds. If time unit is not specified, the default is s(seconds)."
  ID                        id-at-zimbraDataSourceYabPollingInterval }

zimbraDatabaseSlowSqlThreshold ATTRIBUTE ::= {
  WITH SYNTAX               IA5String(SIZE (1..32))
  EQUALITY MATCHING RULE    caseIgnoreIA5Match
  SINGLE VALUE              TRUE
  LDAP-SYNTAX               ia5String.&id
  LDAP-NAME                 {"zimbraDatabaseSlowSqlThreshold"}
  LDAP-DESC                 "SQL statements that take longer than this duration to execute will be logged to the sqltrace category in mailbox.log.. Must be in valid duration format: {digits}{time-unit}. digits: 0-9, time-unit: [hmsd]|ms. h - hours, m - minutes, s - seconds, d - days, ms - milliseconds. If time unit is not specified, the default is s(seconds)."
  ID                        id-at-zimbraDatabaseSlowSqlThreshold }

-- LDAP syntax length {1024} rendered as DirectoryString{1024}.
zimbraDebugInfo ATTRIBUTE ::= {
  WITH SYNTAX               DirectoryString{1024}
  EQUALITY MATCHING RULE    caseIgnoreMatch
  SUBSTRINGS MATCHING RULE  caseIgnoreSubstringsMatch
  LDAP-SYNTAX               directoryString.&id
  LDAP-NAME                 {"zimbraDebugInfo"}
  LDAP-DESC                 "For selective enabling of debug logging"
  ID                        id-at-zimbraDebugInfo }

zimbraDefaultAnalyzerStopWords ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraDefaultAnalyzerStopWords"}
  LDAP-DESC                 "stop words for lucene text analyzer. This setting takes effect only for default analyzer. This setting affects only accounts that do not have custom text analyzers. See zimbraTextAnalyzer for information on custom text analyzers."
  ID                        id-at-zimbraDefaultAnalyzerStopWords }

-- LDAP syntax length {256} rendered as DirectoryString{256}.
zimbraDefaultDomainName ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraDefaultDomainName"}
  LDAP-DESC                 "name of the default domain for accounts when authenticating without a domain"
  ID                        id-at-zimbraDefaultDomainName }

-- LDAP syntax length {32} rendered as DirectoryString{32}.
zimbraDefaultFolderFlags ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraDefaultFolderFlags"}
  LDAP-DESC                 "Default flags on folder. These are set when a new folder is created, has no effect on existing folders. Possible values are: * - \Subscribed b - \ExcludeFB # - \Checked i - \NoInherit y - \SyncFolder ~ - \Sync o - \Noinferiors g - \Global"
  ID                        id-at-zimbraDefaultFolderFlags }

zimbraDeviceAllowedPasscodeLockoutDuration ATTRIBUTE ::= {
  WITH SYNTAX               IA5String(SIZE (1..32))
  EQUALITY MATCHING RULE    caseIgnoreIA5Match
  LDAP-SYNTAX               ia5String.&id
  LDAP-NAME                 {"zimbraDeviceAllowedPasscodeLockoutDuration"}
  LDAP-DESC                 "allowed passcode lockout duration. Must be in valid duration format: {digits}{time-unit}. digits: 0-9, time-unit: [hmsd]|ms. h - hours, m - minutes, s - seconds, d - days, ms - milliseconds. If time unit is not specified, the default is s(seconds)."
  ID                        id-at-zimbraDeviceAllowedPasscodeLockoutDuration }

zimbraDeviceCalendarSoftDeleteExcludePattern ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"zimbraDeviceCalendarSoftDeleteExcludePattern"}
  LDAP-DESC                 "Regex to be matched for preventing devices from soft deletion of out of range calendar items. Suppose device is set to sync calendar item of 2 months range then server will ONLY send softdelete for out of range (expired) calendar items, if device id DOES NOT match to the regex provided."
  ID                        id-at-zimbraDeviceCalendarSoftDeleteExcludePattern }

zimbraDeviceFileOpenWithEnabled ATTRIBUTE ::= {
  WITH SYNTAX               BOOLEAN
  EQUALITY MATCHING RULE    booleanMatch
  SINGLE VALUE              TRUE
  LDAP-SYNTAX               boolean.&id
  LDAP-NAME                 {"zimbraDeviceFileOpenWithEnabled"}
  LDAP-DESC                 "Whether OpenWith feature is enabled on devices."
  ID                        id-at-zimbraDeviceFileOpenWithEnabled }

zimbraDeviceLockWhenInactive ATTRIBUTE ::= {
  WITH SYNTAX               BOOLEAN
  EQUALITY MATCHING RULE    booleanMatch
  SINGLE VALUE              TRUE
  LDAP-SYNTAX               boolean.&id
  LDAP-NAME                 {"zimbraDeviceLockWhenInactive"}
  LDAP-DESC                 "For native apps - whether to lock device when inactive."
  ID                        id-at-zimbraDeviceLockWhenInactive }

zimbraDeviceOfflineCacheEnabled ATTRIBUTE ::= {
  WITH SYNTAX               BOOLEAN
  EQUALITY MATCHING RULE    booleanMatch
  SINGLE VALUE              TRUE
  LDAP-SYNTAX               boolean.&id
  LDAP-NAME                 {"zimbraDeviceOfflineCacheEnabled"}
  LDAP-DESC                 "Whether offline reading of documents on device is allowed"
  ID                        id-at-zimbraDeviceOfflineCacheEnabled }

zimbraDevicePasscodeEnabled ATTRIBUTE ::= {
  WITH SYNTAX               BOOLEAN
  EQUALITY MATCHING RULE    booleanMatch
  SINGLE VALUE              TRUE
  LDAP-SYNTAX               boolean.&id
  LDAP-NAME                 {"zimbraDevicePasscodeEnabled"}
  LDAP-DESC                 "Whether device is password protected in native apps"
  ID                        id-at-zimbraDevicePasscodeEnabled }

zimbraDevicePasscodeLockoutDuration ATTRIBUTE ::= {
  WITH SYNTAX               IA5String(SIZE (1..32))
  EQUALITY MATCHING RULE    caseIgnoreIA5Match
  SINGLE VALUE              TRUE
  LDAP-SYNTAX               ia5String.&id
  LDAP-NAME                 {"zimbraDevicePasscodeLockoutDuration"}
  LDAP-DESC                 "passcode lockout duration. Must be in valid duration format: {digits}{time-unit}. digits: 0-9, time-unit: [hmsd]|ms. h - hours, m - minutes, s - seconds, d - days, ms - milliseconds. If time unit is not specified, the default is s(seconds)."
  ID                        id-at-zimbraDevicePasscodeLockoutDuration }

-- LDAP syntax length {256} rendered as DirectoryString{256}.
zimbraDistributionListSendShareMessageFromAddress ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraDistributionListSendShareMessageFromAddress"}
  LDAP-DESC                 "Email address to put in from header for the share info email. If not set, email address of the authenticated admin account will be used."
  ID                        id-at-zimbraDistributionListSendShareMessageFromAddress }

zimbraDistributionListSendShareMessageToNewMembers ATTRIBUTE ::= {
  WITH SYNTAX               BOOLEAN
  EQUALITY MATCHING RULE    booleanMatch
  SINGLE VALUE              TRUE
  LDAP-SYNTAX               boolean.&id
  LDAP-NAME                 {"zimbraDistributionListSendShareMessageToNewMembers"}
  LDAP-DESC                 "Whether to send an email with all the shares of the group when a new member is added to the group. If not set, default is to send the email."
  ID                        id-at-zimbraDistributionListSendShareMessageToNewMembers }

-- LDAP syntax length {32} rendered as DirectoryString{32}.
zimbraDistributionListSubscriptionPolicy ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraDistributionListSubscriptionPolicy"}
  LDAP-DESC                 "distribution subscription policy. ACCEPT: always accept, REJECT: always reject, APPROVAL: require owners approval."
  ID                        id-at-zimbraDistributionListSubscriptionPolicy }

-- LDAP syntax length {32} rendered as DirectoryString{32}.
zimbraDistributionListUnsubscriptionPolicy ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraDistributionListUnsubscriptionPolicy"}
  LDAP-DESC                 "distribution subscription policy. ACCEPT: always accept, REJECT: always reject, APPROVAL: require owners approval."
  ID                        id-at-zimbraDistributionListUnsubscriptionPolicy }

zimbraDomainAdminMaxMailQuota ATTRIBUTE ::= {
  WITH SYNTAX               INTEGER
  EQUALITY MATCHING RULE    integerMatch
  SINGLE VALUE              TRUE
  LDAP-SYNTAX               integer.&id
  LDAP-NAME                 {"zimbraDomainAdminMaxMailQuota"}
  LDAP-DESC                 "maximum amount of mail quota a domain admin can set on a user"
  ID                        id-at-zimbraDomainAdminMaxMailQuota }

-- LDAP syntax length {1024} rendered as DirectoryString{1024}.
zimbraDomainAdminModifiableAttr ATTRIBUTE ::= {
  WITH SYNTAX               DirectoryString{1024}
  EQUALITY MATCHING RULE    caseIgnoreMatch
  SUBSTRINGS MATCHING RULE  caseIgnoreSubstringsMatch
  LDAP-SYNTAX               directoryString.&id
  LDAP-NAME                 {"zimbraDomainAdminModifiableAttr"}
  LDAP-DESC                 "Deprecated since: 5.0. deprecated in favor of the domainAdminAdminModifiable flag. Orig desc: account attributes that a domain administrator is allowed to modify"
  ID                        id-at-zimbraDomainAdminModifiableAttr }

zimbraDomainAggregateQuota ATTRIBUTE ::= {
  WITH SYNTAX               INTEGER
  EQUALITY MATCHING RULE    integerMatch
  SINGLE VALUE              TRUE
  LDAP-SYNTAX               integer.&id
  LDAP-NAME                 {"zimbraDomainAggregateQuota"}
  LDAP-DESC                 "maximum aggregate quota for the domain in bytes"
  ID                        id-at-zimbraDomainAggregateQuota }

-- LDAP syntax length {32} rendered as DirectoryString{32}.
zimbraDomainAggregateQuotaPolicy ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraDomainAggregateQuotaPolicy"}
  LDAP-DESC                 "policy for a domain whose quota usage is above zimbraDomainAggregateQuota"
  ID                        id-at-zimbraDomainAggregateQuotaPolicy }

zimbraDomainAggregateQuotaWarnEmailRecipient ATTRIBUTE ::= {
  WITH SYNTAX               IA5String(SIZE (1..256))
  EQUALITY MATCHING RULE    caseIgnoreIA5Match
  SUBSTRINGS MATCHING RULE  caseIgnoreSubstringsMatch
  LDAP-SYNTAX               ia5String.&id
  LDAP-NAME                 {"zimbraDomainAggregateQuotaWarnEmailRecipient"}
  LDAP-DESC                 "email recipients to be notified when zimbraAggregateQuotaLastUsage reaches zimbraDomainAggregateQuotaWarnPercent of the zimbraDomainAggregateQuota"
  ID                        id-at-zimbraDomainAggregateQuotaWarnEmailRecipient }

zimbraDomainAggregateQuotaWarnPercent ATTRIBUTE ::= {
  WITH SYNTAX               INTEGER
  EQUALITY MATCHING RULE    integerMatch
  SINGLE VALUE              TRUE
  LDAP-SYNTAX               integer.&id
  LDAP-NAME                 {"zimbraDomainAggregateQuotaWarnPercent"}
  LDAP-DESC                 "percentage threshold for domain aggregate quota warnings"
  ID                        id-at-zimbraDomainAggregateQuotaWarnPercent }

-- LDAP syntax length {256} rendered as DirectoryString{256}.
zimbraDomainAliasTargetId ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraDomainAliasTargetId"}
  LDAP-DESC                 "zimbraId of domain alias target"
  ID                        id-at-zimbraDomainAliasTargetId }

-- LDAP syntax length {256} rendered as DirectoryString{256}.
zimbraDomainCOSMaxAccounts ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraDomainCOSMaxAccounts"}
  LDAP-DESC                 "maximum number of accounts allowed to be assigned to specified COSes in a domain. Values are in the format of {zimbraId-of-a-cos}:{max-accounts}"
  ID                        id-at-zimbraDomainCOSMaxAccounts }

-- LDAP syntax length {256} rendered as DirectoryString{256}.
zimbraDomainDefaultCOSId ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraDomainDefaultCOSId"}
  LDAP-DESC                 "COS zimbraID"
  ID                        id-at-zimbraDomainDefaultCOSId }

-- LDAP syntax length {256} rendered as DirectoryString{256}.
zimbraDomainDefaultExternalUserCOSId ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraDomainDefaultExternalUserCOSId"}
  LDAP-DESC                 "id of the default COS for external user accounts"
  ID                        id-at-zimbraDomainDefaultExternalUserCOSId }

-- LDAP syntax length {256} rendered as DirectoryString{256}.
zimbraDomainExtraObjectClass ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraDomainExtraObjectClass"}
  LDAP-DESC                 "Object classes to add when creating a zimbra domain object."
  ID                        id-at-zimbraDomainExtraObjectClass }

-- LDAP syntax length {256} rendered as DirectoryString{256}.
zimbraDomainFeatureMaxAccounts ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraDomainFeatureMaxAccounts"}
  LDAP-DESC                 "maximum number of accounts allowed to have specified features in a domain"
  ID                        id-at-zimbraDomainFeatureMaxAccounts }

-- LDAP syntax length {256} rendered as DirectoryString{256}.
zimbraDomainId ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraDomainId"}
  LDAP-DESC                 "ZimbraID of the domain that this component is registered under"
  ID                        id-at-zimbraDomainId }

-- LDAP syntax length {1024} rendered as DirectoryString{1024}.
zimbraDomainInheritedAttr ATTRIBUTE ::= {
  WITH SYNTAX               DirectoryString{1024}
  EQUALITY MATCHING RULE    caseIgnoreMatch
  SUBSTRINGS MATCHING RULE  caseIgnoreSubstringsMatch
  LDAP-SYNTAX               directoryString.&id
  LDAP-NAME                 {"zimbraDomainInheritedAttr"}
  LDAP-DESC                 "Deprecated since: 5.0. deprecated in favor of the domainInherited flag. Orig desc: zimbraDomain attrs that get inherited from global config"
  ID                        id-at-zimbraDomainInheritedAttr }

zimbraDomainMandatoryMailSignatureEnabled ATTRIBUTE ::= {
  WITH SYNTAX               BOOLEAN
  EQUALITY MATCHING RULE    booleanMatch
  SINGLE VALUE              TRUE
  LDAP-SYNTAX               boolean.&id
  LDAP-NAME                 {"zimbraDomainMandatoryMailSignatureEnabled"}
  LDAP-DESC                 "enable domain mandatory mail signature"
  ID                        id-at-zimbraDomainMandatoryMailSignatureEnabled }

zimbraDomainMandatoryMailSignatureHTML ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraDomainMandatoryMailSignatureHTML"}
  LDAP-DESC                 "Deprecated since: 8.5.0. deprecated in favor of zimbraAmavisDomainDisclaimerHTML. Orig desc: domain mandatory mail html signature"
  ID                        id-at-zimbraDomainMandatoryMailSignatureHTML }

zimbraDomainMandatoryMailSignatureText ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraDomainMandatoryMailSignatureText"}
  LDAP-DESC                 "Deprecated since: 8.5.0. deprecated in favor of zimbraAmavisDomainDisclaimerText. Orig desc: domain mandatory mail plain text signature"
  ID                        id-at-zimbraDomainMandatoryMailSignatureText }

zimbraDomainMaxAccounts ATTRIBUTE ::= {
  WITH SYNTAX               INTEGER
  EQUALITY MATCHING RULE    integerMatch
  SINGLE VALUE              TRUE
  LDAP-SYNTAX               integer.&id
  LDAP-NAME                 {"zimbraDomainMaxAccounts"}
  LDAP-DESC                 "maximum number of accounts allowed in a domain"
  ID                        id-at-zimbraDomainMaxAccounts }

-- LDAP syntax length {256} rendered as DirectoryString{256}.
zimbraDomainName ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraDomainName"}
  LDAP-DESC                 "name of the domain"
  ID                        id-at-zimbraDomainName }

-- LDAP syntax length {1024} rendered as DirectoryString{1024}.
zimbraDomainRenameInfo ATTRIBUTE ::= {
  WITH SYNTAX               DirectoryString{1024}
  EQUALITY MATCHING RULE    caseIgnoreMatch
  SUBSTRINGS MATCHING RULE  caseIgnoreSubstringsMatch
  SINGLE VALUE              TRUE
  LDAP-SYNTAX               directoryString.&id
  LDAP-NAME                 {"zimbraDomainRenameInfo"}
  LDAP-DESC                 "domain rename info/status"
  ID                        id-at-zimbraDomainRenameInfo }

-- LDAP syntax length {32} rendered as DirectoryString{32}.
zimbraDomainStatus ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraDomainStatus"}
  LDAP-DESC                 "domain status. enum values are akin to those of zimbraAccountStatus but the status affects all accounts on the domain. See table below for how zimbraDomainStatus affects account status. active - see zimbraAccountStatus maintenance - see zimbraAccountStatus locked - see zimbraAccountStatus closed - see zimbraAccountStatus suspended - maintenance + no creating/deleting/modifying accounts/DLs under the domain. shutdown - suspended + cannot modify domain attrs + cannot delete the domain Indicating server is doing major and lengthy maintenance work on the domain, e.g. renaming the domain and moving LDAP entries. Modification and deletion of the domain can only be done internally by the server when it is safe to release the domain, they cannot be done in admin console or zmprov. How zimbraDomainStatus affects account behavior : ------------------------------------- zimbraDomainStatus account behavior ------------------------------------- active zimbraAccountStatus locked zimbraAccountStatus if it is maintenance or pending or closed, else locked maintenance zimbraAccountStatus if it is pending or closed, else maintenance suspended zimbraAccountStatus if it is pending or closed, else maintenance shutdown zimbraAccountStatus if it is pending or closed, else maintenance closed closed"
  ID                        id-at-zimbraDomainStatus }

-- LDAP syntax length {32} rendered as DirectoryString{32}.
zimbraDomainType ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraDomainType"}
  LDAP-DESC                 "should be one of: local, alias"
  ID                        id-at-zimbraDomainType }

zimbraDumpsterEnabled ATTRIBUTE ::= {
  WITH SYNTAX               BOOLEAN
  EQUALITY MATCHING RULE    booleanMatch
  SINGLE VALUE              TRUE
  LDAP-SYNTAX               boolean.&id
  LDAP-NAME                 {"zimbraDumpsterEnabled"}
  LDAP-DESC                 "enable/disable dumpster"
  ID                        id-at-zimbraDumpsterEnabled }

zimbraDumpsterPurgeEnabled ATTRIBUTE ::= {
  WITH SYNTAX               BOOLEAN
  EQUALITY MATCHING RULE    booleanMatch
  SINGLE VALUE              TRUE
  LDAP-SYNTAX               boolean.&id
  LDAP-NAME                 {"zimbraDumpsterPurgeEnabled"}
  LDAP-DESC                 "disables purging from dumpster when set to FALSE"
  ID                        id-at-zimbraDumpsterPurgeEnabled }

zimbraDumpsterUserVisibleAge ATTRIBUTE ::= {
  WITH SYNTAX               IA5String(SIZE (1..32))
  EQUALITY MATCHING RULE    caseIgnoreIA5Match
  SINGLE VALUE              TRUE
  LDAP-SYNTAX               ia5String.&id
  LDAP-NAME                 {"zimbraDumpsterUserVisibleAge"}
  LDAP-DESC                 "limits how much of a dumpster data is viewable by the end user, based on the age since being put in dumpster. Must be in valid duration format: {digits}{time-unit}. digits: 0-9, time-unit: [hmsd]|ms. h - hours, m - minutes, s - seconds, d - days, ms - milliseconds. If time unit is not specified, the default is s(seconds)."
  ID                        id-at-zimbraDumpsterUserVisibleAge }

zimbraEmptyFolderOpTimeout ATTRIBUTE ::= {
  WITH SYNTAX               INTEGER
  EQUALITY MATCHING RULE    integerMatch
  SINGLE VALUE              TRUE
  LDAP-SYNTAX               integer.&id
  LDAP-NAME                 {"zimbraEmptyFolderOpTimeout"}
  LDAP-DESC                 "EmptyFolderOpTimeout is the time in seconds for which empty folder operation will wait for the current empty folder operation to complete"
  ID                        id-at-zimbraEmptyFolderOpTimeout }

-- LDAP syntax length {256} rendered as DirectoryString{256}.
zimbraErrorReportUrl ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraErrorReportUrl"}
  LDAP-DESC                 "URL for posting error report popped up in WEB client"
  ID                        id-at-zimbraErrorReportUrl }

zimbraExcludeFromCMBSearch ATTRIBUTE ::= {
  WITH SYNTAX               BOOLEAN
  EQUALITY MATCHING RULE    booleanMatch
  SINGLE VALUE              TRUE
  LDAP-SYNTAX               boolean.&id
  LDAP-NAME                 {"zimbraExcludeFromCMBSearch"}
  LDAP-DESC                 "Indicates the account should be excluded from Crossmailbox searchers."
  ID                        id-at-zimbraExcludeFromCMBSearch }

-- LDAP syntax length {128} rendered as DirectoryString{128}.
zimbraExtensionBindAddress ATTRIBUTE ::= {
  WITH SYNTAX               DirectoryString{128}
  EQUALITY MATCHING RULE    caseIgnoreMatch
  SUBSTRINGS MATCHING RULE  caseIgnoreSubstringsMatch
  SINGLE VALUE              TRUE
  LDAP-SYNTAX               directoryString.&id
  LDAP-NAME                 {"zimbraExtensionBindAddress"}
  LDAP-DESC                 "interface address on which zimbra extension server should listen; if empty, binds to all interfaces"
  ID                        id-at-zimbraExtensionBindAddress }

zimbraExternalAccountDisabledTime ATTRIBUTE ::= {
  WITH SYNTAX               GeneralizedTime
  EQUALITY MATCHING RULE    generalizedTimeMatch
  ORDERING MATCHING RULE    generalizedTimeOrderingMatch
  SINGLE VALUE              TRUE
  LDAP-SYNTAX               generalizedTime.&id
  LDAP-NAME                 {"zimbraExternalAccountDisabledTime"}
  LDAP-DESC                 "Time when external virtual account was last automatically disabled by the system. Applicable only when zimbraIsExternalVirtualAccount on the account is set to TRUE."
  ID                        id-at-zimbraExternalAccountDisabledTime }

zimbraExternalAccountLifetimeAfterDisabled ATTRIBUTE ::= {
  WITH SYNTAX               IA5String(SIZE (1..32))
  EQUALITY MATCHING RULE    caseIgnoreIA5Match
  SINGLE VALUE              TRUE
  LDAP-SYNTAX               ia5String.&id
  LDAP-NAME                 {"zimbraExternalAccountLifetimeAfterDisabled"}
  LDAP-DESC                 "Duration after the last time the external virtual account was automatically disabled by the system after which the external virtual account would be automatically deleted. Value of 0 indicates that the external virtual account should never be automatically deleted. Applicable only when zimbraIsExternalVirtualAccount on the account is set to TRUE. . Must be in valid duration format: {digits}{time-unit}. digits: 0-9, time-unit: [hmsd]|ms. h - hours, m - minutes, s - seconds, d - days, ms - milliseconds. If time unit is not specified, the default is s(seconds)."
  ID                        id-at-zimbraExternalAccountLifetimeAfterDisabled }

zimbraExternalAccountProvisioningKey ATTRIBUTE ::= {
  WITH SYNTAX               OCTET STRING (SIZE (1..128))
  EQUALITY MATCHING RULE    octetStringMatch
  SINGLE VALUE              TRUE
  LDAP-SYNTAX               octetString.&id
  LDAP-NAME                 {"zimbraExternalAccountProvisioningKey"}
  LDAP-DESC                 "Auth token secret key used for encrypting data/auth token in share URL when created for external users."
  ID                        id-at-zimbraExternalAccountProvisioningKey }

zimbraExternalAccountStatusCheckInterval ATTRIBUTE ::= {
  WITH SYNTAX               IA5String(SIZE (1..32))
  EQUALITY MATCHING RULE    caseIgnoreIA5Match
  SINGLE VALUE              TRUE
  LDAP-SYNTAX               ia5String.&id
  LDAP-NAME                 {"zimbraExternalAccountStatusCheckInterval"}
  LDAP-DESC                 "Interval between successive executions of the task that: - disables an external virtual account when all its accessible shares have been revoked or expired. - deletes an external virtual account after zimbraExternalAccountLifetimeAfterDisabled of being disabled. . Must be in valid duration format: {digits}{time-unit}. digits: 0-9, time-unit: [hmsd]|ms. h - hours, m - minutes, s - seconds, d - days, ms - milliseconds. If time unit is not specified, the default is s(seconds)."
  ID                        id-at-zimbraExternalAccountStatusCheckInterval }

-- LDAP syntax length {1024} rendered as DirectoryString{1024}.
zimbraExternalGroupHandlerClass ATTRIBUTE ::= {
  WITH SYNTAX               DirectoryString{1024}
  EQUALITY MATCHING RULE    caseIgnoreMatch
  SUBSTRINGS MATCHING RULE  caseIgnoreSubstringsMatch
  SINGLE VALUE              TRUE
  LDAP-SYNTAX               directoryString.&id
  LDAP-NAME                 {"zimbraExternalGroupHandlerClass"}
  LDAP-DESC                 "the handler class for getting all groups an account belongs to in the external directory"
  ID                        id-at-zimbraExternalGroupHandlerClass }

-- LDAP syntax length {256} rendered as DirectoryString{256}.
zimbraExternalGroupLdapSearchBase ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraExternalGroupLdapSearchBase"}
  LDAP-DESC                 "LDAP search base for searching external LDAP groups"
  ID                        id-at-zimbraExternalGroupLdapSearchBase }

-- LDAP syntax length {256} rendered as DirectoryString{256}.
zimbraExternalGroupLdapSearchFilter ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraExternalGroupLdapSearchFilter"}
  LDAP-DESC                 "LDAP search filter for searching external LDAP groups"
  ID                        id-at-zimbraExternalGroupLdapSearchFilter }

-- LDAP syntax length {256} rendered as DirectoryString{256}.
zimbraExternalImapHostname ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraExternalImapHostname"}
  LDAP-DESC                 "external imap hostname"
  ID                        id-at-zimbraExternalImapHostname }

zimbraExternalImapPort ATTRIBUTE ::= {
  WITH SYNTAX               INTEGER
  EQUALITY MATCHING RULE    integerMatch
  SINGLE VALUE              TRUE
  LDAP-SYNTAX               integer.&id
  LDAP-NAME                 {"zimbraExternalImapPort"}
  LDAP-DESC                 "external imap port"
  ID                        id-at-zimbraExternalImapPort }

-- LDAP syntax length {256} rendered as DirectoryString{256}.
zimbraExternalImapSSLHostname ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraExternalImapSSLHostname"}
  LDAP-DESC                 "external imap SSL hostname"
  ID                        id-at-zimbraExternalImapSSLHostname }

zimbraExternalImapSSLPort ATTRIBUTE ::= {
  WITH SYNTAX               INTEGER
  EQUALITY MATCHING RULE    integerMatch
  SINGLE VALUE              TRUE
  LDAP-SYNTAX               integer.&id
  LDAP-NAME                 {"zimbraExternalImapSSLPort"}
  LDAP-DESC                 "external imap SSL port"
  ID                        id-at-zimbraExternalImapSSLPort }

-- LDAP syntax length {256} rendered as DirectoryString{256}.
zimbraExternalPop3Hostname ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraExternalPop3Hostname"}
  LDAP-DESC                 "external pop3 hostname"
  ID                        id-at-zimbraExternalPop3Hostname }

zimbraExternalPop3Port ATTRIBUTE ::= {
  WITH SYNTAX               INTEGER
  EQUALITY MATCHING RULE    integerMatch
  SINGLE VALUE              TRUE
  LDAP-SYNTAX               integer.&id
  LDAP-NAME                 {"zimbraExternalPop3Port"}
  LDAP-DESC                 "external pop3 port"
  ID                        id-at-zimbraExternalPop3Port }

-- LDAP syntax length {256} rendered as DirectoryString{256}.
zimbraExternalPop3SSLHostname ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraExternalPop3SSLHostname"}
  LDAP-DESC                 "external pop3 SSL hostname"
  ID                        id-at-zimbraExternalPop3SSLHostname }

zimbraExternalPop3SSLPort ATTRIBUTE ::= {
  WITH SYNTAX               INTEGER
  EQUALITY MATCHING RULE    integerMatch
  SINGLE VALUE              TRUE
  LDAP-SYNTAX               integer.&id
  LDAP-NAME                 {"zimbraExternalPop3SSLPort"}
  LDAP-DESC                 "external pop3 SSL port"
  ID                        id-at-zimbraExternalPop3SSLPort }

zimbraExternalShareDomainWhitelistEnabled ATTRIBUTE ::= {
  WITH SYNTAX               BOOLEAN
  EQUALITY MATCHING RULE    booleanMatch
  SINGLE VALUE              TRUE
  LDAP-SYNTAX               boolean.&id
  LDAP-NAME                 {"zimbraExternalShareDomainWhitelistEnabled"}
  LDAP-DESC                 "whether checking against zimbraExternalShareWhitelistDomain for external user sharing is enabled"
  ID                        id-at-zimbraExternalShareDomainWhitelistEnabled }

zimbraExternalShareInvitationUrlExpiration ATTRIBUTE ::= {
  WITH SYNTAX               IA5String(SIZE (1..32))
  EQUALITY MATCHING RULE    caseIgnoreIA5Match
  SINGLE VALUE              TRUE
  LDAP-SYNTAX               ia5String.&id
  LDAP-NAME                 {"zimbraExternalShareInvitationUrlExpiration"}
  LDAP-DESC                 "Duration for which the URL sent in the share invitation email to an external user is valid. A value of 0 indicates that the URL never expires. . Must be in valid duration format: {digits}{time-unit}. digits: 0-9, time-unit: [hmsd]|ms. h - hours, m - minutes, s - seconds, d - days, ms - milliseconds. If time unit is not specified, the default is s(seconds)."
  ID                        id-at-zimbraExternalShareInvitationUrlExpiration }

zimbraExternalShareLifetime ATTRIBUTE ::= {
  WITH SYNTAX               IA5String(SIZE (1..32))
  EQUALITY MATCHING RULE    caseIgnoreIA5Match
  SINGLE VALUE              TRUE
  LDAP-SYNTAX               ia5String.&id
  LDAP-NAME                 {"zimbraExternalShareLifetime"}
  LDAP-DESC                 "Maximum allowed lifetime of shares to external users. A value of 0 indicates that there's no limit on an external share's lifetime. . Must be in valid duration format: {digits}{time-unit}. digits: 0-9, time-unit: [hmsd]|ms. h - hours, m - minutes, s - seconds, d - days, ms - milliseconds. If time unit is not specified, the default is s(seconds)."
  ID                        id-at-zimbraExternalShareLifetime }

zimbraExternalShareWhitelistDomain ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraExternalShareWhitelistDomain"}
  LDAP-DESC                 "list of external domains that users can share files and folders with"
  ID                        id-at-zimbraExternalShareWhitelistDomain }

zimbraExternalSharingEnabled ATTRIBUTE ::= {
  WITH SYNTAX               BOOLEAN
  EQUALITY MATCHING RULE    booleanMatch
  SINGLE VALUE              TRUE
  LDAP-SYNTAX               boolean.&id
  LDAP-NAME                 {"zimbraExternalSharingEnabled"}
  LDAP-DESC                 "switch for turning external user sharing on/off"
  ID                        id-at-zimbraExternalSharingEnabled }

zimbraExternalUserMailAddress ATTRIBUTE ::= {
  WITH SYNTAX               IA5String(SIZE (1..256))
  EQUALITY MATCHING RULE    caseIgnoreIA5Match
  SUBSTRINGS MATCHING RULE  caseIgnoreSubstringsMatch
  SINGLE VALUE              TRUE
  LDAP-SYNTAX               ia5String.&id
  LDAP-NAME                 {"zimbraExternalUserMailAddress"}
  LDAP-DESC                 "External email address of an external user. Applicable only when zimbraIsExternalVirtualAccount is set to TRUE."
  ID                        id-at-zimbraExternalUserMailAddress }

zimbraFeatureAdminMailEnabled ATTRIBUTE ::= {
  WITH SYNTAX               BOOLEAN
  EQUALITY MATCHING RULE    booleanMatch
  SINGLE VALUE              TRUE
  LDAP-SYNTAX               boolean.&id
  LDAP-NAME                 {"zimbraFeatureAdminMailEnabled"}
  LDAP-DESC                 "whether email features and tabs are enabled in the web client if accessed from the admin console"
  ID                        id-at-zimbraFeatureAdminMailEnabled }

zimbraFeatureAdvancedSearchEnabled ATTRIBUTE ::= {
  WITH SYNTAX               BOOLEAN
  EQUALITY MATCHING RULE    booleanMatch
  SINGLE VALUE              TRUE
  LDAP-SYNTAX               boolean.&id
  LDAP-NAME                 {"zimbraFeatureAdvancedSearchEnabled"}
  LDAP-DESC                 "Deprecated since: 8.0.0. Deprecated as of bug 56924. Orig desc: advanced search button enabled"
  ID                        id-at-zimbraFeatureAdvancedSearchEnabled }

zimbraFeatureAntispamEnabled ATTRIBUTE ::= {
  WITH SYNTAX               BOOLEAN
  EQUALITY MATCHING RULE    booleanMatch
  SINGLE VALUE              TRUE
  LDAP-SYNTAX               boolean.&id
  LDAP-NAME                 {"zimbraFeatureAntispamEnabled"}
  LDAP-DESC                 "whether or not to enable rerouting spam messages to Junk folder in ZCS, exposing Junk folder and actions in the web UI, and exposing Junk folder to IMAP clients."
  ID                        id-at-zimbraFeatureAntispamEnabled }

zimbraFeatureBriefcaseDocsEnabled ATTRIBUTE ::= {
  WITH SYNTAX               BOOLEAN
  EQUALITY MATCHING RULE    booleanMatch
  SINGLE VALUE              TRUE
  LDAP-SYNTAX               boolean.&id
  LDAP-NAME                 {"zimbraFeatureBriefcaseDocsEnabled"}
  LDAP-DESC                 "Docs features enabled in briefcase"
  ID                        id-at-zimbraFeatureBriefcaseDocsEnabled }

zimbraFeatureBriefcaseSlidesEnabled ATTRIBUTE ::= {
  WITH SYNTAX               BOOLEAN
  EQUALITY MATCHING RULE    booleanMatch
  SINGLE VALUE              TRUE
  LDAP-SYNTAX               boolean.&id
  LDAP-NAME                 {"zimbraFeatureBriefcaseSlidesEnabled"}
  LDAP-DESC                 "Slides features enabled in briefcase"
  ID                        id-at-zimbraFeatureBriefcaseSlidesEnabled }

zimbraFeatureBriefcaseSpreadsheetEnabled ATTRIBUTE ::= {
  WITH SYNTAX               BOOLEAN
  EQUALITY MATCHING RULE    booleanMatch
  SINGLE VALUE              TRUE
  LDAP-SYNTAX               boolean.&id
  LDAP-NAME                 {"zimbraFeatureBriefcaseSpreadsheetEnabled"}
  LDAP-DESC                 "Spreadsheet features enabled in briefcase"
  ID                        id-at-zimbraFeatureBriefcaseSpreadsheetEnabled }

zimbraFeatureBriefcasesEnabled ATTRIBUTE ::= {
  WITH SYNTAX               BOOLEAN
  EQUALITY MATCHING RULE    booleanMatch
  SINGLE VALUE              TRUE
  LDAP-SYNTAX               boolean.&id
  LDAP-NAME                 {"zimbraFeatureBriefcasesEnabled"}
  LDAP-DESC                 "whether to allow use of briefcase feature"
  ID                        id-at-zimbraFeatureBriefcasesEnabled }

zimbraFeatureCalendarEnabled ATTRIBUTE ::= {
  WITH SYNTAX               BOOLEAN
  EQUALITY MATCHING RULE    booleanMatch
  SINGLE VALUE              TRUE
  LDAP-SYNTAX               boolean.&id
  LDAP-NAME                 {"zimbraFeatureCalendarEnabled"}
  LDAP-DESC                 "calendar features"
  ID                        id-at-zimbraFeatureCalendarEnabled }

zimbraFeatureCalendarReminderDeviceEmailEnabled ATTRIBUTE ::= {
  WITH SYNTAX               BOOLEAN
  EQUALITY MATCHING RULE    booleanMatch
  SINGLE VALUE              TRUE
  LDAP-SYNTAX               boolean.&id
  LDAP-NAME                 {"zimbraFeatureCalendarReminderDeviceEmailEnabled"}
  LDAP-DESC                 "whether receiving reminders on the designated device for appointments and tasks is enabled"
  ID                        id-at-zimbraFeatureCalendarReminderDeviceEmailEnabled }

zimbraFeatureCalendarUpsellEnabled ATTRIBUTE ::= {
  WITH SYNTAX               BOOLEAN
  EQUALITY MATCHING RULE    booleanMatch
  SINGLE VALUE              TRUE
  LDAP-SYNTAX               boolean.&id
  LDAP-NAME                 {"zimbraFeatureCalendarUpsellEnabled"}
  LDAP-DESC                 "calendar upsell enabled"
  ID                        id-at-zimbraFeatureCalendarUpsellEnabled }

-- LDAP syntax length {256} rendered as DirectoryString{256}.
zimbraFeatureCalendarUpsellURL ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraFeatureCalendarUpsellURL"}
  LDAP-DESC                 "calendar upsell URL"
  ID                        id-at-zimbraFeatureCalendarUpsellURL }

zimbraFeatureChangePasswordEnabled ATTRIBUTE ::= {
  WITH SYNTAX               BOOLEAN
  EQUALITY MATCHING RULE    booleanMatch
  SINGLE VALUE              TRUE
  LDAP-SYNTAX               boolean.&id
  LDAP-NAME                 {"zimbraFeatureChangePasswordEnabled"}
  LDAP-DESC                 "password changing"
  ID                        id-at-zimbraFeatureChangePasswordEnabled }

zimbraFeatureComposeInNewWindowEnabled ATTRIBUTE ::= {
  WITH SYNTAX               BOOLEAN
  EQUALITY MATCHING RULE    booleanMatch
  SINGLE VALUE              TRUE
  LDAP-SYNTAX               boolean.&id
  LDAP-NAME                 {"zimbraFeatureComposeInNewWindowEnabled"}
  LDAP-DESC                 "whether or not compose messages in a new windows is allowed"
  ID                        id-at-zimbraFeatureComposeInNewWindowEnabled }

zimbraFeatureConfirmationPageEnabled ATTRIBUTE ::= {
  WITH SYNTAX               BOOLEAN
  EQUALITY MATCHING RULE    booleanMatch
  SINGLE VALUE              TRUE
  LDAP-SYNTAX               boolean.&id
  LDAP-NAME                 {"zimbraFeatureConfirmationPageEnabled"}
  LDAP-DESC                 "whether a confirmation page should be display after an operation is done in the UI"
  ID                        id-at-zimbraFeatureConfirmationPageEnabled }

zimbraFeatureContactsDetailedSearchEnabled ATTRIBUTE ::= {
  WITH SYNTAX               BOOLEAN
  EQUALITY MATCHING RULE    booleanMatch
  SINGLE VALUE              TRUE
  LDAP-SYNTAX               boolean.&id
  LDAP-NAME                 {"zimbraFeatureContactsDetailedSearchEnabled"}
  LDAP-DESC                 "whether detailed contact search UI is enabled"
  ID                        id-at-zimbraFeatureContactsDetailedSearchEnabled }

zimbraFeatureContactsEnabled ATTRIBUTE ::= {
  WITH SYNTAX               BOOLEAN
  EQUALITY MATCHING RULE    booleanMatch
  SINGLE VALUE              TRUE
  LDAP-SYNTAX               boolean.&id
  LDAP-NAME                 {"zimbraFeatureContactsEnabled"}
  LDAP-DESC                 "contact features"
  ID                        id-at-zimbraFeatureContactsEnabled }

zimbraFeatureContactsUpsellEnabled ATTRIBUTE ::= {
  WITH SYNTAX               BOOLEAN
  EQUALITY MATCHING RULE    booleanMatch
  SINGLE VALUE              TRUE
  LDAP-SYNTAX               boolean.&id
  LDAP-NAME                 {"zimbraFeatureContactsUpsellEnabled"}
  LDAP-DESC                 "address book upsell enabled"
  ID                        id-at-zimbraFeatureContactsUpsellEnabled }

-- LDAP syntax length {256} rendered as DirectoryString{256}.
zimbraFeatureContactsUpsellURL ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraFeatureContactsUpsellURL"}
  LDAP-DESC                 "address book upsell URL"
  ID                        id-at-zimbraFeatureContactsUpsellURL }

zimbraFeatureConversationsEnabled ATTRIBUTE ::= {
  WITH SYNTAX               BOOLEAN
  EQUALITY MATCHING RULE    booleanMatch
  SINGLE VALUE              TRUE
  LDAP-SYNTAX               boolean.&id
  LDAP-NAME                 {"zimbraFeatureConversationsEnabled"}
  LDAP-DESC                 "conversations"
  ID                        id-at-zimbraFeatureConversationsEnabled }

zimbraFeatureCrocodocEnabled ATTRIBUTE ::= {
  WITH SYNTAX               BOOLEAN
  EQUALITY MATCHING RULE    booleanMatch
  SINGLE VALUE              TRUE
  LDAP-SYNTAX               boolean.&id
  LDAP-NAME                 {"zimbraFeatureCrocodocEnabled"}
  LDAP-DESC                 "whether Crocodoc feature is enabled in the web client"
  ID                        id-at-zimbraFeatureCrocodocEnabled }

zimbraFeatureDiscardInFiltersEnabled ATTRIBUTE ::= {
  WITH SYNTAX               BOOLEAN
  EQUALITY MATCHING RULE    booleanMatch
  SINGLE VALUE              TRUE
  LDAP-SYNTAX               boolean.&id
  LDAP-NAME                 {"zimbraFeatureDiscardInFiltersEnabled"}
  LDAP-DESC                 "enable end-user mail discarding defined in mail filters features"
  ID                        id-at-zimbraFeatureDiscardInFiltersEnabled }

zimbraFeatureDistributionListExpandMembersEnabled ATTRIBUTE ::= {
  WITH SYNTAX               BOOLEAN
  EQUALITY MATCHING RULE    booleanMatch
  SINGLE VALUE              TRUE
  LDAP-SYNTAX               boolean.&id
  LDAP-NAME                 {"zimbraFeatureDistributionListExpandMembersEnabled"}
  LDAP-DESC                 "whether expanding distribution list members feature is enabled"
  ID                        id-at-zimbraFeatureDistributionListExpandMembersEnabled }

zimbraFeatureDistributionListFolderEnabled ATTRIBUTE ::= {
  WITH SYNTAX               BOOLEAN
  EQUALITY MATCHING RULE    booleanMatch
  SINGLE VALUE              TRUE
  LDAP-SYNTAX               boolean.&id
  LDAP-NAME                 {"zimbraFeatureDistributionListFolderEnabled"}
  LDAP-DESC                 "Whether to display the distribution list folder in address book"
  ID                        id-at-zimbraFeatureDistributionListFolderEnabled }

zimbraFeatureEwsEnabled ATTRIBUTE ::= {
  WITH SYNTAX               BOOLEAN
  EQUALITY MATCHING RULE    booleanMatch
  SINGLE VALUE              TRUE
  LDAP-SYNTAX               boolean.&id
  LDAP-NAME                 {"zimbraFeatureEwsEnabled"}
  LDAP-DESC                 "Whether to allow a user to access EWS service"
  ID                        id-at-zimbraFeatureEwsEnabled }

zimbraFeatureExportFolderEnabled ATTRIBUTE ::= {
  WITH SYNTAX               BOOLEAN
  EQUALITY MATCHING RULE    booleanMatch
  SINGLE VALUE              TRUE
  LDAP-SYNTAX               boolean.&id
  LDAP-NAME                 {"zimbraFeatureExportFolderEnabled"}
  LDAP-DESC                 "whether export folder feature is enabled"
  ID                        id-at-zimbraFeatureExportFolderEnabled }

zimbraFeatureExternalFeedbackEnabled ATTRIBUTE ::= {
  WITH SYNTAX               BOOLEAN
  EQUALITY MATCHING RULE    booleanMatch
  SINGLE VALUE              TRUE
  LDAP-SYNTAX               boolean.&id
  LDAP-NAME                 {"zimbraFeatureExternalFeedbackEnabled"}
  LDAP-DESC                 "whether external feedback feature is enabled"
  ID                        id-at-zimbraFeatureExternalFeedbackEnabled }

zimbraFeatureFiltersEnabled ATTRIBUTE ::= {
  WITH SYNTAX               BOOLEAN
  EQUALITY MATCHING RULE    booleanMatch
  SINGLE VALUE              TRUE
  LDAP-SYNTAX               boolean.&id
  LDAP-NAME                 {"zimbraFeatureFiltersEnabled"}
  LDAP-DESC                 "filter prefs enabled"
  ID                        id-at-zimbraFeatureFiltersEnabled }

zimbraFeatureFlaggingEnabled ATTRIBUTE ::= {
  WITH SYNTAX               BOOLEAN
  EQUALITY MATCHING RULE    booleanMatch
  SINGLE VALUE              TRUE
  LDAP-SYNTAX               boolean.&id
  LDAP-NAME                 {"zimbraFeatureFlaggingEnabled"}
  LDAP-DESC                 "whether to allow use of flagging feature"
  ID                        id-at-zimbraFeatureFlaggingEnabled }

zimbraFeatureFreeBusyViewEnabled ATTRIBUTE ::= {
  WITH SYNTAX               BOOLEAN
  EQUALITY MATCHING RULE    booleanMatch
  SINGLE VALUE              TRUE
  LDAP-SYNTAX               boolean.&id
  LDAP-NAME                 {"zimbraFeatureFreeBusyViewEnabled"}
  LDAP-DESC                 "whether free busy view is enabled in the web UI"
  ID                        id-at-zimbraFeatureFreeBusyViewEnabled }

zimbraFeatureFromDisplayEnabled ATTRIBUTE ::= {
  WITH SYNTAX               BOOLEAN
  EQUALITY MATCHING RULE    booleanMatch
  SINGLE VALUE              TRUE
  LDAP-SYNTAX               boolean.&id
  LDAP-NAME                 {"zimbraFeatureFromDisplayEnabled"}
  LDAP-DESC                 "whether to display from address control in user preferences"
  ID                        id-at-zimbraFeatureFromDisplayEnabled }

zimbraFeatureGalAutoCompleteEnabled ATTRIBUTE ::= {
  WITH SYNTAX               BOOLEAN
  EQUALITY MATCHING RULE    booleanMatch
  SINGLE VALUE              TRUE
  LDAP-SYNTAX               boolean.&id
  LDAP-NAME                 {"zimbraFeatureGalAutoCompleteEnabled"}
  LDAP-DESC                 "enable auto-completion from the GAL, zimbraFeatureGalEnabled also has to be enabled for the auto-completion feature"
  ID                        id-at-zimbraFeatureGalAutoCompleteEnabled }

zimbraFeatureGalEnabled ATTRIBUTE ::= {
  WITH SYNTAX               BOOLEAN
  EQUALITY MATCHING RULE    booleanMatch
  SINGLE VALUE              TRUE
  LDAP-SYNTAX               boolean.&id
  LDAP-NAME                 {"zimbraFeatureGalEnabled"}
  LDAP-DESC                 "whether GAL features are enabled"
  ID                        id-at-zimbraFeatureGalEnabled }

zimbraFeatureGalSyncEnabled ATTRIBUTE ::= {
  WITH SYNTAX               BOOLEAN
  EQUALITY MATCHING RULE    booleanMatch
  SINGLE VALUE              TRUE
  LDAP-SYNTAX               boolean.&id
  LDAP-NAME                 {"zimbraFeatureGalSyncEnabled"}
  LDAP-DESC                 "whether GAL sync feature is enabled"
  ID                        id-at-zimbraFeatureGalSyncEnabled }

zimbraFeatureGroupCalendarEnabled ATTRIBUTE ::= {
  WITH SYNTAX               BOOLEAN
  EQUALITY MATCHING RULE    booleanMatch
  SINGLE VALUE              TRUE
  LDAP-SYNTAX               boolean.&id
  LDAP-NAME                 {"zimbraFeatureGroupCalendarEnabled"}
  LDAP-DESC                 "group calendar features. if set to FALSE, calendar works as a personal calendar and attendees and scheduling etc are turned off in web UI"
  ID                        id-at-zimbraFeatureGroupCalendarEnabled }

zimbraFeatureHtmlComposeEnabled ATTRIBUTE ::= {
  WITH SYNTAX               BOOLEAN
  EQUALITY MATCHING RULE    booleanMatch
  SINGLE VALUE              TRUE
  LDAP-SYNTAX               boolean.&id
  LDAP-NAME                 {"zimbraFeatureHtmlComposeEnabled"}
  LDAP-DESC                 "enabled html composing"
  ID                        id-at-zimbraFeatureHtmlComposeEnabled }

zimbraFeatureIMEnabled ATTRIBUTE ::= {
  WITH SYNTAX               BOOLEAN
  EQUALITY MATCHING RULE    booleanMatch
  SINGLE VALUE              TRUE
  LDAP-SYNTAX               boolean.&id
  LDAP-NAME                 {"zimbraFeatureIMEnabled"}
  LDAP-DESC                 "IM features"
  ID                        id-at-zimbraFeatureIMEnabled }

zimbraFeatureIdentitiesEnabled ATTRIBUTE ::= {
  WITH SYNTAX               BOOLEAN
  EQUALITY MATCHING RULE    booleanMatch
  SINGLE VALUE              TRUE
  LDAP-SYNTAX               boolean.&id
  LDAP-NAME                 {"zimbraFeatureIdentitiesEnabled"}
  LDAP-DESC                 "whether to allow use of identities feature"
  ID                        id-at-zimbraFeatureIdentitiesEnabled }

zimbraFeatureImapDataSourceEnabled ATTRIBUTE ::= {
  WITH SYNTAX               BOOLEAN
  EQUALITY MATCHING RULE    booleanMatch
  SINGLE VALUE              TRUE
  LDAP-SYNTAX               boolean.&id
  LDAP-NAME                 {"zimbraFeatureImapDataSourceEnabled"}
  LDAP-DESC                 "whether user is allowed to retrieve mail from an external IMAP data source"
  ID                        id-at-zimbraFeatureImapDataSourceEnabled }

zimbraFeatureImportExportFolderEnabled ATTRIBUTE ::= {
  WITH SYNTAX               BOOLEAN
  EQUALITY MATCHING RULE    booleanMatch
  SINGLE VALUE              TRUE
  LDAP-SYNTAX               boolean.&id
  LDAP-NAME                 {"zimbraFeatureImportExportFolderEnabled"}
  LDAP-DESC                 "Deprecated since: 7.1.0. deprecated in favor of zimbraFeatureImportFolderEnabled and zimbraFeatureExportFolderEnabled for bug 53745. Orig desc: whether import export folder feature is enabled"
  ID                        id-at-zimbraFeatureImportExportFolderEnabled }

zimbraFeatureImportFolderEnabled ATTRIBUTE ::= {
  WITH SYNTAX               BOOLEAN
  EQUALITY MATCHING RULE    booleanMatch
  SINGLE VALUE              TRUE
  LDAP-SYNTAX               boolean.&id
  LDAP-NAME                 {"zimbraFeatureImportFolderEnabled"}
  LDAP-DESC                 "whether import folder feature is enabled"
  ID                        id-at-zimbraFeatureImportFolderEnabled }

zimbraFeatureInitialSearchPreferenceEnabled ATTRIBUTE ::= {
  WITH SYNTAX               BOOLEAN
  EQUALITY MATCHING RULE    booleanMatch
  SINGLE VALUE              TRUE
  LDAP-SYNTAX               boolean.&id
  LDAP-NAME                 {"zimbraFeatureInitialSearchPreferenceEnabled"}
  LDAP-DESC                 "preference to set initial search"
  ID                        id-at-zimbraFeatureInitialSearchPreferenceEnabled }

zimbraFeatureInstantNotify ATTRIBUTE ::= {
  WITH SYNTAX               BOOLEAN
  EQUALITY MATCHING RULE    booleanMatch
  SINGLE VALUE              TRUE
  LDAP-SYNTAX               boolean.&id
  LDAP-NAME                 {"zimbraFeatureInstantNotify"}
  LDAP-DESC                 "Enable instant notifications"
  ID                        id-at-zimbraFeatureInstantNotify }

zimbraFeatureMAPIConnectorEnabled ATTRIBUTE ::= {
  WITH SYNTAX               BOOLEAN
  EQUALITY MATCHING RULE    booleanMatch
  SINGLE VALUE              TRUE
  LDAP-SYNTAX               boolean.&id
  LDAP-NAME                 {"zimbraFeatureMAPIConnectorEnabled"}
  LDAP-DESC                 "enable/disable MAPI (Microsoft Outlook) Connector"
  ID                        id-at-zimbraFeatureMAPIConnectorEnabled }

zimbraFeatureMailEnabled ATTRIBUTE ::= {
  WITH SYNTAX               BOOLEAN
  EQUALITY MATCHING RULE    booleanMatch
  SINGLE VALUE              TRUE
  LDAP-SYNTAX               boolean.&id
  LDAP-NAME                 {"zimbraFeatureMailEnabled"}
  LDAP-DESC                 "email features enabled"
  ID                        id-at-zimbraFeatureMailEnabled }

zimbraFeatureMailForwardingEnabled ATTRIBUTE ::= {
  WITH SYNTAX               BOOLEAN
  EQUALITY MATCHING RULE    booleanMatch
  SINGLE VALUE              TRUE
  LDAP-SYNTAX               boolean.&id
  LDAP-NAME                 {"zimbraFeatureMailForwardingEnabled"}
  LDAP-DESC                 "enable end-user mail forwarding features"
  ID                        id-at-zimbraFeatureMailForwardingEnabled }

zimbraFeatureMailForwardingInFiltersEnabled ATTRIBUTE ::= {
  WITH SYNTAX               BOOLEAN
  EQUALITY MATCHING RULE    booleanMatch
  SINGLE VALUE              TRUE
  LDAP-SYNTAX               boolean.&id
  LDAP-NAME                 {"zimbraFeatureMailForwardingInFiltersEnabled"}
  LDAP-DESC                 "enable end-user mail forwarding defined in mail filters features"
  ID                        id-at-zimbraFeatureMailForwardingInFiltersEnabled }

zimbraFeatureMailPollingIntervalPreferenceEnabled ATTRIBUTE ::= {
  WITH SYNTAX               BOOLEAN
  EQUALITY MATCHING RULE    booleanMatch
  SINGLE VALUE              TRUE
  LDAP-SYNTAX               boolean.&id
  LDAP-NAME                 {"zimbraFeatureMailPollingIntervalPreferenceEnabled"}
  LDAP-DESC                 "Deprecated since: 5.0. done via skin template overrides. Orig desc: whether user is allowed to set mail polling interval"
  ID                        id-at-zimbraFeatureMailPollingIntervalPreferenceEnabled }

zimbraFeatureMailPriorityEnabled ATTRIBUTE ::= {
  WITH SYNTAX               BOOLEAN
  EQUALITY MATCHING RULE    booleanMatch
  SINGLE VALUE              TRUE
  LDAP-SYNTAX               boolean.&id
  LDAP-NAME                 {"zimbraFeatureMailPriorityEnabled"}
  LDAP-DESC                 "mail priority feature"
  ID                        id-at-zimbraFeatureMailPriorityEnabled }

zimbraFeatureMailSendLaterEnabled ATTRIBUTE ::= {
  WITH SYNTAX               BOOLEAN
  EQUALITY MATCHING RULE    booleanMatch
  SINGLE VALUE              TRUE
  LDAP-SYNTAX               boolean.&id
  LDAP-NAME                 {"zimbraFeatureMailSendLaterEnabled"}
  LDAP-DESC                 "whether the send later feature is enabled"
  ID                        id-at-zimbraFeatureMailSendLaterEnabled }

zimbraFeatureMailUpsellEnabled ATTRIBUTE ::= {
  WITH SYNTAX               BOOLEAN
  EQUALITY MATCHING RULE    booleanMatch
  SINGLE VALUE              TRUE
  LDAP-SYNTAX               boolean.&id
  LDAP-NAME                 {"zimbraFeatureMailUpsellEnabled"}
  LDAP-DESC                 "email upsell enabled"
  ID                        id-at-zimbraFeatureMailUpsellEnabled }

-- LDAP syntax length {256} rendered as DirectoryString{256}.
zimbraFeatureMailUpsellURL ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraFeatureMailUpsellURL"}
  LDAP-DESC                 "email upsell URL"
  ID                        id-at-zimbraFeatureMailUpsellURL }

zimbraFeatureManageSMIMECertificateEnabled ATTRIBUTE ::= {
  WITH SYNTAX               BOOLEAN
  EQUALITY MATCHING RULE    booleanMatch
  SINGLE VALUE              TRUE
  LDAP-SYNTAX               boolean.&id
  LDAP-NAME                 {"zimbraFeatureManageSMIMECertificateEnabled"}
  LDAP-DESC                 "whether to allow end user to publish and remove S/MIME certificates to their GAL entry in the web UI"
  ID                        id-at-zimbraFeatureManageSMIMECertificateEnabled }

zimbraFeatureManageZimlets ATTRIBUTE ::= {
  WITH SYNTAX               BOOLEAN
  EQUALITY MATCHING RULE    booleanMatch
  SINGLE VALUE              TRUE
  LDAP-SYNTAX               boolean.&id
  LDAP-NAME                 {"zimbraFeatureManageZimlets"}
  LDAP-DESC                 "enable end-user to manage zimlets"
  ID                        id-at-zimbraFeatureManageZimlets }

zimbraFeatureMobilePolicyEnabled ATTRIBUTE ::= {
  WITH SYNTAX               BOOLEAN
  EQUALITY MATCHING RULE    booleanMatch
  SINGLE VALUE              TRUE
  LDAP-SYNTAX               boolean.&id
  LDAP-NAME                 {"zimbraFeatureMobilePolicyEnabled"}
  LDAP-DESC                 "whether to enforce mobile policy"
  ID                        id-at-zimbraFeatureMobilePolicyEnabled }

zimbraFeatureMobileSyncEnabled ATTRIBUTE ::= {
  WITH SYNTAX               BOOLEAN
  EQUALITY MATCHING RULE    booleanMatch
  SINGLE VALUE              TRUE
  LDAP-SYNTAX               boolean.&id
  LDAP-NAME                 {"zimbraFeatureMobileSyncEnabled"}
  LDAP-DESC                 "whether to permit mobile sync"
  ID                        id-at-zimbraFeatureMobileSyncEnabled }

zimbraFeatureNewAddrBookEnabled ATTRIBUTE ::= {
  WITH SYNTAX               BOOLEAN
  EQUALITY MATCHING RULE    booleanMatch
  SINGLE VALUE              TRUE
  LDAP-SYNTAX               boolean.&id
  LDAP-NAME                 {"zimbraFeatureNewAddrBookEnabled"}
  LDAP-DESC                 "Whether user can create address books"
  ID                        id-at-zimbraFeatureNewAddrBookEnabled }

zimbraFeatureNewMailNotificationEnabled ATTRIBUTE ::= {
  WITH SYNTAX               BOOLEAN
  EQUALITY MATCHING RULE    booleanMatch
  SINGLE VALUE              TRUE
  LDAP-SYNTAX               boolean.&id
  LDAP-NAME                 {"zimbraFeatureNewMailNotificationEnabled"}
  LDAP-DESC                 "Whether new mail notification feature should be allowed for this account or in this cos"
  ID                        id-at-zimbraFeatureNewMailNotificationEnabled }

zimbraFeatureNotebookEnabled ATTRIBUTE ::= {
  WITH SYNTAX               BOOLEAN
  EQUALITY MATCHING RULE    booleanMatch
  SINGLE VALUE              TRUE
  LDAP-SYNTAX               boolean.&id
  LDAP-NAME                 {"zimbraFeatureNotebookEnabled"}
  LDAP-DESC                 "Deprecated since: 7.0.0. Deprecated per bugs 50465, 56201. Orig desc: Whether notebook feature should be allowed for this account or in this cos"
  ID                        id-at-zimbraFeatureNotebookEnabled }

zimbraFeatureOpenMailInNewWindowEnabled ATTRIBUTE ::= {
  WITH SYNTAX               BOOLEAN
  EQUALITY MATCHING RULE    booleanMatch
  SINGLE VALUE              TRUE
  LDAP-SYNTAX               boolean.&id
  LDAP-NAME                 {"zimbraFeatureOpenMailInNewWindowEnabled"}
  LDAP-DESC                 "whether or not open a new msg/conv in a new windows is allowed"
  ID                        id-at-zimbraFeatureOpenMailInNewWindowEnabled }

zimbraFeatureOptionsEnabled ATTRIBUTE ::= {
  WITH SYNTAX               BOOLEAN
  EQUALITY MATCHING RULE    booleanMatch
  SINGLE VALUE              TRUE
  LDAP-SYNTAX               boolean.&id
  LDAP-NAME                 {"zimbraFeatureOptionsEnabled"}
  LDAP-DESC                 "whether an account can modify its zimbraPref* attributes"
  ID                        id-at-zimbraFeatureOptionsEnabled }

zimbraFeatureOutOfOfficeReplyEnabled ATTRIBUTE ::= {
  WITH SYNTAX               BOOLEAN
  EQUALITY MATCHING RULE    booleanMatch
  SINGLE VALUE              TRUE
  LDAP-SYNTAX               boolean.&id
  LDAP-NAME                 {"zimbraFeatureOutOfOfficeReplyEnabled"}
  LDAP-DESC                 "Whether out of office reply feature should be allowed for this account or in this cos"
  ID                        id-at-zimbraFeatureOutOfOfficeReplyEnabled }

zimbraFeaturePeopleSearchEnabled ATTRIBUTE ::= {
  WITH SYNTAX               BOOLEAN
  EQUALITY MATCHING RULE    booleanMatch
  SINGLE VALUE              TRUE
  LDAP-SYNTAX               boolean.&id
  LDAP-NAME                 {"zimbraFeaturePeopleSearchEnabled"}
  LDAP-DESC                 "Deprecated since: 8.0.0. Deprecated per bug 56924. Orig desc: whether people search feature is enabled"
  ID                        id-at-zimbraFeaturePeopleSearchEnabled }

zimbraFeaturePop3DataSourceEnabled ATTRIBUTE ::= {
  WITH SYNTAX               BOOLEAN
  EQUALITY MATCHING RULE    booleanMatch
  SINGLE VALUE              TRUE
  LDAP-SYNTAX               boolean.&id
  LDAP-NAME                 {"zimbraFeaturePop3DataSourceEnabled"}
  LDAP-DESC                 "whether user is allowed to retrieve mail from an external POP3 data source"
  ID                        id-at-zimbraFeaturePop3DataSourceEnabled }

zimbraFeaturePortalEnabled ATTRIBUTE ::= {
  WITH SYNTAX               BOOLEAN
  EQUALITY MATCHING RULE    booleanMatch
  SINGLE VALUE              TRUE
  LDAP-SYNTAX               boolean.&id
  LDAP-NAME                 {"zimbraFeaturePortalEnabled"}
  LDAP-DESC                 "portal features"
  ID                        id-at-zimbraFeaturePortalEnabled }

zimbraFeaturePriorityInboxEnabled ATTRIBUTE ::= {
  WITH SYNTAX               BOOLEAN
  EQUALITY MATCHING RULE    booleanMatch
  SINGLE VALUE              TRUE
  LDAP-SYNTAX               boolean.&id
  LDAP-NAME                 {"zimbraFeaturePriorityInboxEnabled"}
  LDAP-DESC                 "whether priority inbox feature is enabled"
  ID                        id-at-zimbraFeaturePriorityInboxEnabled }

zimbraFeatureReadReceiptsEnabled ATTRIBUTE ::= {
  WITH SYNTAX               BOOLEAN
  EQUALITY MATCHING RULE    booleanMatch
  SINGLE VALUE              TRUE
  LDAP-SYNTAX               boolean.&id
  LDAP-NAME                 {"zimbraFeatureReadReceiptsEnabled"}
  LDAP-DESC                 "whether the web UI shows UI elements related to read receipts"
  ID                        id-at-zimbraFeatureReadReceiptsEnabled }

zimbraFeatureSMIMEEnabled ATTRIBUTE ::= {
  WITH SYNTAX               BOOLEAN
  EQUALITY MATCHING RULE    booleanMatch
  SINGLE VALUE              TRUE
  LDAP-SYNTAX               boolean.&id
  LDAP-NAME                 {"zimbraFeatureSMIMEEnabled"}
  LDAP-DESC                 "whether S/MIME feature is enabled. Note: SMIME is a Network feature, this attribute is effective only if SMIME is permitted by license."
  ID                        id-at-zimbraFeatureSMIMEEnabled }

zimbraFeatureSavedSearchesEnabled ATTRIBUTE ::= {
  WITH SYNTAX               BOOLEAN
  EQUALITY MATCHING RULE    booleanMatch
  SINGLE VALUE              TRUE
  LDAP-SYNTAX               boolean.&id
  LDAP-NAME                 {"zimbraFeatureSavedSearchesEnabled"}
  LDAP-DESC                 "saved search feature"
  ID                        id-at-zimbraFeatureSavedSearchesEnabled }

zimbraFeatureSharingEnabled ATTRIBUTE ::= {
  WITH SYNTAX               BOOLEAN
  EQUALITY MATCHING RULE    booleanMatch
  SINGLE VALUE              TRUE
  LDAP-SYNTAX               boolean.&id
  LDAP-NAME                 {"zimbraFeatureSharingEnabled"}
  LDAP-DESC                 "enabled sharing"
  ID                        id-at-zimbraFeatureSharingEnabled }

zimbraFeatureShortcutAliasesEnabled ATTRIBUTE ::= {
  WITH SYNTAX               BOOLEAN
  EQUALITY MATCHING RULE    booleanMatch
  SINGLE VALUE              TRUE
  LDAP-SYNTAX               boolean.&id
  LDAP-NAME                 {"zimbraFeatureShortcutAliasesEnabled"}
  LDAP-DESC                 "Deprecated since: 6.0.0_GA. deprecated. Orig desc: keyboard shortcuts aliases features"
  ID                        id-at-zimbraFeatureShortcutAliasesEnabled }

zimbraFeatureSignaturesEnabled ATTRIBUTE ::= {
  WITH SYNTAX               BOOLEAN
  EQUALITY MATCHING RULE    booleanMatch
  SINGLE VALUE              TRUE
  LDAP-SYNTAX               boolean.&id
  LDAP-NAME                 {"zimbraFeatureSignaturesEnabled"}
  LDAP-DESC                 "whether to allow use of signature feature"
  ID                        id-at-zimbraFeatureSignaturesEnabled }

zimbraFeatureSkinChangeEnabled ATTRIBUTE ::= {
  WITH SYNTAX               BOOLEAN
  EQUALITY MATCHING RULE    booleanMatch
  SINGLE VALUE              TRUE
  LDAP-SYNTAX               boolean.&id
  LDAP-NAME                 {"zimbraFeatureSkinChangeEnabled"}
  LDAP-DESC                 "Whether changing skin is allowed for this account or in this cos"
  ID                        id-at-zimbraFeatureSkinChangeEnabled }

zimbraFeatureSocialEnabled ATTRIBUTE ::= {
  WITH SYNTAX               BOOLEAN
  EQUALITY MATCHING RULE    booleanMatch
  SINGLE VALUE              TRUE
  LDAP-SYNTAX               boolean.&id
  LDAP-NAME                 {"zimbraFeatureSocialEnabled"}
  LDAP-DESC                 "internal social features"
  ID                        id-at-zimbraFeatureSocialEnabled }

zimbraFeatureSocialExternalEnabled ATTRIBUTE ::= {
  WITH SYNTAX               BOOLEAN
  EQUALITY MATCHING RULE    booleanMatch
  SINGLE VALUE              TRUE
  LDAP-SYNTAX               boolean.&id
  LDAP-NAME                 {"zimbraFeatureSocialExternalEnabled"}
  LDAP-DESC                 "external social features"
  ID                        id-at-zimbraFeatureSocialExternalEnabled }

zimbraFeatureSocialExternalURL ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraFeatureSocialExternalURL"}
  LDAP-DESC                 "external social URL"
  ID                        id-at-zimbraFeatureSocialExternalURL }

-- LDAP syntax length {32} rendered as DirectoryString{32}.
zimbraFeatureSocialFiltersEnabled ATTRIBUTE ::= {
  WITH SYNTAX               DirectoryString{32}
  EQUALITY MATCHING RULE    caseIgnoreMatch
  SUBSTRINGS MATCHING RULE  caseIgnoreSubstringsMatch
  LDAP-SYNTAX               directoryString.&id
  LDAP-NAME                 {"zimbraFeatureSocialFiltersEnabled"}
  LDAP-DESC                 "message social filters enabled in the web client UI"
  ID                        id-at-zimbraFeatureSocialFiltersEnabled }

zimbraFeatureSocialName ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraFeatureSocialName"}
  LDAP-DESC                 "social tab name"
  ID                        id-at-zimbraFeatureSocialName }

zimbraFeatureSocialcastEnabled ATTRIBUTE ::= {
  WITH SYNTAX               BOOLEAN
  EQUALITY MATCHING RULE    booleanMatch
  SINGLE VALUE              TRUE
  LDAP-SYNTAX               boolean.&id
  LDAP-NAME                 {"zimbraFeatureSocialcastEnabled"}
  LDAP-DESC                 "whether Socialcast integration is enabled in the web client"
  ID                        id-at-zimbraFeatureSocialcastEnabled }

zimbraFeatureTaggingEnabled ATTRIBUTE ::= {
  WITH SYNTAX               BOOLEAN
  EQUALITY MATCHING RULE    booleanMatch
  SINGLE VALUE              TRUE
  LDAP-SYNTAX               boolean.&id
  LDAP-NAME                 {"zimbraFeatureTaggingEnabled"}
  LDAP-DESC                 "tagging feature"
  ID                        id-at-zimbraFeatureTaggingEnabled }

zimbraFeatureTasksEnabled ATTRIBUTE ::= {
  WITH SYNTAX               BOOLEAN
  EQUALITY MATCHING RULE    booleanMatch
  SINGLE VALUE              TRUE
  LDAP-SYNTAX               boolean.&id
  LDAP-NAME                 {"zimbraFeatureTasksEnabled"}
  LDAP-DESC                 "whether to allow use of tasks feature"
  ID                        id-at-zimbraFeatureTasksEnabled }

zimbraFeatureTouchClientEnabled ATTRIBUTE ::= {
  WITH SYNTAX               BOOLEAN
  EQUALITY MATCHING RULE    booleanMatch
  SINGLE VALUE              TRUE
  LDAP-SYNTAX               boolean.&id
  LDAP-NAME                 {"zimbraFeatureTouchClientEnabled"}
  LDAP-DESC                 "Whether to allow a user to access touch client"
  ID                        id-at-zimbraFeatureTouchClientEnabled }

zimbraFeatureViewInHtmlEnabled ATTRIBUTE ::= {
  WITH SYNTAX               BOOLEAN
  EQUALITY MATCHING RULE    booleanMatch
  SINGLE VALUE              TRUE
  LDAP-SYNTAX               boolean.&id
  LDAP-NAME                 {"zimbraFeatureViewInHtmlEnabled"}
  LDAP-DESC                 "option to view attachments in html"
  ID                        id-at-zimbraFeatureViewInHtmlEnabled }

zimbraFeatureVoiceChangePinEnabled ATTRIBUTE ::= {
  WITH SYNTAX               BOOLEAN
  EQUALITY MATCHING RULE    booleanMatch
  SINGLE VALUE              TRUE
  LDAP-SYNTAX               boolean.&id
  LDAP-NAME                 {"zimbraFeatureVoiceChangePinEnabled"}
  LDAP-DESC                 "whether or not changing voicemail pin is enabled"
  ID                        id-at-zimbraFeatureVoiceChangePinEnabled }

zimbraFeatureVoiceEnabled ATTRIBUTE ::= {
  WITH SYNTAX               BOOLEAN
  EQUALITY MATCHING RULE    booleanMatch
  SINGLE VALUE              TRUE
  LDAP-SYNTAX               boolean.&id
  LDAP-NAME                 {"zimbraFeatureVoiceEnabled"}
  LDAP-DESC                 "Voicemail features enabled"
  ID                        id-at-zimbraFeatureVoiceEnabled }

zimbraFeatureVoiceUpsellEnabled ATTRIBUTE ::= {
  WITH SYNTAX               BOOLEAN
  EQUALITY MATCHING RULE    booleanMatch
  SINGLE VALUE              TRUE
  LDAP-SYNTAX               boolean.&id
  LDAP-NAME                 {"zimbraFeatureVoiceUpsellEnabled"}
  LDAP-DESC                 "voice upsell enabled"
  ID                        id-at-zimbraFeatureVoiceUpsellEnabled }

-- LDAP syntax length {256} rendered as DirectoryString{256}.
zimbraFeatureVoiceUpsellURL ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraFeatureVoiceUpsellURL"}
  LDAP-DESC                 "voice upsell URL"
  ID                        id-at-zimbraFeatureVoiceUpsellURL }

zimbraFeatureWebClientOfflineAccessEnabled ATTRIBUTE ::= {
  WITH SYNTAX               BOOLEAN
  EQUALITY MATCHING RULE    booleanMatch
  SINGLE VALUE              TRUE
  LDAP-SYNTAX               boolean.&id
  LDAP-NAME                 {"zimbraFeatureWebClientOfflineAccessEnabled"}
  LDAP-DESC                 "admin setting to enable/disable the web client offline access feature"
  ID                        id-at-zimbraFeatureWebClientOfflineAccessEnabled }

zimbraFeatureWebSearchEnabled ATTRIBUTE ::= {
  WITH SYNTAX               BOOLEAN
  EQUALITY MATCHING RULE    booleanMatch
  SINGLE VALUE              TRUE
  LDAP-SYNTAX               boolean.&id
  LDAP-NAME                 {"zimbraFeatureWebSearchEnabled"}
  LDAP-DESC                 "Deprecated since: 6.0.0_GA. deprecated per bug 40170. Orig desc: whether web search feature is enabled"
  ID                        id-at-zimbraFeatureWebSearchEnabled }

zimbraFeatureZimbraAssistantEnabled ATTRIBUTE ::= {
  WITH SYNTAX               BOOLEAN
  EQUALITY MATCHING RULE    booleanMatch
  SINGLE VALUE              TRUE
  LDAP-SYNTAX               boolean.&id
  LDAP-NAME                 {"zimbraFeatureZimbraAssistantEnabled"}
  LDAP-DESC                 "Zimbra Assistant enabled"
  ID                        id-at-zimbraFeatureZimbraAssistantEnabled }

zimbraFileAndroidCrashReportingEnabled ATTRIBUTE ::= {
  WITH SYNTAX               BOOLEAN
  EQUALITY MATCHING RULE    booleanMatch
  SINGLE VALUE              TRUE
  LDAP-SYNTAX               boolean.&id
  LDAP-NAME                 {"zimbraFileAndroidCrashReportingEnabled"}
  LDAP-DESC                 "whether crash reporting is enabled in the Android client"
  ID                        id-at-zimbraFileAndroidCrashReportingEnabled }

zimbraFileDeletionNotificationBody ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraFileDeletionNotificationBody"}
  LDAP-DESC                 "template for constructing the body of a file deletion warning message"
  ID                        id-at-zimbraFileDeletionNotificationBody }

zimbraFileDeletionNotificationSubject ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraFileDeletionNotificationSubject"}
  LDAP-DESC                 "template for constructing the subject of a file deletion warning message"
  ID                        id-at-zimbraFileDeletionNotificationSubject }

zimbraFileExpirationWarningBody ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraFileExpirationWarningBody"}
  LDAP-DESC                 "template for constructing the body of a file expiration warning message"
  ID                        id-at-zimbraFileExpirationWarningBody }

zimbraFileExpirationWarningSubject ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraFileExpirationWarningSubject"}
  LDAP-DESC                 "template for constructing the subject of a file expiration warning message"
  ID                        id-at-zimbraFileExpirationWarningSubject }

zimbraFileExpirationWarningThreshold ATTRIBUTE ::= {
  WITH SYNTAX               IA5String(SIZE (1..32))
  EQUALITY MATCHING RULE    caseIgnoreIA5Match
  SINGLE VALUE              TRUE
  LDAP-SYNTAX               ia5String.&id
  LDAP-NAME                 {"zimbraFileExpirationWarningThreshold"}
  LDAP-DESC                 "Period of inactivity after which file owner receives a deletion warning email. Must be in valid duration format: {digits}{time-unit}. digits: 0-9, time-unit: [hmsd]|ms. h - hours, m - minutes, s - seconds, d - days, ms - milliseconds. If time unit is not specified, the default is s(seconds)."
  ID                        id-at-zimbraFileExpirationWarningThreshold }

zimbraFileExternalShareLifetime ATTRIBUTE ::= {
  WITH SYNTAX               IA5String(SIZE (1..32))
  EQUALITY MATCHING RULE    caseIgnoreIA5Match
  SINGLE VALUE              TRUE
  LDAP-SYNTAX               ia5String.&id
  LDAP-NAME                 {"zimbraFileExternalShareLifetime"}
  LDAP-DESC                 "Maximum allowed lifetime of file shares to external users. A value of 0 indicates that there's no limit on an external file share's lifetime. . Must be in valid duration format: {digits}{time-unit}. digits: 0-9, time-unit: [hmsd]|ms. h - hours, m - minutes, s - seconds, d - days, ms - milliseconds. If time unit is not specified, the default is s(seconds)."
  ID                        id-at-zimbraFileExternalShareLifetime }

zimbraFileIOSCrashReportingEnabled ATTRIBUTE ::= {
  WITH SYNTAX               BOOLEAN
  EQUALITY MATCHING RULE    booleanMatch
  SINGLE VALUE              TRUE
  LDAP-SYNTAX               boolean.&id
  LDAP-NAME                 {"zimbraFileIOSCrashReportingEnabled"}
  LDAP-DESC                 "whether crash reporting is enabled in the IOS client"
  ID                        id-at-zimbraFileIOSCrashReportingEnabled }

zimbraFileLifetime ATTRIBUTE ::= {
  WITH SYNTAX               IA5String(SIZE (1..32))
  EQUALITY MATCHING RULE    caseIgnoreIA5Match
  SINGLE VALUE              TRUE
  LDAP-SYNTAX               ia5String.&id
  LDAP-NAME                 {"zimbraFileLifetime"}
  LDAP-DESC                 "Period of inactivity after which a file gets deleted. Must be in valid duration format: {digits}{time-unit}. digits: 0-9, time-unit: [hmsd]|ms. h - hours, m - minutes, s - seconds, d - days, ms - milliseconds. If time unit is not specified, the default is s(seconds)."
  ID                        id-at-zimbraFileLifetime }

zimbraFilePreviewMaxSize ATTRIBUTE ::= {
  WITH SYNTAX               INTEGER
  EQUALITY MATCHING RULE    integerMatch
  SINGLE VALUE              TRUE
  LDAP-SYNTAX               integer.&id
  LDAP-NAME                 {"zimbraFilePreviewMaxSize"}
  LDAP-DESC                 "Maximum size in bytes for file preview in web client"
  ID                        id-at-zimbraFilePreviewMaxSize }

zimbraFilePublicShareLifetime ATTRIBUTE ::= {
  WITH SYNTAX               IA5String(SIZE (1..32))
  EQUALITY MATCHING RULE    caseIgnoreIA5Match
  SINGLE VALUE              TRUE
  LDAP-SYNTAX               ia5String.&id
  LDAP-NAME                 {"zimbraFilePublicShareLifetime"}
  LDAP-DESC                 "Maximum allowed lifetime of public file shares. A value of 0 indicates that there's no limit on a public file share's lifetime. . Must be in valid duration format: {digits}{time-unit}. digits: 0-9, time-unit: [hmsd]|ms. h - hours, m - minutes, s - seconds, d - days, ms - milliseconds. If time unit is not specified, the default is s(seconds)."
  ID                        id-at-zimbraFilePublicShareLifetime }

zimbraFileShareLifetime ATTRIBUTE ::= {
  WITH SYNTAX               IA5String(SIZE (1..32))
  EQUALITY MATCHING RULE    caseIgnoreIA5Match
  SINGLE VALUE              TRUE
  LDAP-SYNTAX               ia5String.&id
  LDAP-NAME                 {"zimbraFileShareLifetime"}
  LDAP-DESC                 "Maximum allowed lifetime of file shares to internal users or groups. A value of 0 indicates that there's no limit on an internal file share's lifetime. . Must be in valid duration format: {digits}{time-unit}. digits: 0-9, time-unit: [hmsd]|ms. h - hours, m - minutes, s - seconds, d - days, ms - milliseconds. If time unit is not specified, the default is s(seconds)."
  ID                        id-at-zimbraFileShareLifetime }

zimbraFileUploadMaxSize ATTRIBUTE ::= {
  WITH SYNTAX               INTEGER
  EQUALITY MATCHING RULE    integerMatch
  SINGLE VALUE              TRUE
  LDAP-SYNTAX               integer.&id
  LDAP-NAME                 {"zimbraFileUploadMaxSize"}
  LDAP-DESC                 "Maximum size in bytes for file uploads"
  ID                        id-at-zimbraFileUploadMaxSize }

zimbraFileUploadMaxSizePerFile ATTRIBUTE ::= {
  WITH SYNTAX               INTEGER
  EQUALITY MATCHING RULE    integerMatch
  SINGLE VALUE              TRUE
  LDAP-SYNTAX               integer.&id
  LDAP-NAME                 {"zimbraFileUploadMaxSizePerFile"}
  LDAP-DESC                 "Maximum size in bytes for each attachment."
  ID                        id-at-zimbraFileUploadMaxSizePerFile }

zimbraFileVersionLifetime ATTRIBUTE ::= {
  WITH SYNTAX               IA5String(SIZE (1..32))
  EQUALITY MATCHING RULE    caseIgnoreIA5Match
  SINGLE VALUE              TRUE
  LDAP-SYNTAX               ia5String.&id
  LDAP-NAME                 {"zimbraFileVersionLifetime"}
  LDAP-DESC                 "how long a file version is kept around. Must be in valid duration format: {digits}{time-unit}. digits: 0-9, time-unit: [hmsd]|ms. h - hours, m - minutes, s - seconds, d - days, ms - milliseconds. If time unit is not specified, the default is s(seconds)."
  ID                        id-at-zimbraFileVersionLifetime }

zimbraFileVersioningEnabled ATTRIBUTE ::= {
  WITH SYNTAX               BOOLEAN
  EQUALITY MATCHING RULE    booleanMatch
  SINGLE VALUE              TRUE
  LDAP-SYNTAX               boolean.&id
  LDAP-NAME                 {"zimbraFileVersioningEnabled"}
  LDAP-DESC                 "whether file versioning is enabled"
  ID                        id-at-zimbraFileVersioningEnabled }

zimbraFilterBatchSize ATTRIBUTE ::= {
  WITH SYNTAX               INTEGER
  EQUALITY MATCHING RULE    integerMatch
  SINGLE VALUE              TRUE
  LDAP-SYNTAX               integer.&id
  LDAP-NAME                 {"zimbraFilterBatchSize"}
  LDAP-DESC                 "Maximum number of messages that can be processed in a single ApplyFilterRules operation."
  ID                        id-at-zimbraFilterBatchSize }

zimbraFilterSleepInterval ATTRIBUTE ::= {
  WITH SYNTAX               IA5String(SIZE (1..32))
  EQUALITY MATCHING RULE    caseIgnoreIA5Match
  SINGLE VALUE              TRUE
  LDAP-SYNTAX               ia5String.&id
  LDAP-NAME                 {"zimbraFilterSleepInterval"}
  LDAP-DESC                 "The amount of time to sleep between every two messages during ApplyFilterRules. Increasing this value will even out server load at the expense of slowing down the operation. . Must be in valid duration format: {digits}{time-unit}. digits: 0-9, time-unit: [hmsd]|ms. h - hours, m - minutes, s - seconds, d - days, ms - milliseconds. If time unit is not specified, the default is s(seconds)."
  ID                        id-at-zimbraFilterSleepInterval }

zimbraForceClearCookies ATTRIBUTE ::= {
  WITH SYNTAX               BOOLEAN
  EQUALITY MATCHING RULE    booleanMatch
  SINGLE VALUE              TRUE
  LDAP-SYNTAX               boolean.&id
  LDAP-NAME                 {"zimbraForceClearCookies"}
  LDAP-DESC                 "Whether to force clear zimbra auth cookies when SOAP session ends (i.e. force logout on browser tab close)"
  ID                        id-at-zimbraForceClearCookies }

zimbraForeignName ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraForeignName"}
  LDAP-DESC                 "foreign name for mapping an external name to a zimbra domain on domain level, it is in the format of {application}:{foreign name}"
  ID                        id-at-zimbraForeignName }

zimbraForeignNameHandler ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraForeignNameHandler"}
  LDAP-DESC                 "handler for foreign name mapping, it is in the format of {application}:{class name}[:{params}]"
  ID                        id-at-zimbraForeignNameHandler }

-- LDAP syntax length {256} rendered as DirectoryString{256}.
zimbraForeignPrincipal ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraForeignPrincipal"}
  LDAP-DESC                 "mapping to foreign principal identifier"
  ID                        id-at-zimbraForeignPrincipal }

-- LDAP syntax length {256} rendered as DirectoryString{256}.
zimbraFreebusyExchangeAuthPassword ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraFreebusyExchangeAuthPassword"}
  LDAP-DESC                 "Exchange user password for free/busy lookup and propagation"
  ID                        id-at-zimbraFreebusyExchangeAuthPassword }

-- LDAP syntax length {32} rendered as DirectoryString{32}.
zimbraFreebusyExchangeAuthScheme ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraFreebusyExchangeAuthScheme"}
  LDAP-DESC                 "auth scheme to use"
  ID                        id-at-zimbraFreebusyExchangeAuthScheme }

-- LDAP syntax length {256} rendered as DirectoryString{256}.
zimbraFreebusyExchangeAuthUsername ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraFreebusyExchangeAuthUsername"}
  LDAP-DESC                 "Exchange username for free/busy lookup and propagation"
  ID                        id-at-zimbraFreebusyExchangeAuthUsername }

zimbraFreebusyExchangeCachedInterval ATTRIBUTE ::= {
  WITH SYNTAX               IA5String(SIZE (1..32))
  EQUALITY MATCHING RULE    caseIgnoreIA5Match
  SINGLE VALUE              TRUE
  LDAP-SYNTAX               ia5String.&id
  LDAP-NAME                 {"zimbraFreebusyExchangeCachedInterval"}
  LDAP-DESC                 "The duration of f/b block pushed to Exchange server.. Must be in valid duration format: {digits}{time-unit}. digits: 0-9, time-unit: [hmsd]|ms. h - hours, m - minutes, s - seconds, d - days, ms - milliseconds. If time unit is not specified, the default is s(seconds)."
  ID                        id-at-zimbraFreebusyExchangeCachedInterval }

zimbraFreebusyExchangeCachedIntervalStart ATTRIBUTE ::= {
  WITH SYNTAX               IA5String(SIZE (1..32))
  EQUALITY MATCHING RULE    caseIgnoreIA5Match
  SINGLE VALUE              TRUE
  LDAP-SYNTAX               ia5String.&id
  LDAP-NAME                 {"zimbraFreebusyExchangeCachedIntervalStart"}
  LDAP-DESC                 "The value of duration is used to indicate the start date (in the past relative to today) of the f/b interval pushed to Exchange server.. Must be in valid duration format: {digits}{time-unit}. digits: 0-9, time-unit: [hmsd]|ms. h - hours, m - minutes, s - seconds, d - days, ms - milliseconds. If time unit is not specified, the default is s(seconds)."
  ID                        id-at-zimbraFreebusyExchangeCachedIntervalStart }

-- LDAP syntax length {32} rendered as DirectoryString{32}.
zimbraFreebusyExchangeServerType ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraFreebusyExchangeServerType"}
  LDAP-DESC                 "Can be set to either webdav for Exchange 2007 or older, or ews for 2010 and newer"
  ID                        id-at-zimbraFreebusyExchangeServerType }

-- LDAP syntax length {256} rendered as DirectoryString{256}.
zimbraFreebusyExchangeURL ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraFreebusyExchangeURL"}
  LDAP-DESC                 "URL to Exchange server for free/busy lookup and propagation"
  ID                        id-at-zimbraFreebusyExchangeURL }

-- LDAP syntax length {256} rendered as DirectoryString{256}.
zimbraFreebusyExchangeUserOrg ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraFreebusyExchangeUserOrg"}
  LDAP-DESC                 "O and OU used in legacyExchangeDN attribute"
  ID                        id-at-zimbraFreebusyExchangeUserOrg }

-- LDAP syntax length {256} rendered as DirectoryString{256}.
zimbraFreebusyExternalZimbraURL ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraFreebusyExternalZimbraURL"}
  LDAP-DESC                 "URLs of external Zimbra servers for free/busy lookup in the form of http[s]://[user:pass@]host:port"
  ID                        id-at-zimbraFreebusyExternalZimbraURL }

zimbraFreebusyLocalMailboxNotActive ATTRIBUTE ::= {
  WITH SYNTAX               BOOLEAN
  EQUALITY MATCHING RULE    booleanMatch
  SINGLE VALUE              TRUE
  LDAP-SYNTAX               boolean.&id
  LDAP-NAME                 {"zimbraFreebusyLocalMailboxNotActive"}
  LDAP-DESC                 "when set to TRUE, free/busy for the account is not calculated from local mailbox."
  ID                        id-at-zimbraFreebusyLocalMailboxNotActive }

zimbraFreebusyPropagationRetryInterval ATTRIBUTE ::= {
  WITH SYNTAX               IA5String(SIZE (1..32))
  EQUALITY MATCHING RULE    caseIgnoreIA5Match
  SINGLE VALUE              TRUE
  LDAP-SYNTAX               ia5String.&id
  LDAP-NAME                 {"zimbraFreebusyPropagationRetryInterval"}
  LDAP-DESC                 "The interval to wait when the server encounters problems while propagating Zimbra users free/busy information to external provider such as Exchange. . Must be in valid duration format: {digits}{time-unit}. digits: 0-9, time-unit: [hmsd]|ms. h - hours, m - minutes, s - seconds, d - days, ms - milliseconds. If time unit is not specified, the default is s(seconds)."
  ID                        id-at-zimbraFreebusyPropagationRetryInterval }

-- LDAP syntax length {256} rendered as DirectoryString{256}.
zimbraGalAccountId ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraGalAccountId"}
  LDAP-DESC                 "zimbraId of GAL sync accounts"
  ID                        id-at-zimbraGalAccountId }

zimbraGalAlwaysIncludeLocalCalendarResources ATTRIBUTE ::= {
  WITH SYNTAX               BOOLEAN
  EQUALITY MATCHING RULE    booleanMatch
  SINGLE VALUE              TRUE
  LDAP-SYNTAX               boolean.&id
  LDAP-NAME                 {"zimbraGalAlwaysIncludeLocalCalendarResources"}
  LDAP-DESC                 "When set to TRUE, GAL search will always include local calendar resources regardless of zimbraGalMode."
  ID                        id-at-zimbraGalAlwaysIncludeLocalCalendarResources }

-- LDAP syntax length {4096} rendered as DirectoryString{4096}.
zimbraGalAutoCompleteLdapFilter ATTRIBUTE ::= {
  WITH SYNTAX               DirectoryString{4096}
  EQUALITY MATCHING RULE    caseIgnoreMatch
  SUBSTRINGS MATCHING RULE  caseIgnoreSubstringsMatch
  SINGLE VALUE              TRUE
  LDAP-SYNTAX               directoryString.&id
  LDAP-NAME                 {"zimbraGalAutoCompleteLdapFilter"}
  LDAP-DESC                 "LDAP search filter for external GAL auto-complete queries"
  ID                        id-at-zimbraGalAutoCompleteLdapFilter }

zimbraGalDefinitionLastModifiedTime ATTRIBUTE ::= {
  WITH SYNTAX               GeneralizedTime
  EQUALITY MATCHING RULE    generalizedTimeMatch
  ORDERING MATCHING RULE    generalizedTimeOrderingMatch
  SINGLE VALUE              TRUE
  LDAP-SYNTAX               generalizedTime.&id
  LDAP-NAME                 {"zimbraGalDefinitionLastModifiedTime"}
  LDAP-DESC                 "the time at which GAL definition is last modified."
  ID                        id-at-zimbraGalDefinitionLastModifiedTime }

zimbraGalGroupIndicatorEnabled ATTRIBUTE ::= {
  WITH SYNTAX               BOOLEAN
  EQUALITY MATCHING RULE    booleanMatch
  SINGLE VALUE              TRUE
  LDAP-SYNTAX               boolean.&id
  LDAP-NAME                 {"zimbraGalGroupIndicatorEnabled"}
  LDAP-DESC                 "whether to indicate if an email address on a message is a GAL group"
  ID                        id-at-zimbraGalGroupIndicatorEnabled }

-- LDAP syntax length {256} rendered as DirectoryString{256}.
zimbraGalInternalSearchBase ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraGalInternalSearchBase"}
  LDAP-DESC                 "LDAP search base for internal GAL queries (special values: ""ROOT"" for top, ""DOMAIN"" for domain only, ""SUBDOMAINS"" for domain and subdomains)"
  ID                        id-at-zimbraGalInternalSearchBase }

zimbraGalLastFailedSyncTimestamp ATTRIBUTE ::= {
  WITH SYNTAX               GeneralizedTime
  EQUALITY MATCHING RULE    generalizedTimeMatch
  ORDERING MATCHING RULE    generalizedTimeOrderingMatch
  SINGLE VALUE              TRUE
  LDAP-SYNTAX               generalizedTime.&id
  LDAP-NAME                 {"zimbraGalLastFailedSyncTimestamp"}
  LDAP-DESC                 "the last time at which a syncing attempt failed"
  ID                        id-at-zimbraGalLastFailedSyncTimestamp }

zimbraGalLastSuccessfulSyncTimestamp ATTRIBUTE ::= {
  WITH SYNTAX               GeneralizedTime
  EQUALITY MATCHING RULE    generalizedTimeMatch
  ORDERING MATCHING RULE    generalizedTimeOrderingMatch
  SINGLE VALUE              TRUE
  LDAP-SYNTAX               generalizedTime.&id
  LDAP-NAME                 {"zimbraGalLastSuccessfulSyncTimestamp"}
  LDAP-DESC                 "the last time at which this GAL data source was successfully synced"
  ID                        id-at-zimbraGalLastSuccessfulSyncTimestamp }

-- LDAP syntax length {4096} rendered as DirectoryString{4096}.
zimbraGalLdapAttrMap ATTRIBUTE ::= {
  WITH SYNTAX               DirectoryString{4096}
  EQUALITY MATCHING RULE    caseIgnoreMatch
  SUBSTRINGS MATCHING RULE  caseIgnoreSubstringsMatch
  LDAP-SYNTAX               directoryString.&id
  LDAP-NAME                 {"zimbraGalLdapAttrMap"}
  LDAP-DESC                 "LDAP Gal attribute to contact attr mapping"
  ID                        id-at-zimbraGalLdapAttrMap }

-- LDAP syntax length {32} rendered as DirectoryString{32}.
zimbraGalLdapAuthMech ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraGalLdapAuthMech"}
  LDAP-DESC                 "external LDAP GAL authentication mechanism none: anonymous binding simple: zimbraGalLdapBindDn and zimbraGalLdapBindPassword has to be set kerberos5: zimbraGalLdapKerberos5Principal and zimbraGalLdapKerberos5Keytab has to be set"
  ID                        id-at-zimbraGalLdapAuthMech }

-- LDAP syntax length {256} rendered as DirectoryString{256}.
zimbraGalLdapBindDn ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraGalLdapBindDn"}
  LDAP-DESC                 "LDAP bind dn for external GAL queries"
  ID                        id-at-zimbraGalLdapBindDn }

-- LDAP syntax length {256} rendered as DirectoryString{256}.
zimbraGalLdapBindPassword ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraGalLdapBindPassword"}
  LDAP-DESC                 "LDAP bind password for external GAL queries"
  ID                        id-at-zimbraGalLdapBindPassword }

-- LDAP syntax length {4096} rendered as DirectoryString{4096}.
zimbraGalLdapFilter ATTRIBUTE ::= {
  WITH SYNTAX               DirectoryString{4096}
  EQUALITY MATCHING RULE    caseIgnoreMatch
  SUBSTRINGS MATCHING RULE  caseIgnoreSubstringsMatch
  SINGLE VALUE              TRUE
  LDAP-SYNTAX               directoryString.&id
  LDAP-NAME                 {"zimbraGalLdapFilter"}
  LDAP-DESC                 "LDAP search filter for external GAL search queries"
  ID                        id-at-zimbraGalLdapFilter }

-- LDAP syntax length {4096} rendered as DirectoryString{4096}.
zimbraGalLdapFilterDef ATTRIBUTE ::= {
  WITH SYNTAX               DirectoryString{4096}
  EQUALITY MATCHING RULE    caseIgnoreMatch
  SUBSTRINGS MATCHING RULE  caseIgnoreSubstringsMatch
  LDAP-SYNTAX               directoryString.&id
  LDAP-NAME                 {"zimbraGalLdapFilterDef"}
  LDAP-DESC                 "LDAP search filter definitions for GAL queries"
  ID                        id-at-zimbraGalLdapFilterDef }

-- LDAP syntax length {1024} rendered as DirectoryString{1024}.
zimbraGalLdapGroupHandlerClass ATTRIBUTE ::= {
  WITH SYNTAX               DirectoryString{1024}
  EQUALITY MATCHING RULE    caseIgnoreMatch
  SUBSTRINGS MATCHING RULE  caseIgnoreSubstringsMatch
  SINGLE VALUE              TRUE
  LDAP-SYNTAX               directoryString.&id
  LDAP-NAME                 {"zimbraGalLdapGroupHandlerClass"}
  LDAP-DESC                 "the handler class for mapping groups from GAL source to zimbra GAL contacts for external GAL"
  ID                        id-at-zimbraGalLdapGroupHandlerClass }

-- LDAP syntax length {256} rendered as DirectoryString{256}.
zimbraGalLdapKerberos5Keytab ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraGalLdapKerberos5Keytab"}
  LDAP-DESC                 "kerberos5 keytab file path for external GAL queries"
  ID                        id-at-zimbraGalLdapKerberos5Keytab }

-- LDAP syntax length {256} rendered as DirectoryString{256}.
zimbraGalLdapKerberos5Principal ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraGalLdapKerberos5Principal"}
  LDAP-DESC                 "kerberos5 principal for external GAL queries"
  ID                        id-at-zimbraGalLdapKerberos5Principal }

zimbraGalLdapPageSize ATTRIBUTE ::= {
  WITH SYNTAX               INTEGER
  EQUALITY MATCHING RULE    integerMatch
  SINGLE VALUE              TRUE
  LDAP-SYNTAX               integer.&id
  LDAP-NAME                 {"zimbraGalLdapPageSize"}
  LDAP-DESC                 "LDAP page size for paged search control while accessing LDAP server for GAL. This applies to both Zimbra and external LDAP servers. A value of 0 means paging is not enabled."
  ID                        id-at-zimbraGalLdapPageSize }

-- LDAP syntax length {256} rendered as DirectoryString{256}.
zimbraGalLdapSearchBase ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraGalLdapSearchBase"}
  LDAP-DESC                 "LDAP search base for external GAL queries"
  ID                        id-at-zimbraGalLdapSearchBase }

zimbraGalLdapStartTlsEnabled ATTRIBUTE ::= {
  WITH SYNTAX               BOOLEAN
  EQUALITY MATCHING RULE    booleanMatch
  SINGLE VALUE              TRUE
  LDAP-SYNTAX               boolean.&id
  LDAP-NAME                 {"zimbraGalLdapStartTlsEnabled"}
  LDAP-DESC                 "whether to use startTLS for external GAL. startTLS will be used for external GAL access only if this attribute is true and zimbraGalLdapURL(or zimbraGalSyncLdapURL for sync) does not contain a ldaps URL."
  ID                        id-at-zimbraGalLdapStartTlsEnabled }

-- LDAP syntax length {256} rendered as DirectoryString{256}.
zimbraGalLdapURL ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraGalLdapURL"}
  LDAP-DESC                 "LDAP URL for external GAL queries"
  ID                        id-at-zimbraGalLdapURL }

-- LDAP syntax length {4096} rendered as DirectoryString{4096}.
zimbraGalLdapValueMap ATTRIBUTE ::= {
  WITH SYNTAX               DirectoryString{4096}
  EQUALITY MATCHING RULE    caseIgnoreMatch
  SUBSTRINGS MATCHING RULE  caseIgnoreSubstringsMatch
  LDAP-SYNTAX               directoryString.&id
  LDAP-NAME                 {"zimbraGalLdapValueMap"}
  LDAP-DESC                 "LDAP Gal attribute to contact value mapping. Each value is in the format of {gal contact filed}: {regex} {replacement}"
  ID                        id-at-zimbraGalLdapValueMap }

zimbraGalMaxResults ATTRIBUTE ::= {
  WITH SYNTAX               INTEGER
  EQUALITY MATCHING RULE    integerMatch
  SINGLE VALUE              TRUE
  LDAP-SYNTAX               integer.&id
  LDAP-NAME                 {"zimbraGalMaxResults"}
  LDAP-DESC                 "maximum number of gal entries to return from a search"
  ID                        id-at-zimbraGalMaxResults }

-- LDAP syntax length {32} rendered as DirectoryString{32}.
zimbraGalMode ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraGalMode"}
  LDAP-DESC                 "valid modes are ""zimbra"" (query internal directory only), ""ldap"" (query external directory only), or ""both"" (query internal and external directory)"
  ID                        id-at-zimbraGalMode }

-- LDAP syntax length {32} rendered as DirectoryString{32}.
zimbraGalStatus ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraGalStatus"}
  LDAP-DESC                 "GAL data source status"
  ID                        id-at-zimbraGalStatus }

zimbraGalSyncAccountBasedAutoCompleteEnabled ATTRIBUTE ::= {
  WITH SYNTAX               BOOLEAN
  EQUALITY MATCHING RULE    booleanMatch
  SINGLE VALUE              TRUE
  LDAP-SYNTAX               boolean.&id
  LDAP-NAME                 {"zimbraGalSyncAccountBasedAutoCompleteEnabled"}
  LDAP-DESC                 "whether to use gal sync account for autocomplete"
  ID                        id-at-zimbraGalSyncAccountBasedAutoCompleteEnabled }

-- LDAP syntax length {256} rendered as DirectoryString{256}.
zimbraGalSyncIgnoredAttributes ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraGalSyncIgnoredAttributes"}
  LDAP-DESC                 "List of attributes that will be ignored when determining whether a GAL contact has been modified. Any change in other attribute values will make the contact ""dirty"" and the contact will show as modified in the next GAL sync response. By default modifyTimeStamp is always included in ignored attributes. Then if the only change in GAL contact is modifyTimeStamp, the contact will not be shown as modified in the next GAL sync response from the client, thus minimizing the need to download the GAL contact again when none of the meaningful attributes have changed."
  ID                        id-at-zimbraGalSyncIgnoredAttributes }

-- LDAP syntax length {256} rendered as DirectoryString{256}.
zimbraGalSyncInternalSearchBase ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraGalSyncInternalSearchBase"}
  LDAP-DESC                 "LDAP search base for internal GAL sync (special values: ""ROOT"" for top, ""DOMAIN"" for domain only, ""SUBDOMAINS"" for domain and subdomains) If not set fallback to zimbraGalInternalSearchBase"
  ID                        id-at-zimbraGalSyncInternalSearchBase }

-- LDAP syntax length {32} rendered as DirectoryString{32}.
zimbraGalSyncLdapAuthMech ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraGalSyncLdapAuthMech"}
  LDAP-DESC                 "external LDAP GAL authentication mechanism for GAL sync none: anonymous binding simple: zimbraGalLdapBindDn and zimbraGalLdapBindPassword has to be set kerberos5: zimbraGalLdapKerberos5Principal and zimbraGalLdapKerberos5Keytab has to be set if not set fallback to zimbraGalLdapAuthMech"
  ID                        id-at-zimbraGalSyncLdapAuthMech }

-- LDAP syntax length {256} rendered as DirectoryString{256}.
zimbraGalSyncLdapBindDn ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraGalSyncLdapBindDn"}
  LDAP-DESC                 "LDAP bind dn for external GAL sync queries, if not set fallback to zimbraGalLdapBindDn"
  ID                        id-at-zimbraGalSyncLdapBindDn }

-- LDAP syntax length {256} rendered as DirectoryString{256}.
zimbraGalSyncLdapBindPassword ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraGalSyncLdapBindPassword"}
  LDAP-DESC                 "LDAP bind password for external GAL sync queries, if not set fallback to zimbraGalLdapBindPassword"
  ID                        id-at-zimbraGalSyncLdapBindPassword }

-- LDAP syntax length {4096} rendered as DirectoryString{4096}.
zimbraGalSyncLdapFilter ATTRIBUTE ::= {
  WITH SYNTAX               DirectoryString{4096}
  EQUALITY MATCHING RULE    caseIgnoreMatch
  SUBSTRINGS MATCHING RULE  caseIgnoreSubstringsMatch
  SINGLE VALUE              TRUE
  LDAP-SYNTAX               directoryString.&id
  LDAP-NAME                 {"zimbraGalSyncLdapFilter"}
  LDAP-DESC                 "LDAP search filter for external GAL sync queries, if not set fallback to zimbraGalLdapFilter"
  ID                        id-at-zimbraGalSyncLdapFilter }

-- LDAP syntax length {256} rendered as DirectoryString{256}.
zimbraGalSyncLdapKerberos5Keytab ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraGalSyncLdapKerberos5Keytab"}
  LDAP-DESC                 "kerberos5 keytab file path for external GAL sync queries, if not set fallback to zimbraGalLdapKerberos5Keytab"
  ID                        id-at-zimbraGalSyncLdapKerberos5Keytab }

-- LDAP syntax length {256} rendered as DirectoryString{256}.
zimbraGalSyncLdapKerberos5Principal ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraGalSyncLdapKerberos5Principal"}
  LDAP-DESC                 "kerberos5 principal for external GAL sync queries, if not set fallback to zimbraGalLdapKerberos5Principal"
  ID                        id-at-zimbraGalSyncLdapKerberos5Principal }

zimbraGalSyncLdapPageSize ATTRIBUTE ::= {
  WITH SYNTAX               INTEGER
  EQUALITY MATCHING RULE    integerMatch
  SINGLE VALUE              TRUE
  LDAP-SYNTAX               integer.&id
  LDAP-NAME                 {"zimbraGalSyncLdapPageSize"}
  LDAP-DESC                 "LDAP page size for paged search control while accessing LDAP server for GAL sync. This applies to both Zimbra and external LDAP servers. A value of 0 means paging is not enabled. If not set fallback to zimbraGalLdapPageSize"
  ID                        id-at-zimbraGalSyncLdapPageSize }

-- LDAP syntax length {256} rendered as DirectoryString{256}.
zimbraGalSyncLdapSearchBase ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraGalSyncLdapSearchBase"}
  LDAP-DESC                 "LDAP search base for external GAL sync queries, if not set fallback to zimbraGalLdapSearchBase"
  ID                        id-at-zimbraGalSyncLdapSearchBase }

zimbraGalSyncLdapStartTlsEnabled ATTRIBUTE ::= {
  WITH SYNTAX               BOOLEAN
  EQUALITY MATCHING RULE    booleanMatch
  SINGLE VALUE              TRUE
  LDAP-SYNTAX               boolean.&id
  LDAP-NAME                 {"zimbraGalSyncLdapStartTlsEnabled"}
  LDAP-DESC                 "whether to use startTLS for external GAL sync, if not set fallback to zimbraGalLdapStartTlsEnabled"
  ID                        id-at-zimbraGalSyncLdapStartTlsEnabled }

-- LDAP syntax length {256} rendered as DirectoryString{256}.
zimbraGalSyncLdapURL ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraGalSyncLdapURL"}
  LDAP-DESC                 "LDAP URL for external GAL sync, if not set fallback to zimbraGalLdapURL"
  ID                        id-at-zimbraGalSyncLdapURL }

zimbraGalSyncMaxConcurrentClients ATTRIBUTE ::= {
  WITH SYNTAX               INTEGER
  EQUALITY MATCHING RULE    integerMatch
  SINGLE VALUE              TRUE
  LDAP-SYNTAX               integer.&id
  LDAP-NAME                 {"zimbraGalSyncMaxConcurrentClients"}
  LDAP-DESC                 "Maximum number of concurrent GAL sync requests allowed on the system / domain."
  ID                        id-at-zimbraGalSyncMaxConcurrentClients }

-- LDAP syntax length {256} rendered as DirectoryString{256}.
zimbraGalSyncTimestampFormat ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraGalSyncTimestampFormat"}
  LDAP-DESC                 "LDAP generalized time format for external GAL sync"
  ID                        id-at-zimbraGalSyncTimestampFormat }

-- LDAP syntax length {32} rendered as DirectoryString{32}.
zimbraGalTokenizeAutoCompleteKey ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraGalTokenizeAutoCompleteKey"}
  LDAP-DESC                 "whether to tokenize key and AND or OR the tokenized queries for GAL auto complete, if not set, key is not tokenized"
  ID                        id-at-zimbraGalTokenizeAutoCompleteKey }

-- LDAP syntax length {32} rendered as DirectoryString{32}.
zimbraGalTokenizeSearchKey ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraGalTokenizeSearchKey"}
  LDAP-DESC                 "whether to tokenize key and AND or OR the tokenized queries for GAL search, if not set, key is not tokenized"
  ID                        id-at-zimbraGalTokenizeSearchKey }

-- LDAP syntax length {32} rendered as DirectoryString{32}.
zimbraGalType ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraGalType"}
  LDAP-DESC                 "type of this GAl data source. zimbra - zimbra internal GAL. ldap - external LDAP GAL."
  ID                        id-at-zimbraGalType }

-- LDAP syntax length {256} rendered as DirectoryString{256}.
zimbraGlobalConfigExtraObjectClass ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraGlobalConfigExtraObjectClass"}
  LDAP-DESC                 "Object classes added on the global config entry. Unlike other zimbra***ExtraObjectClass attributes, object classes specified in this attributes will not be automatically added to the global config entry. Extra object class on the global config entry must be added using ""zmprov mcf +objectClass {object class}"", then recorded in this attributes."
  ID                        id-at-zimbraGlobalConfigExtraObjectClass }

-- LDAP syntax length {256} rendered as DirectoryString{256}.
zimbraGroupId ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraGroupId"}
  LDAP-DESC                 "zimbraId of the main dynamic group for the dynamic group unit"
  ID                        id-at-zimbraGroupId }

-- LDAP syntax length {256} rendered as DirectoryString{256}.
zimbraHelpAdminURL ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraHelpAdminURL"}
  LDAP-DESC                 "help URL for admin"
  ID                        id-at-zimbraHelpAdminURL }

-- LDAP syntax length {256} rendered as DirectoryString{256}.
zimbraHelpAdvancedURL ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraHelpAdvancedURL"}
  LDAP-DESC                 "help URL for advanced client"
  ID                        id-at-zimbraHelpAdvancedURL }

-- LDAP syntax length {256} rendered as DirectoryString{256}.
zimbraHelpDelegatedURL ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraHelpDelegatedURL"}
  LDAP-DESC                 "help URL for delegated admin"
  ID                        id-at-zimbraHelpDelegatedURL }

-- LDAP syntax length {256} rendered as DirectoryString{256}.
zimbraHelpStandardURL ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraHelpStandardURL"}
  LDAP-DESC                 "help URL for standard client"
  ID                        id-at-zimbraHelpStandardURL }

zimbraHideInGal ATTRIBUTE ::= {
  WITH SYNTAX               BOOLEAN
  EQUALITY MATCHING RULE    booleanMatch
  SINGLE VALUE              TRUE
  LDAP-SYNTAX               boolean.&id
  LDAP-NAME                 {"zimbraHideInGal"}
  LDAP-DESC                 "hide entry in Global Address List"
  ID                        id-at-zimbraHideInGal }

zimbraHsmAge ATTRIBUTE ::= {
  WITH SYNTAX               IA5String(SIZE (1..32))
  EQUALITY MATCHING RULE    caseIgnoreIA5Match
  SINGLE VALUE              TRUE
  LDAP-SYNTAX               ia5String.&id
  LDAP-NAME                 {"zimbraHsmAge"}
  LDAP-DESC                 "Deprecated since: 6.0.0_BETA2. deprecated in favor for zimbraHsmPolicy. Orig desc: Minimum age of mail items whose filesystem data will be moved to secondary storage.. Must be in valid duration format: {digits}{time-unit}. digits: 0-9, time-unit: [hmsd]|ms. h - hours, m - minutes, s - seconds, d - days, ms - milliseconds. If time unit is not specified, the default is s(seconds)."
  ID                        id-at-zimbraHsmAge }

zimbraHsmBatchSize ATTRIBUTE ::= {
  WITH SYNTAX               INTEGER
  EQUALITY MATCHING RULE    integerMatch
  SINGLE VALUE              TRUE
  LDAP-SYNTAX               integer.&id
  LDAP-NAME                 {"zimbraHsmBatchSize"}
  LDAP-DESC                 "Maximum number of items to move during a single HSM operation. If the limit is exceeded, the HSM operation is repeated until all qualifying items are moved."
  ID                        id-at-zimbraHsmBatchSize }

zimbraHsmMovePreviousRevisions ATTRIBUTE ::= {
  WITH SYNTAX               BOOLEAN
  EQUALITY MATCHING RULE    booleanMatch
  SINGLE VALUE              TRUE
  LDAP-SYNTAX               boolean.&id
  LDAP-NAME                 {"zimbraHsmMovePreviousRevisions"}
  LDAP-DESC                 "Keep only the tip revision in the main volume, and move all the old revisions to the secondary volume. For document type mail items only, works independently of zimbraHsmPolicy."
  ID                        id-at-zimbraHsmMovePreviousRevisions }

zimbraHsmPolicy ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraHsmPolicy"}
  LDAP-DESC                 "The policy that determines which mail items get moved to secondary storage during HSM. Each value specifies a comma-separated list of item types and the search query used to select items to move. See the spec for <SearchRequest> for the complete list of item types and query.txt for the search query spec."
  ID                        id-at-zimbraHsmPolicy }

zimbraHttpCompressionEnabled ATTRIBUTE ::= {
  WITH SYNTAX               BOOLEAN
  EQUALITY MATCHING RULE    booleanMatch
  SINGLE VALUE              TRUE
  LDAP-SYNTAX               boolean.&id
  LDAP-NAME                 {"zimbraHttpCompressionEnabled"}
  LDAP-DESC                 "Whether or not to enable HTTP compression. Defaults to true."
  ID                        id-at-zimbraHttpCompressionEnabled }

zimbraHttpConnectorMaxIdleTimeMillis ATTRIBUTE ::= {
  WITH SYNTAX               INTEGER
  EQUALITY MATCHING RULE    integerMatch
  SINGLE VALUE              TRUE
  LDAP-SYNTAX               integer.&id
  LDAP-NAME                 {"zimbraHttpConnectorMaxIdleTimeMillis"}
  LDAP-DESC                 "Maximum Idle time in milli seconds for a connection. This is applied when waiting for a new request to be received on a connection; when reading the headers and content of a request; when writing the headers and content of a response."
  ID                        id-at-zimbraHttpConnectorMaxIdleTimeMillis }

zimbraHttpContextPathBasedThreadPoolBalancingFilterRules ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraHttpContextPathBasedThreadPoolBalancingFilterRules"}
  LDAP-DESC                 "Rules for governing the allocation of threads to various web contexts for the current thread pool. Sample value: /zimbra:min=10;max=40% or /zimbraAdmin:min=5"
  ID                        id-at-zimbraHttpContextPathBasedThreadPoolBalancingFilterRules }

zimbraHttpDebugHandlerEnabled ATTRIBUTE ::= {
  WITH SYNTAX               BOOLEAN
  EQUALITY MATCHING RULE    booleanMatch
  SINGLE VALUE              TRUE
  LDAP-SYNTAX               boolean.&id
  LDAP-NAME                 {"zimbraHttpDebugHandlerEnabled"}
  LDAP-DESC                 "Whether to enable http debug handler on a server"
  ID                        id-at-zimbraHttpDebugHandlerEnabled }

zimbraHttpDosFilterDelayMillis ATTRIBUTE ::= {
  WITH SYNTAX               INTEGER
  EQUALITY MATCHING RULE    integerMatch
  SINGLE VALUE              TRUE
  LDAP-SYNTAX               integer.&id
  LDAP-NAME                 {"zimbraHttpDosFilterDelayMillis"}
  LDAP-DESC                 "Delay imposed on all requests over the rate limit, before they are considered at all. -1 = Reject request, 0 = No delay, any other value = Delay in ms"
  ID                        id-at-zimbraHttpDosFilterDelayMillis }

zimbraHttpDosFilterMaxRequestsPerSec ATTRIBUTE ::= {
  WITH SYNTAX               INTEGER
  EQUALITY MATCHING RULE    integerMatch
  SINGLE VALUE              TRUE
  LDAP-SYNTAX               integer.&id
  LDAP-NAME                 {"zimbraHttpDosFilterMaxRequestsPerSec"}
  LDAP-DESC                 "Maximum number of requests from a connection per second. Requests in excess of this are throttled."
  ID                        id-at-zimbraHttpDosFilterMaxRequestsPerSec }

zimbraHttpHeaderCacheSize ATTRIBUTE ::= {
  WITH SYNTAX               INTEGER
  EQUALITY MATCHING RULE    integerMatch
  SINGLE VALUE              TRUE
  LDAP-SYNTAX               integer.&id
  LDAP-NAME                 {"zimbraHttpHeaderCacheSize"}
  LDAP-DESC                 "The maximum allowed size in bytes for a HTTP header field cache in Jetty"
  ID                        id-at-zimbraHttpHeaderCacheSize }

zimbraHttpMaxFormContentSize ATTRIBUTE ::= {
  WITH SYNTAX               INTEGER
  EQUALITY MATCHING RULE    integerMatch
  SINGLE VALUE              TRUE
  LDAP-SYNTAX               integer.&id
  LDAP-NAME                 {"zimbraHttpMaxFormContentSize"}
  LDAP-DESC                 "The maximum allowed size in bytes for a HTTP form content in Jetty. Can be set to 0 to block all web form submission"
  ID                        id-at-zimbraHttpMaxFormContentSize }

zimbraHttpNumThreads ATTRIBUTE ::= {
  WITH SYNTAX               INTEGER
  EQUALITY MATCHING RULE    integerMatch
  SINGLE VALUE              TRUE
  LDAP-SYNTAX               integer.&id
  LDAP-NAME                 {"zimbraHttpNumThreads"}
  LDAP-DESC                 "number of http handler threads"
  ID                        id-at-zimbraHttpNumThreads }

zimbraHttpOutputBufferSize ATTRIBUTE ::= {
  WITH SYNTAX               INTEGER
  EQUALITY MATCHING RULE    integerMatch
  SINGLE VALUE              TRUE
  LDAP-SYNTAX               integer.&id
  LDAP-NAME                 {"zimbraHttpOutputBufferSize"}
  LDAP-DESC                 "The size in bytes of the output buffer used to aggregate HTTP output in Jetty"
  ID                        id-at-zimbraHttpOutputBufferSize }

zimbraHttpProxyURL ATTRIBUTE ::= {
  WITH SYNTAX               IA5String(SIZE (1..512))
  EQUALITY MATCHING RULE    caseIgnoreIA5Match
  SUBSTRINGS MATCHING RULE  caseIgnoreSubstringsMatch
  LDAP-SYNTAX               ia5String.&id
  LDAP-NAME                 {"zimbraHttpProxyURL"}
  LDAP-DESC                 "external socks proxy URL to connect to when making outgoing connections (eg.Zimlet proxy, RSS/ATOM feeds, etc)"
  ID                        id-at-zimbraHttpProxyURL }

zimbraHttpRequestHeaderSize ATTRIBUTE ::= {
  WITH SYNTAX               INTEGER
  EQUALITY MATCHING RULE    integerMatch
  SINGLE VALUE              TRUE
  LDAP-SYNTAX               integer.&id
  LDAP-NAME                 {"zimbraHttpRequestHeaderSize"}
  LDAP-DESC                 "The maximum allowed size in bytes for a HTTP request header in Jetty"
  ID                        id-at-zimbraHttpRequestHeaderSize }

zimbraHttpResponseHeaderSize ATTRIBUTE ::= {
  WITH SYNTAX               INTEGER
  EQUALITY MATCHING RULE    integerMatch
  SINGLE VALUE              TRUE
  LDAP-SYNTAX               integer.&id
  LDAP-NAME                 {"zimbraHttpResponseHeaderSize"}
  LDAP-DESC                 "The maximum allowed size in bytes for a HTTP response header in Jetty"
  ID                        id-at-zimbraHttpResponseHeaderSize }

zimbraHttpSSLNumThreads ATTRIBUTE ::= {
  WITH SYNTAX               INTEGER
  EQUALITY MATCHING RULE    integerMatch
  SINGLE VALUE              TRUE
  LDAP-SYNTAX               integer.&id
  LDAP-NAME                 {"zimbraHttpSSLNumThreads"}
  LDAP-DESC                 "Deprecated since: 5.0. not applicable for jetty. Orig desc: number of https handler threads"
  ID                        id-at-zimbraHttpSSLNumThreads }

zimbraHttpThreadPoolMaxIdleTimeMillis ATTRIBUTE ::= {
  WITH SYNTAX               INTEGER
  EQUALITY MATCHING RULE    integerMatch
  SINGLE VALUE              TRUE
  LDAP-SYNTAX               integer.&id
  LDAP-NAME                 {"zimbraHttpThreadPoolMaxIdleTimeMillis"}
  LDAP-DESC                 "The maximum thread idle time in milli seconds. Threads that are idle for longer than this period may be stopped."
  ID                        id-at-zimbraHttpThreadPoolMaxIdleTimeMillis }

zimbraHttpThrottleSafeIPs ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraHttpThrottleSafeIPs"}
  LDAP-DESC                 "IP addresses to ignore when applying Jetty DosFilter."
  ID                        id-at-zimbraHttpThrottleSafeIPs }

zimbraIMAvailableInteropGateways ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraIMAvailableInteropGateways"}
  LDAP-DESC                 "available IM interop gateways"
  ID                        id-at-zimbraIMAvailableInteropGateways }

-- LDAP syntax length {128} rendered as DirectoryString{128}.
zimbraIMBindAddress ATTRIBUTE ::= {
  WITH SYNTAX               DirectoryString{128}
  EQUALITY MATCHING RULE    caseIgnoreMatch
  SUBSTRINGS MATCHING RULE  caseIgnoreSubstringsMatch
  LDAP-SYNTAX               directoryString.&id
  LDAP-NAME                 {"zimbraIMBindAddress"}
  LDAP-DESC                 "interface address on which IM server should listen; if empty, binds to all interfaces"
  ID                        id-at-zimbraIMBindAddress }

-- LDAP syntax length {32} rendered as DirectoryString{32}.
zimbraIMService ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraIMService"}
  LDAP-DESC                 "Deprecated since: 6.0.0_GA. deprecated per bug 40069. Orig desc: IM service"
  ID                        id-at-zimbraIMService }

-- LDAP syntax length {32} rendered as DirectoryString{32}.
zimbraIPMode ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraIPMode"}
  LDAP-DESC                 "supported IP mode"
  ID                        id-at-zimbraIPMode }

-- LDAP syntax length {256} rendered as DirectoryString{256}.
zimbraId ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraId"}
  LDAP-DESC                 "Zimbra Systems Unique ID"
  ID                        id-at-zimbraId }

zimbraIdentityMaxNumEntries ATTRIBUTE ::= {
  WITH SYNTAX               INTEGER
  EQUALITY MATCHING RULE    integerMatch
  SINGLE VALUE              TRUE
  LDAP-SYNTAX               integer.&id
  LDAP-NAME                 {"zimbraIdentityMaxNumEntries"}
  LDAP-DESC                 "maximum number of identities allowed on an account"
  ID                        id-at-zimbraIdentityMaxNumEntries }

-- LDAP syntax length {128} rendered as DirectoryString{128}.
zimbraImapAdvertisedName ATTRIBUTE ::= {
  WITH SYNTAX               DirectoryString{128}
  EQUALITY MATCHING RULE    caseIgnoreMatch
  SUBSTRINGS MATCHING RULE  caseIgnoreSubstringsMatch
  SINGLE VALUE              TRUE
  LDAP-SYNTAX               directoryString.&id
  LDAP-NAME                 {"zimbraImapAdvertisedName"}
  LDAP-DESC                 "name to use in greeting and sign-off; if empty, uses hostname"
  ID                        id-at-zimbraImapAdvertisedName }

-- LDAP syntax length {128} rendered as DirectoryString{128}.
zimbraImapBindAddress ATTRIBUTE ::= {
  WITH SYNTAX               DirectoryString{128}
  EQUALITY MATCHING RULE    caseIgnoreMatch
  SUBSTRINGS MATCHING RULE  caseIgnoreSubstringsMatch
  LDAP-SYNTAX               directoryString.&id
  LDAP-NAME                 {"zimbraImapBindAddress"}
  LDAP-DESC                 "interface address on which IMAP server should listen; if empty, binds to all interfaces"
  ID                        id-at-zimbraImapBindAddress }

zimbraImapBindOnStartup ATTRIBUTE ::= {
  WITH SYNTAX               BOOLEAN
  EQUALITY MATCHING RULE    booleanMatch
  SINGLE VALUE              TRUE
  LDAP-SYNTAX               boolean.&id
  LDAP-NAME                 {"zimbraImapBindOnStartup"}
  LDAP-DESC                 "Whether to bind to port on startup irrespective of whether the server is enabled. Useful when port to bind is privileged and must be bound early."
  ID                        id-at-zimbraImapBindOnStartup }

zimbraImapBindPort ATTRIBUTE ::= {
  WITH SYNTAX               INTEGER
  EQUALITY MATCHING RULE    integerMatch
  SINGLE VALUE              TRUE
  LDAP-SYNTAX               integer.&id
  LDAP-NAME                 {"zimbraImapBindPort"}
  LDAP-DESC                 "port number on which IMAP server should listen"
  ID                        id-at-zimbraImapBindPort }

zimbraImapCleartextLoginEnabled ATTRIBUTE ::= {
  WITH SYNTAX               BOOLEAN
  EQUALITY MATCHING RULE    booleanMatch
  SINGLE VALUE              TRUE
  LDAP-SYNTAX               boolean.&id
  LDAP-NAME                 {"zimbraImapCleartextLoginEnabled"}
  LDAP-DESC                 "whether or not to allow cleartext logins over a non SSL/TLS connection"
  ID                        id-at-zimbraImapCleartextLoginEnabled }

-- LDAP syntax length {256} rendered as DirectoryString{256}.
zimbraImapDisabledCapability ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraImapDisabledCapability"}
  LDAP-DESC                 "disabled IMAP capabilities. Capabilities are listed on the CAPABILITY line, also known in RFCs as extensions"
  ID                        id-at-zimbraImapDisabledCapability }

zimbraImapEnabled ATTRIBUTE ::= {
  WITH SYNTAX               BOOLEAN
  EQUALITY MATCHING RULE    booleanMatch
  SINGLE VALUE              TRUE
  LDAP-SYNTAX               boolean.&id
  LDAP-NAME                 {"zimbraImapEnabled"}
  LDAP-DESC                 "whether IMAP is enabled for an account"
  ID                        id-at-zimbraImapEnabled }

zimbraImapExposeVersionOnBanner ATTRIBUTE ::= {
  WITH SYNTAX               BOOLEAN
  EQUALITY MATCHING RULE    booleanMatch
  SINGLE VALUE              TRUE
  LDAP-SYNTAX               boolean.&id
  LDAP-NAME                 {"zimbraImapExposeVersionOnBanner"}
  LDAP-DESC                 "Whether to expose version on IMAP banner"
  ID                        id-at-zimbraImapExposeVersionOnBanner }

zimbraImapMaxConnections ATTRIBUTE ::= {
  WITH SYNTAX               INTEGER
  EQUALITY MATCHING RULE    integerMatch
  SINGLE VALUE              TRUE
  LDAP-SYNTAX               integer.&id
  LDAP-NAME                 {"zimbraImapMaxConnections"}
  LDAP-DESC                 "Maximum number of concurrent IMAP connections allowed. New connections exceeding this limit are rejected."
  ID                        id-at-zimbraImapMaxConnections }

zimbraImapMaxRequestSize ATTRIBUTE ::= {
  WITH SYNTAX               INTEGER
  EQUALITY MATCHING RULE    integerMatch
  SINGLE VALUE              TRUE
  LDAP-SYNTAX               integer.&id
  LDAP-NAME                 {"zimbraImapMaxRequestSize"}
  LDAP-DESC                 "maximum size of IMAP request in bytes excluding literal data"
  ID                        id-at-zimbraImapMaxRequestSize }

zimbraImapNumThreads ATTRIBUTE ::= {
  WITH SYNTAX               INTEGER
  EQUALITY MATCHING RULE    integerMatch
  SINGLE VALUE              TRUE
  LDAP-SYNTAX               integer.&id
  LDAP-NAME                 {"zimbraImapNumThreads"}
  LDAP-DESC                 "number of handler threads"
  ID                        id-at-zimbraImapNumThreads }

zimbraImapProxyBindPort ATTRIBUTE ::= {
  WITH SYNTAX               INTEGER
  EQUALITY MATCHING RULE    integerMatch
  SINGLE VALUE              TRUE
  LDAP-SYNTAX               integer.&id
  LDAP-NAME                 {"zimbraImapProxyBindPort"}
  LDAP-DESC                 "port number on which IMAP proxy server should listen"
  ID                        id-at-zimbraImapProxyBindPort }

-- LDAP syntax length {128} rendered as DirectoryString{128}.
zimbraImapSSLBindAddress ATTRIBUTE ::= {
  WITH SYNTAX               DirectoryString{128}
  EQUALITY MATCHING RULE    caseIgnoreMatch
  SUBSTRINGS MATCHING RULE  caseIgnoreSubstringsMatch
  LDAP-SYNTAX               directoryString.&id
  LDAP-NAME                 {"zimbraImapSSLBindAddress"}
  LDAP-DESC                 "interface address on which IMAP server should listen; if empty, binds to all interfaces"
  ID                        id-at-zimbraImapSSLBindAddress }

zimbraImapSSLBindOnStartup ATTRIBUTE ::= {
  WITH SYNTAX               BOOLEAN
  EQUALITY MATCHING RULE    booleanMatch
  SINGLE VALUE              TRUE
  LDAP-SYNTAX               boolean.&id
  LDAP-NAME                 {"zimbraImapSSLBindOnStartup"}
  LDAP-DESC                 "Whether to bind to port on startup irrespective of whether the server is enabled. Useful when port to bind is privileged and must be bound early."
  ID                        id-at-zimbraImapSSLBindOnStartup }

zimbraImapSSLBindPort ATTRIBUTE ::= {
  WITH SYNTAX               INTEGER
  EQUALITY MATCHING RULE    integerMatch
  SINGLE VALUE              TRUE
  LDAP-SYNTAX               integer.&id
  LDAP-NAME                 {"zimbraImapSSLBindPort"}
  LDAP-DESC                 "port number on which IMAP SSL server should listen on"
  ID                        id-at-zimbraImapSSLBindPort }

-- LDAP syntax length {256} rendered as DirectoryString{256}.
zimbraImapSSLDisabledCapability ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraImapSSLDisabledCapability"}
  LDAP-DESC                 "disabled IMAP SSL capabilities. Capabilities are listed on the CAPABILITY line, also known in RFCs as extensions"
  ID                        id-at-zimbraImapSSLDisabledCapability }

zimbraImapSSLProxyBindPort ATTRIBUTE ::= {
  WITH SYNTAX               INTEGER
  EQUALITY MATCHING RULE    integerMatch
  SINGLE VALUE              TRUE
  LDAP-SYNTAX               integer.&id
  LDAP-NAME                 {"zimbraImapSSLProxyBindPort"}
  LDAP-DESC                 "port number on which IMAPS proxy server should listen"
  ID                        id-at-zimbraImapSSLProxyBindPort }

zimbraImapSSLServerEnabled ATTRIBUTE ::= {
  WITH SYNTAX               BOOLEAN
  EQUALITY MATCHING RULE    booleanMatch
  SINGLE VALUE              TRUE
  LDAP-SYNTAX               boolean.&id
  LDAP-NAME                 {"zimbraImapSSLServerEnabled"}
  LDAP-DESC                 "whether IMAP SSL server is enabled for a given server"
  ID                        id-at-zimbraImapSSLServerEnabled }

zimbraImapSaslGssapiEnabled ATTRIBUTE ::= {
  WITH SYNTAX               BOOLEAN
  EQUALITY MATCHING RULE    booleanMatch
  SINGLE VALUE              TRUE
  LDAP-SYNTAX               boolean.&id
  LDAP-NAME                 {"zimbraImapSaslGssapiEnabled"}
  LDAP-DESC                 "whether IMAP SASL GSSAPI is enabled for a given server"
  ID                        id-at-zimbraImapSaslGssapiEnabled }

zimbraImapServerEnabled ATTRIBUTE ::= {
  WITH SYNTAX               BOOLEAN
  EQUALITY MATCHING RULE    booleanMatch
  SINGLE VALUE              TRUE
  LDAP-SYNTAX               boolean.&id
  LDAP-NAME                 {"zimbraImapServerEnabled"}
  LDAP-DESC                 "whether IMAP is enabled for a server"
  ID                        id-at-zimbraImapServerEnabled }

zimbraImapShutdownGraceSeconds ATTRIBUTE ::= {
  WITH SYNTAX               INTEGER
  EQUALITY MATCHING RULE    integerMatch
  SINGLE VALUE              TRUE
  LDAP-SYNTAX               integer.&id
  LDAP-NAME                 {"zimbraImapShutdownGraceSeconds"}
  LDAP-DESC                 "number of seconds to wait before forcing IMAP server shutdown"
  ID                        id-at-zimbraImapShutdownGraceSeconds }

-- LDAP syntax length {80} rendered as DirectoryString{80}.
zimbraInstalledSkin ATTRIBUTE ::= {
  WITH SYNTAX               DirectoryString{80}
  EQUALITY MATCHING RULE    caseIgnoreMatch
  SUBSTRINGS MATCHING RULE  caseIgnoreSubstringsMatch
  LDAP-SYNTAX               directoryString.&id
  LDAP-NAME                 {"zimbraInstalledSkin"}
  LDAP-DESC                 "Deprecated since: 5.0. Installed skin list is a per server property, the list is now generated by directory scan of skin files. Orig desc: Skins installed and available on all servers (this is global config only)"
  ID                        id-at-zimbraInstalledSkin }

zimbraInterceptAddress ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraInterceptAddress"}
  LDAP-DESC                 "The address to which legal intercept messages will be sent."
  ID                        id-at-zimbraInterceptAddress }

zimbraInterceptBody ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraInterceptBody"}
  LDAP-DESC                 "Template used to construct the body of a legal intercept message."
  ID                        id-at-zimbraInterceptBody }

zimbraInterceptFrom ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraInterceptFrom"}
  LDAP-DESC                 "Template used to construct the sender of a legal intercept message."
  ID                        id-at-zimbraInterceptFrom }

zimbraInterceptSendHeadersOnly ATTRIBUTE ::= {
  WITH SYNTAX               BOOLEAN
  EQUALITY MATCHING RULE    booleanMatch
  SINGLE VALUE              TRUE
  LDAP-SYNTAX               boolean.&id
  LDAP-NAME                 {"zimbraInterceptSendHeadersOnly"}
  LDAP-DESC                 "Specifies whether legal intercept messages should contain the entire original message or just the headers."
  ID                        id-at-zimbraInterceptSendHeadersOnly }

zimbraInterceptSubject ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraInterceptSubject"}
  LDAP-DESC                 "Template used to construct the subject of a legal intercept message."
  ID                        id-at-zimbraInterceptSubject }

zimbraInternalSendersDomain ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraInternalSendersDomain"}
  LDAP-DESC                 "additional domains considered as internal w.r.t. recipient"
  ID                        id-at-zimbraInternalSendersDomain }

zimbraInternalSharingCrossDomainEnabled ATTRIBUTE ::= {
  WITH SYNTAX               BOOLEAN
  EQUALITY MATCHING RULE    booleanMatch
  SINGLE VALUE              TRUE
  LDAP-SYNTAX               boolean.&id
  LDAP-NAME                 {"zimbraInternalSharingCrossDomainEnabled"}
  LDAP-DESC                 "whether sharing with accounts and groups of all other domains hosted on this deployment be considered internal sharing"
  ID                        id-at-zimbraInternalSharingCrossDomainEnabled }

zimbraInternalSharingDomain ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraInternalSharingDomain"}
  LDAP-DESC                 "Domains hosted on this deployment, accounts and groups of which are considered internal during sharing. Applicable when zimbraInternalSharingCrossDomainEnabled is set to FALSE."
  ID                        id-at-zimbraInternalSharingDomain }

zimbraInvalidLoginFilterDelayInMinBetwnReqBeforeReinstating ATTRIBUTE ::= {
  WITH SYNTAX               INTEGER
  EQUALITY MATCHING RULE    integerMatch
  SINGLE VALUE              TRUE
  LDAP-SYNTAX               integer.&id
  LDAP-NAME                 {"zimbraInvalidLoginFilterDelayInMinBetwnReqBeforeReinstating"}
  LDAP-DESC                 "This attribute is used for failed authentication requests. It indicates the minimum time between current req and last req from the same IP before this suspended IP will be reinstated"
  ID                        id-at-zimbraInvalidLoginFilterDelayInMinBetwnReqBeforeReinstating }

zimbraInvalidLoginFilterMaxFailedLogin ATTRIBUTE ::= {
  WITH SYNTAX               INTEGER
  EQUALITY MATCHING RULE    integerMatch
  SINGLE VALUE              TRUE
  LDAP-SYNTAX               integer.&id
  LDAP-NAME                 {"zimbraInvalidLoginFilterMaxFailedLogin"}
  LDAP-DESC                 "This attribute is used for failed authentication requests.This is a DOSFilter style check for repeated failed logins from IP, if set to 0 no check happens, else failed login is recorded."
  ID                        id-at-zimbraInvalidLoginFilterMaxFailedLogin }

zimbraInvalidLoginFilterMaxSizeOfFailedIpDb ATTRIBUTE ::= {
  WITH SYNTAX               INTEGER
  EQUALITY MATCHING RULE    integerMatch
  SINGLE VALUE              TRUE
  LDAP-SYNTAX               integer.&id
  LDAP-NAME                 {"zimbraInvalidLoginFilterMaxSizeOfFailedIpDb"}
  LDAP-DESC                 "This attribute is used for failed authentication requests. It indicates the max size of data structures that holds the list of failed logins"
  ID                        id-at-zimbraInvalidLoginFilterMaxSizeOfFailedIpDb }

zimbraInvalidLoginFilterReinstateIpTaskIntervalInMin ATTRIBUTE ::= {
  WITH SYNTAX               INTEGER
  EQUALITY MATCHING RULE    integerMatch
  SINGLE VALUE              TRUE
  LDAP-SYNTAX               integer.&id
  LDAP-NAME                 {"zimbraInvalidLoginFilterReinstateIpTaskIntervalInMin"}
  LDAP-DESC                 "This attribute is used for failed authentication requests. Interval at which Task to reinstate IPs suspended as part of ZimbraInvalidLoging filter are run."
  ID                        id-at-zimbraInvalidLoginFilterReinstateIpTaskIntervalInMin }

zimbraIsACLGroup ATTRIBUTE ::= {
  WITH SYNTAX               BOOLEAN
  EQUALITY MATCHING RULE    booleanMatch
  SINGLE VALUE              TRUE
  LDAP-SYNTAX               boolean.&id
  LDAP-NAME                 {"zimbraIsACLGroup"}
  LDAP-DESC                 "if the dynamic group can be a legitimate grantee for folder grantees; and a legitimate grantee or target for delegated admin grants"
  ID                        id-at-zimbraIsACLGroup }

zimbraIsAdminAccount ATTRIBUTE ::= {
  WITH SYNTAX               BOOLEAN
  EQUALITY MATCHING RULE    booleanMatch
  SINGLE VALUE              TRUE
  LDAP-SYNTAX               boolean.&id
  LDAP-NAME                 {"zimbraIsAdminAccount"}
  LDAP-DESC                 "set to true for admin accounts"
  ID                        id-at-zimbraIsAdminAccount }

zimbraIsAdminGroup ATTRIBUTE ::= {
  WITH SYNTAX               BOOLEAN
  EQUALITY MATCHING RULE    booleanMatch
  SINGLE VALUE              TRUE
  LDAP-SYNTAX               boolean.&id
  LDAP-NAME                 {"zimbraIsAdminGroup"}
  LDAP-DESC                 "set to true for admin groups"
  ID                        id-at-zimbraIsAdminGroup }

zimbraIsCustomerCareAccount ATTRIBUTE ::= {
  WITH SYNTAX               BOOLEAN
  EQUALITY MATCHING RULE    booleanMatch
  SINGLE VALUE              TRUE
  LDAP-SYNTAX               boolean.&id
  LDAP-NAME                 {"zimbraIsCustomerCareAccount"}
  LDAP-DESC                 "set to true for customer care accounts"
  ID                        id-at-zimbraIsCustomerCareAccount }

zimbraIsDelegatedAdminAccount ATTRIBUTE ::= {
  WITH SYNTAX               BOOLEAN
  EQUALITY MATCHING RULE    booleanMatch
  SINGLE VALUE              TRUE
  LDAP-SYNTAX               boolean.&id
  LDAP-NAME                 {"zimbraIsDelegatedAdminAccount"}
  LDAP-DESC                 "set to true for delegated admin accounts"
  ID                        id-at-zimbraIsDelegatedAdminAccount }

zimbraIsDomainAdminAccount ATTRIBUTE ::= {
  WITH SYNTAX               BOOLEAN
  EQUALITY MATCHING RULE    booleanMatch
  SINGLE VALUE              TRUE
  LDAP-SYNTAX               boolean.&id
  LDAP-NAME                 {"zimbraIsDomainAdminAccount"}
  LDAP-DESC                 "set to true for domain admin accounts"
  ID                        id-at-zimbraIsDomainAdminAccount }

zimbraIsExternalVirtualAccount ATTRIBUTE ::= {
  WITH SYNTAX               BOOLEAN
  EQUALITY MATCHING RULE    booleanMatch
  SINGLE VALUE              TRUE
  LDAP-SYNTAX               boolean.&id
  LDAP-NAME                 {"zimbraIsExternalVirtualAccount"}
  LDAP-DESC                 "whether it is an external user account"
  ID                        id-at-zimbraIsExternalVirtualAccount }

zimbraIsMonitorHost ATTRIBUTE ::= {
  WITH SYNTAX               BOOLEAN
  EQUALITY MATCHING RULE    booleanMatch
  SINGLE VALUE              TRUE
  LDAP-SYNTAX               boolean.&id
  LDAP-NAME                 {"zimbraIsMonitorHost"}
  LDAP-DESC                 "true if this server is the monitor host"
  ID                        id-at-zimbraIsMonitorHost }

zimbraIsSystemAccount ATTRIBUTE ::= {
  WITH SYNTAX               BOOLEAN
  EQUALITY MATCHING RULE    booleanMatch
  SINGLE VALUE              TRUE
  LDAP-SYNTAX               boolean.&id
  LDAP-NAME                 {"zimbraIsSystemAccount"}
  LDAP-DESC                 "Indicates the account is an account used by the system such as spam accounts or Notebook accounts. System accounts cannot be deleted in admin console."
  ID                        id-at-zimbraIsSystemAccount }

zimbraIsSystemResource ATTRIBUTE ::= {
  WITH SYNTAX               BOOLEAN
  EQUALITY MATCHING RULE    booleanMatch
  SINGLE VALUE              TRUE
  LDAP-SYNTAX               boolean.&id
  LDAP-NAME                 {"zimbraIsSystemResource"}
  LDAP-DESC                 "Indicates the account is a resource used by the system. System resource accounts are not counted against license quota."
  ID                        id-at-zimbraIsSystemResource }

zimbraItemActionBatchSize ATTRIBUTE ::= {
  WITH SYNTAX               INTEGER
  EQUALITY MATCHING RULE    integerMatch
  SINGLE VALUE              TRUE
  LDAP-SYNTAX               integer.&id
  LDAP-NAME                 {"zimbraItemActionBatchSize"}
  LDAP-DESC                 "Maximum number of item to perform an ItemAction on at a time."
  ID                        id-at-zimbraItemActionBatchSize }

zimbraJunkMessagesIndexingEnabled ATTRIBUTE ::= {
  WITH SYNTAX               BOOLEAN
  EQUALITY MATCHING RULE    booleanMatch
  SINGLE VALUE              TRUE
  LDAP-SYNTAX               boolean.&id
  LDAP-NAME                 {"zimbraJunkMessagesIndexingEnabled"}
  LDAP-DESC                 "Whether to index junk messages"
  ID                        id-at-zimbraJunkMessagesIndexingEnabled }

zimbraLastLogonTimestamp ATTRIBUTE ::= {
  WITH SYNTAX               GeneralizedTime
  EQUALITY MATCHING RULE    generalizedTimeMatch
  ORDERING MATCHING RULE    generalizedTimeOrderingMatch
  SINGLE VALUE              TRUE
  LDAP-SYNTAX               generalizedTime.&id
  LDAP-NAME                 {"zimbraLastLogonTimestamp"}
  LDAP-DESC                 "rough estimate of when the user last logged in. see zimbraLastLogonTimestampFrequency"
  ID                        id-at-zimbraLastLogonTimestamp }

zimbraLastLogonTimestampFrequency ATTRIBUTE ::= {
  WITH SYNTAX               IA5String(SIZE (1..32))
  EQUALITY MATCHING RULE    caseIgnoreIA5Match
  SINGLE VALUE              TRUE
  LDAP-SYNTAX               ia5String.&id
  LDAP-NAME                 {"zimbraLastLogonTimestampFrequency"}
  LDAP-DESC                 "how often the zimbraLastLogonTimestamp is updated. if set to 0, updating zimbraLastLogonTimestamp is completely disabled . Must be in valid duration format: {digits}{time-unit}. digits: 0-9, time-unit: [hmsd]|ms. h - hours, m - minutes, s - seconds, d - days, ms - milliseconds. If time unit is not specified, the default is s(seconds)."
  ID                        id-at-zimbraLastLogonTimestampFrequency }

zimbraLastPurgeMaxDuration ATTRIBUTE ::= {
  WITH SYNTAX               IA5String(SIZE (1..32))
  EQUALITY MATCHING RULE    caseIgnoreIA5Match
  SINGLE VALUE              TRUE
  LDAP-SYNTAX               ia5String.&id
  LDAP-NAME                 {"zimbraLastPurgeMaxDuration"}
  LDAP-DESC                 "Maximum duration beyond which the mailbox must be scheduled for purge irrespective of whether it is loaded into memory or not.. Must be in valid duration format: {digits}{time-unit}. digits: 0-9, time-unit: [hmsd]|ms. h - hours, m - minutes, s - seconds, d - days, ms - milliseconds. If time unit is not specified, the default is s(seconds)."
  ID                        id-at-zimbraLastPurgeMaxDuration }

zimbraLdapGalSyncDisabled ATTRIBUTE ::= {
  WITH SYNTAX               BOOLEAN
  EQUALITY MATCHING RULE    booleanMatch
  SINGLE VALUE              TRUE
  LDAP-SYNTAX               boolean.&id
  LDAP-NAME                 {"zimbraLdapGalSyncDisabled"}
  LDAP-DESC                 "whether ldap based galsync disabled or not"
  ID                        id-at-zimbraLdapGalSyncDisabled }

-- LDAP syntax length {128} rendered as DirectoryString{128}.
zimbraLmtpAdvertisedName ATTRIBUTE ::= {
  WITH SYNTAX               DirectoryString{128}
  EQUALITY MATCHING RULE    caseIgnoreMatch
  SUBSTRINGS MATCHING RULE  caseIgnoreSubstringsMatch
  SINGLE VALUE              TRUE
  LDAP-SYNTAX               directoryString.&id
  LDAP-NAME                 {"zimbraLmtpAdvertisedName"}
  LDAP-DESC                 "name to use in greeting and sign-off; if empty, uses hostname"
  ID                        id-at-zimbraLmtpAdvertisedName }

-- LDAP syntax length {128} rendered as DirectoryString{128}.
zimbraLmtpBindAddress ATTRIBUTE ::= {
  WITH SYNTAX               DirectoryString{128}
  EQUALITY MATCHING RULE    caseIgnoreMatch
  SUBSTRINGS MATCHING RULE  caseIgnoreSubstringsMatch
  LDAP-SYNTAX               directoryString.&id
  LDAP-NAME                 {"zimbraLmtpBindAddress"}
  LDAP-DESC                 "interface address on which LMTP server should listen; if empty, binds to all interfaces"
  ID                        id-at-zimbraLmtpBindAddress }

zimbraLmtpBindOnStartup ATTRIBUTE ::= {
  WITH SYNTAX               BOOLEAN
  EQUALITY MATCHING RULE    booleanMatch
  SINGLE VALUE              TRUE
  LDAP-SYNTAX               boolean.&id
  LDAP-NAME                 {"zimbraLmtpBindOnStartup"}
  LDAP-DESC                 "Whether to bind to port on startup irrespective of whether the server is enabled. Useful when port to bind is privileged and must be bound early."
  ID                        id-at-zimbraLmtpBindOnStartup }

zimbraLmtpBindPort ATTRIBUTE ::= {
  WITH SYNTAX               INTEGER
  EQUALITY MATCHING RULE    integerMatch
  SINGLE VALUE              TRUE
  LDAP-SYNTAX               integer.&id
  LDAP-NAME                 {"zimbraLmtpBindPort"}
  LDAP-DESC                 "port number on which LMTP server should listen"
  ID                        id-at-zimbraLmtpBindPort }

zimbraLmtpExposeVersionOnBanner ATTRIBUTE ::= {
  WITH SYNTAX               BOOLEAN
  EQUALITY MATCHING RULE    booleanMatch
  SINGLE VALUE              TRUE
  LDAP-SYNTAX               boolean.&id
  LDAP-NAME                 {"zimbraLmtpExposeVersionOnBanner"}
  LDAP-DESC                 "Whether to expose version on LMTP banner"
  ID                        id-at-zimbraLmtpExposeVersionOnBanner }

zimbraLmtpLHLORequired ATTRIBUTE ::= {
  WITH SYNTAX               BOOLEAN
  EQUALITY MATCHING RULE    booleanMatch
  SINGLE VALUE              TRUE
  LDAP-SYNTAX               boolean.&id
  LDAP-NAME                 {"zimbraLmtpLHLORequired"}
  LDAP-DESC                 "Lmtp Server will reject the client transactions which do not issue LHLO"
  ID                        id-at-zimbraLmtpLHLORequired }

zimbraLmtpNumThreads ATTRIBUTE ::= {
  WITH SYNTAX               INTEGER
  EQUALITY MATCHING RULE    integerMatch
  SINGLE VALUE              TRUE
  LDAP-SYNTAX               integer.&id
  LDAP-NAME                 {"zimbraLmtpNumThreads"}
  LDAP-DESC                 "number of handler threads, should match MTA concurrency setting for this server"
  ID                        id-at-zimbraLmtpNumThreads }

zimbraLmtpPermanentFailureWhenOverQuota ATTRIBUTE ::= {
  WITH SYNTAX               BOOLEAN
  EQUALITY MATCHING RULE    booleanMatch
  SINGLE VALUE              TRUE
  LDAP-SYNTAX               boolean.&id
  LDAP-NAME                 {"zimbraLmtpPermanentFailureWhenOverQuota"}
  LDAP-DESC                 "If true, a permanent failure (552) is returned when the user is over quota. If false, a temporary failure (452) is returned."
  ID                        id-at-zimbraLmtpPermanentFailureWhenOverQuota }

zimbraLmtpServerEnabled ATTRIBUTE ::= {
  WITH SYNTAX               BOOLEAN
  EQUALITY MATCHING RULE    booleanMatch
  SINGLE VALUE              TRUE
  LDAP-SYNTAX               boolean.&id
  LDAP-NAME                 {"zimbraLmtpServerEnabled"}
  LDAP-DESC                 "whether LMTP server is enabled for a given server"
  ID                        id-at-zimbraLmtpServerEnabled }

zimbraLmtpShutdownGraceSeconds ATTRIBUTE ::= {
  WITH SYNTAX               INTEGER
  EQUALITY MATCHING RULE    integerMatch
  SINGLE VALUE              TRUE
  LDAP-SYNTAX               integer.&id
  LDAP-NAME                 {"zimbraLmtpShutdownGraceSeconds"}
  LDAP-DESC                 "number of seconds to wait before forcing LMTP server shutdown"
  ID                        id-at-zimbraLmtpShutdownGraceSeconds }

-- LDAP syntax length {64} rendered as DirectoryString{64}.
zimbraLocale ATTRIBUTE ::= {
  WITH SYNTAX               DirectoryString{64}
  EQUALITY MATCHING RULE    caseIgnoreMatch
  SUBSTRINGS MATCHING RULE  caseIgnoreSubstringsMatch
  SINGLE VALUE              TRUE
  LDAP-SYNTAX               directoryString.&id
  LDAP-NAME                 {"zimbraLocale"}
  LDAP-DESC                 "locale of entry, e.g. en_US"
  ID                        id-at-zimbraLocale }

zimbraLogHostname ATTRIBUTE ::= {
  WITH SYNTAX               IA5String(SIZE (1..256))
  EQUALITY MATCHING RULE    caseIgnoreIA5Match
  SUBSTRINGS MATCHING RULE  caseIgnoreSubstringsMatch
  LDAP-SYNTAX               ia5String.&id
  LDAP-NAME                 {"zimbraLogHostname"}
  LDAP-DESC                 "destination for syslog messages"
  ID                        id-at-zimbraLogHostname }

zimbraLogOutFromAllServers ATTRIBUTE ::= {
  WITH SYNTAX               BOOLEAN
  EQUALITY MATCHING RULE    booleanMatch
  SINGLE VALUE              TRUE
  LDAP-SYNTAX               boolean.&id
  LDAP-NAME                 {"zimbraLogOutFromAllServers"}
  LDAP-DESC                 "Flag to control how authtokens are invalidated in multi-server environment. If set to TRUE: when this account logs out on a server, the server will notify other servers that this account's authtoken has been invalidated. If set to FALSE, an auth token may remain vallid on servers other than the account's home server after a user logs out for as long as an account object remains in Provisioning Cache. Set to TRUE for increased protection against Cookie Re-use attack. Default is FALSE to reduce network chatter."
  ID                        id-at-zimbraLogOutFromAllServers }

zimbraLogRawLifetime ATTRIBUTE ::= {
  WITH SYNTAX               IA5String(SIZE (1..32))
  EQUALITY MATCHING RULE    caseIgnoreIA5Match
  SINGLE VALUE              TRUE
  LDAP-SYNTAX               ia5String.&id
  LDAP-NAME                 {"zimbraLogRawLifetime"}
  LDAP-DESC                 "lifetime of raw log rows in consolidated logger tables. Must be in valid duration format: {digits}{time-unit}. digits: 0-9, time-unit: [hmsd]|ms. h - hours, m - minutes, s - seconds, d - days, ms - milliseconds. If time unit is not specified, the default is s(seconds)."
  ID                        id-at-zimbraLogRawLifetime }

zimbraLogSummaryLifetime ATTRIBUTE ::= {
  WITH SYNTAX               IA5String(SIZE (1..32))
  EQUALITY MATCHING RULE    caseIgnoreIA5Match
  SINGLE VALUE              TRUE
  LDAP-SYNTAX               ia5String.&id
  LDAP-NAME                 {"zimbraLogSummaryLifetime"}
  LDAP-DESC                 "lifetime of summarized log rows in consolidated logger tables. Must be in valid duration format: {digits}{time-unit}. digits: 0-9, time-unit: [hmsd]|ms. h - hours, m - minutes, s - seconds, d - days, ms - milliseconds. If time unit is not specified, the default is s(seconds)."
  ID                        id-at-zimbraLogSummaryLifetime }

zimbraLogToSyslog ATTRIBUTE ::= {
  WITH SYNTAX               BOOLEAN
  EQUALITY MATCHING RULE    booleanMatch
  SINGLE VALUE              TRUE
  LDAP-SYNTAX               boolean.&id
  LDAP-NAME                 {"zimbraLogToSyslog"}
  LDAP-DESC                 "whether mailbox server should log to syslog"
  ID                        id-at-zimbraLogToSyslog }

zimbraLowestSupportedAuthVersion ATTRIBUTE ::= {
  WITH SYNTAX               INTEGER
  EQUALITY MATCHING RULE    integerMatch
  SINGLE VALUE              TRUE
  LDAP-SYNTAX               integer.&id
  LDAP-NAME                 {"zimbraLowestSupportedAuthVersion"}
  LDAP-DESC                 "version of lowest supported authentication protocol"
  ID                        id-at-zimbraLowestSupportedAuthVersion }

zimbraMailAddress ATTRIBUTE ::= {
  WITH SYNTAX               IA5String(SIZE (1..256))
  EQUALITY MATCHING RULE    caseIgnoreIA5Match
  SUBSTRINGS MATCHING RULE  caseIgnoreSubstringsMatch
  LDAP-SYNTAX               ia5String.&id
  LDAP-NAME                 {"zimbraMailAddress"}
  LDAP-DESC                 "RFC822 email address of this recipient for accepting mail"
  ID                        id-at-zimbraMailAddress }

-- LDAP syntax length {512} rendered as DirectoryString{512}.
zimbraMailAddressValidationRegex ATTRIBUTE ::= {
  WITH SYNTAX               DirectoryString{512}
  EQUALITY MATCHING RULE    caseIgnoreMatch
  SUBSTRINGS MATCHING RULE  caseIgnoreSubstringsMatch
  LDAP-SYNTAX               directoryString.&id
  LDAP-NAME                 {"zimbraMailAddressValidationRegex"}
  LDAP-DESC                 "optional regex used by web client to validate email address"
  ID                        id-at-zimbraMailAddressValidationRegex }

zimbraMailAlias ATTRIBUTE ::= {
  WITH SYNTAX               IA5String(SIZE (1..256))
  EQUALITY MATCHING RULE    caseIgnoreIA5Match
  SUBSTRINGS MATCHING RULE  caseIgnoreSubstringsMatch
  LDAP-SYNTAX               ia5String.&id
  LDAP-NAME                 {"zimbraMailAlias"}
  LDAP-DESC                 "RFC822 email address of this recipient for accepting mail"
  ID                        id-at-zimbraMailAlias }

zimbraMailAllowReceiveButNotSendWhenOverQuota ATTRIBUTE ::= {
  WITH SYNTAX               BOOLEAN
  EQUALITY MATCHING RULE    booleanMatch
  SINGLE VALUE              TRUE
  LDAP-SYNTAX               boolean.&id
  LDAP-NAME                 {"zimbraMailAllowReceiveButNotSendWhenOverQuota"}
  LDAP-DESC                 "If TRUE, a mailbox that exceeds its quota is still allowed to receive mail, but is not allowed to send."
  ID                        id-at-zimbraMailAllowReceiveButNotSendWhenOverQuota }

-- LDAP syntax length {128} rendered as DirectoryString{128}.
zimbraMailBindAddress ATTRIBUTE ::= {
  WITH SYNTAX               DirectoryString{128}
  EQUALITY MATCHING RULE    caseIgnoreMatch
  SUBSTRINGS MATCHING RULE  caseIgnoreSubstringsMatch
  SINGLE VALUE              TRUE
  LDAP-SYNTAX               directoryString.&id
  LDAP-NAME                 {"zimbraMailBindAddress"}
  LDAP-DESC                 "interface address on which HTTP server should listen; if empty, binds to all interfaces"
  ID                        id-at-zimbraMailBindAddress }

zimbraMailBlacklistMaxNumEntries ATTRIBUTE ::= {
  WITH SYNTAX               INTEGER
  EQUALITY MATCHING RULE    integerMatch
  SINGLE VALUE              TRUE
  LDAP-SYNTAX               integer.&id
  LDAP-NAME                 {"zimbraMailBlacklistMaxNumEntries"}
  LDAP-DESC                 "Maximum number of entries for per user black list. This restricts the number of values that can be set on the amavisBlacklistSender attribute of an account. If set to 0, the per user white list feature is disabled."
  ID                        id-at-zimbraMailBlacklistMaxNumEntries }

zimbraMailCanonicalAddress ATTRIBUTE ::= {
  WITH SYNTAX               IA5String(SIZE (1..256))
  EQUALITY MATCHING RULE    caseIgnoreIA5Match
  SUBSTRINGS MATCHING RULE  caseIgnoreSubstringsMatch
  SINGLE VALUE              TRUE
  LDAP-SYNTAX               ia5String.&id
  LDAP-NAME                 {"zimbraMailCanonicalAddress"}
  LDAP-DESC                 "RFC822 email address for senders outbound messages"
  ID                        id-at-zimbraMailCanonicalAddress }

-- LDAP syntax length {256} rendered as DirectoryString{256}.
zimbraMailCatchAllAddress ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraMailCatchAllAddress"}
  LDAP-DESC                 "Address to catch all messages to specified domain"
  ID                        id-at-zimbraMailCatchAllAddress }

-- LDAP syntax length {256} rendered as DirectoryString{256}.
zimbraMailCatchAllCanonicalAddress ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraMailCatchAllCanonicalAddress"}
  LDAP-DESC                 "Catch all address to rewrite to"
  ID                        id-at-zimbraMailCatchAllCanonicalAddress }

-- LDAP syntax length {256} rendered as DirectoryString{256}.
zimbraMailCatchAllForwardingAddress ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraMailCatchAllForwardingAddress"}
  LDAP-DESC                 "Address to deliver catch all messages to"
  ID                        id-at-zimbraMailCatchAllForwardingAddress }

zimbraMailClearTextPasswordEnabled ATTRIBUTE ::= {
  WITH SYNTAX               BOOLEAN
  EQUALITY MATCHING RULE    booleanMatch
  SINGLE VALUE              TRUE
  LDAP-SYNTAX               boolean.&id
  LDAP-NAME                 {"zimbraMailClearTextPasswordEnabled"}
  LDAP-DESC                 "Whether to allow password sent to non-secured port when zimbraMailMode is mixed. If it set to TRUE the server will allow login with clear text AuthRequests and change password with clear text ChangePasswordRequest. If it set to FALSE the server will return an error if an attempt is made to ChangePasswordRequest or AuthRequest."
  ID                        id-at-zimbraMailClearTextPasswordEnabled }

zimbraMailContentMaxSize ATTRIBUTE ::= {
  WITH SYNTAX               INTEGER
  EQUALITY MATCHING RULE    integerMatch
  SINGLE VALUE              TRUE
  LDAP-SYNTAX               integer.&id
  LDAP-NAME                 {"zimbraMailContentMaxSize"}
  LDAP-DESC                 "Maximum size in bytes for the <content > element in SOAP. Mail content larger than this limit will be truncated."
  ID                        id-at-zimbraMailContentMaxSize }

zimbraMailDeliveryAddress ATTRIBUTE ::= {
  WITH SYNTAX               IA5String(SIZE (1..256))
  EQUALITY MATCHING RULE    caseIgnoreIA5Match
  SUBSTRINGS MATCHING RULE  caseIgnoreSubstringsMatch
  LDAP-SYNTAX               ia5String.&id
  LDAP-NAME                 {"zimbraMailDeliveryAddress"}
  LDAP-DESC                 "RFC822 email address of this recipient for local delivery"
  ID                        id-at-zimbraMailDeliveryAddress }

zimbraMailDiskStreamingThreshold ATTRIBUTE ::= {
  WITH SYNTAX               INTEGER
  EQUALITY MATCHING RULE    integerMatch
  SINGLE VALUE              TRUE
  LDAP-SYNTAX               integer.&id
  LDAP-NAME                 {"zimbraMailDiskStreamingThreshold"}
  LDAP-DESC                 "Incoming messages larger than this number of bytes are streamed to disk during LMTP delivery, instead of being read into memory. This limits memory consumption at the expense of higher disk utilization."
  ID                        id-at-zimbraMailDiskStreamingThreshold }

zimbraMailDomainQuota ATTRIBUTE ::= {
  WITH SYNTAX               INTEGER
  EQUALITY MATCHING RULE    integerMatch
  SINGLE VALUE              TRUE
  LDAP-SYNTAX               integer.&id
  LDAP-NAME                 {"zimbraMailDomainQuota"}
  LDAP-DESC                 "Maximum mailbox quota for the domain in bytes. The effective quota for a mailbox would be the minimum of this and zimbraMailQuota."
  ID                        id-at-zimbraMailDomainQuota }

zimbraMailDumpsterLifetime ATTRIBUTE ::= {
  WITH SYNTAX               IA5String(SIZE (1..32))
  EQUALITY MATCHING RULE    caseIgnoreIA5Match
  SINGLE VALUE              TRUE
  LDAP-SYNTAX               ia5String.&id
  LDAP-NAME                 {"zimbraMailDumpsterLifetime"}
  LDAP-DESC                 "Retention period of messages in the dumpster. 0 means that all messages will be retained. . Must be in valid duration format: {digits}{time-unit}. digits: 0-9, time-unit: [hmsd]|ms. h - hours, m - minutes, s - seconds, d - days, ms - milliseconds. If time unit is not specified, the default is s(seconds)."
  ID                        id-at-zimbraMailDumpsterLifetime }

zimbraMailEmptyFolderBatchSize ATTRIBUTE ::= {
  WITH SYNTAX               INTEGER
  EQUALITY MATCHING RULE    integerMatch
  SINGLE VALUE              TRUE
  LDAP-SYNTAX               integer.&id
  LDAP-NAME                 {"zimbraMailEmptyFolderBatchSize"}
  LDAP-DESC                 "Maximum number of messages to delete during a single transaction when emptying a large folder."
  ID                        id-at-zimbraMailEmptyFolderBatchSize }

zimbraMailEmptyFolderBatchThreshold ATTRIBUTE ::= {
  WITH SYNTAX               INTEGER
  EQUALITY MATCHING RULE    integerMatch
  SINGLE VALUE              TRUE
  LDAP-SYNTAX               integer.&id
  LDAP-NAME                 {"zimbraMailEmptyFolderBatchThreshold"}
  LDAP-DESC                 "Deprecated since: 8.0.0. Empty folder operation now always deletes items in batches, hence a threshold is no longer applicable.. Orig desc: Folders that contain more than this many messages will be emptied in batches of size zimbraMailEmptyFolderBatchSize."
  ID                        id-at-zimbraMailEmptyFolderBatchThreshold }

zimbraMailFileDescriptorBufferSize ATTRIBUTE ::= {
  WITH SYNTAX               INTEGER
  EQUALITY MATCHING RULE    integerMatch
  SINGLE VALUE              TRUE
  LDAP-SYNTAX               integer.&id
  LDAP-NAME                 {"zimbraMailFileDescriptorBufferSize"}
  LDAP-DESC                 "Number of bytes to buffer in memory per file descriptor in the cache. Larger values result in fewer disk reads, but increase memory consumption."
  ID                        id-at-zimbraMailFileDescriptorBufferSize }

zimbraMailFileDescriptorCacheSize ATTRIBUTE ::= {
  WITH SYNTAX               INTEGER
  EQUALITY MATCHING RULE    integerMatch
  SINGLE VALUE              TRUE
  LDAP-SYNTAX               integer.&id
  LDAP-NAME                 {"zimbraMailFileDescriptorCacheSize"}
  LDAP-DESC                 "Maximum number of file descriptors that are opened for accessing message content."
  ID                        id-at-zimbraMailFileDescriptorCacheSize }

zimbraMailForwardingAddress ATTRIBUTE ::= {
  WITH SYNTAX               IA5String(SIZE (1..256))
  EQUALITY MATCHING RULE    caseIgnoreIA5Match
  SUBSTRINGS MATCHING RULE  caseIgnoreSubstringsMatch
  LDAP-SYNTAX               ia5String.&id
  LDAP-NAME                 {"zimbraMailForwardingAddress"}
  LDAP-DESC                 "RFC822 forwarding address for an account"
  ID                        id-at-zimbraMailForwardingAddress }

zimbraMailForwardingAddressMaxLength ATTRIBUTE ::= {
  WITH SYNTAX               INTEGER
  EQUALITY MATCHING RULE    integerMatch
  SINGLE VALUE              TRUE
  LDAP-SYNTAX               integer.&id
  LDAP-NAME                 {"zimbraMailForwardingAddressMaxLength"}
  LDAP-DESC                 "max number of chars in zimbraPrefMailForwardingAddress"
  ID                        id-at-zimbraMailForwardingAddressMaxLength }

zimbraMailForwardingAddressMaxNumAddrs ATTRIBUTE ::= {
  WITH SYNTAX               INTEGER
  EQUALITY MATCHING RULE    integerMatch
  SINGLE VALUE              TRUE
  LDAP-SYNTAX               integer.&id
  LDAP-NAME                 {"zimbraMailForwardingAddressMaxNumAddrs"}
  LDAP-DESC                 "max number of email addresses in zimbraPrefMailForwardingAddress"
  ID                        id-at-zimbraMailForwardingAddressMaxNumAddrs }

zimbraMailHighlightObjectsMaxSize ATTRIBUTE ::= {
  WITH SYNTAX               INTEGER
  EQUALITY MATCHING RULE    integerMatch
  SINGLE VALUE              TRUE
  LDAP-SYNTAX               integer.&id
  LDAP-NAME                 {"zimbraMailHighlightObjectsMaxSize"}
  LDAP-DESC                 "max size in KB of text emails that will automatically highlight objects"
  ID                        id-at-zimbraMailHighlightObjectsMaxSize }

zimbraMailHost ATTRIBUTE ::= {
  WITH SYNTAX               IA5String(SIZE (1..256))
  EQUALITY MATCHING RULE    caseIgnoreIA5Match
  SUBSTRINGS MATCHING RULE  caseIgnoreSubstringsMatch
  SINGLE VALUE              TRUE
  LDAP-SYNTAX               ia5String.&id
  LDAP-NAME                 {"zimbraMailHost"}
  LDAP-DESC                 "the server hosting the account's mailbox"
  ID                        id-at-zimbraMailHost }

-- LDAP syntax length {256} rendered as DirectoryString{256}.
zimbraMailHostPool ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraMailHostPool"}
  LDAP-DESC                 "servers that an account can be initially provisioned on"
  ID                        id-at-zimbraMailHostPool }

zimbraMailIdleSessionTimeout ATTRIBUTE ::= {
  WITH SYNTAX               IA5String(SIZE (1..32))
  EQUALITY MATCHING RULE    caseIgnoreIA5Match
  SINGLE VALUE              TRUE
  LDAP-SYNTAX               ia5String.&id
  LDAP-NAME                 {"zimbraMailIdleSessionTimeout"}
  LDAP-DESC                 "idle timeout. Must be in valid duration format: {digits}{time-unit}. digits: 0-9, time-unit: [hmsd]|ms. h - hours, m - minutes, s - seconds, d - days, ms - milliseconds. If time unit is not specified, the default is s(seconds)."
  ID                        id-at-zimbraMailIdleSessionTimeout }

zimbraMailKeepOutWebCrawlers ATTRIBUTE ::= {
  WITH SYNTAX               BOOLEAN
  EQUALITY MATCHING RULE    booleanMatch
  SINGLE VALUE              TRUE
  LDAP-SYNTAX               boolean.&id
  LDAP-NAME                 {"zimbraMailKeepOutWebCrawlers"}
  LDAP-DESC                 "When set to true, robots.txt on mailboxd will be set up to keep web crawlers out"
  ID                        id-at-zimbraMailKeepOutWebCrawlers }

zimbraMailLastPurgedMailboxId ATTRIBUTE ::= {
  WITH SYNTAX               INTEGER
  EQUALITY MATCHING RULE    integerMatch
  SINGLE VALUE              TRUE
  LDAP-SYNTAX               integer.&id
  LDAP-NAME                 {"zimbraMailLastPurgedMailboxId"}
  LDAP-DESC                 "Deprecated since: 5.0.7. deprecated per bug 28842. Orig desc: The id of the last purged mailbox."
  ID                        id-at-zimbraMailLastPurgedMailboxId }

zimbraMailLocalBind ATTRIBUTE ::= {
  WITH SYNTAX               BOOLEAN
  EQUALITY MATCHING RULE    booleanMatch
  SINGLE VALUE              TRUE
  LDAP-SYNTAX               boolean.&id
  LDAP-NAME                 {"zimbraMailLocalBind"}
  LDAP-DESC                 "Specifies whether the http server should bound to localhost or not. This is an immutable property and is generated based on zimbraMailMode and zimbraMailBindAddress."
  ID                        id-at-zimbraMailLocalBind }

zimbraMailMessageLifetime ATTRIBUTE ::= {
  WITH SYNTAX               IA5String(SIZE (1..32))
  EQUALITY MATCHING RULE    caseIgnoreIA5Match
  SINGLE VALUE              TRUE
  LDAP-SYNTAX               ia5String.&id
  LDAP-NAME                 {"zimbraMailMessageLifetime"}
  LDAP-DESC                 "lifetime of a mail message regardless of location. Must be in valid duration format: {digits}{time-unit}. digits: 0-9, time-unit: [hmsd]|ms. h - hours, m - minutes, s - seconds, d - days, ms - milliseconds. If time unit is not specified, the default is s(seconds)."
  ID                        id-at-zimbraMailMessageLifetime }

zimbraMailMinPollingInterval ATTRIBUTE ::= {
  WITH SYNTAX               IA5String(SIZE (1..32))
  EQUALITY MATCHING RULE    caseIgnoreIA5Match
  SINGLE VALUE              TRUE
  LDAP-SYNTAX               ia5String.&id
  LDAP-NAME                 {"zimbraMailMinPollingInterval"}
  LDAP-DESC                 "minimum allowed value for zimbraPrefMailPollingInterval. Must be in valid duration format: {digits}{time-unit}. digits: 0-9, time-unit: [hmsd]|ms. h - hours, m - minutes, s - seconds, d - days, ms - milliseconds. If time unit is not specified, the default is s(seconds)."
  ID                        id-at-zimbraMailMinPollingInterval }

-- LDAP syntax length {32} rendered as DirectoryString{32}.
zimbraMailMode ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraMailMode"}
  LDAP-DESC                 "whether to run HTTP or HTTPS or both/mixed mode or redirect mode. See also related attributes zimbraMailPort and zimbraMailSSLPort"
  ID                        id-at-zimbraMailMode }

zimbraMailOutgoingSieveScript ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMailOutgoingSieveScript"}
  LDAP-DESC                 "sieve script generated from user outgoing filter rules"
  ID                        id-at-zimbraMailOutgoingSieveScript }

zimbraMailPort ATTRIBUTE ::= {
  WITH SYNTAX               INTEGER
  EQUALITY MATCHING RULE    integerMatch
  SINGLE VALUE              TRUE
  LDAP-SYNTAX               integer.&id
  LDAP-NAME                 {"zimbraMailPort"}
  LDAP-DESC                 "HTTP port for end-user UI"
  ID                        id-at-zimbraMailPort }

zimbraMailProxyMaxFails ATTRIBUTE ::= {
  WITH SYNTAX               INTEGER
  EQUALITY MATCHING RULE    integerMatch
  SINGLE VALUE              TRUE
  LDAP-SYNTAX               integer.&id
  LDAP-NAME                 {"zimbraMailProxyMaxFails"}
  LDAP-DESC                 "The max number of unsuccessful attempts to connect to the current server (as an upstream). If this number is reached, proxy will refuse to connect to the current server, wait for zimbraMailProxyReconnectTimeout and then try to reconnect. Default value is 1. Setting this to 0 means turning this check off."
  ID                        id-at-zimbraMailProxyMaxFails }

zimbraMailProxyPort ATTRIBUTE ::= {
  WITH SYNTAX               INTEGER
  EQUALITY MATCHING RULE    integerMatch
  SINGLE VALUE              TRUE
  LDAP-SYNTAX               integer.&id
  LDAP-NAME                 {"zimbraMailProxyPort"}
  LDAP-DESC                 "HTTP proxy port"
  ID                        id-at-zimbraMailProxyPort }

zimbraMailProxyReconnectTimeout ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMailProxyReconnectTimeout"}
  LDAP-DESC                 "the time in sec that proxy will reconnect the current server (as an upstream) after connection errors happened before"
  ID                        id-at-zimbraMailProxyReconnectTimeout }

zimbraMailPurgeBatchSize ATTRIBUTE ::= {
  WITH SYNTAX               INTEGER
  EQUALITY MATCHING RULE    integerMatch
  SINGLE VALUE              TRUE
  LDAP-SYNTAX               integer.&id
  LDAP-NAME                 {"zimbraMailPurgeBatchSize"}
  LDAP-DESC                 "Maximum number of messages to delete from a folder during a single purge operation. If the limit is exceeded, the mailbox is purged again at the end of the purge cycle until all qualifying messages are purged."
  ID                        id-at-zimbraMailPurgeBatchSize }

zimbraMailPurgeSleepInterval ATTRIBUTE ::= {
  WITH SYNTAX               IA5String(SIZE (1..32))
  EQUALITY MATCHING RULE    caseIgnoreIA5Match
  SINGLE VALUE              TRUE
  LDAP-SYNTAX               ia5String.&id
  LDAP-NAME                 {"zimbraMailPurgeSleepInterval"}
  LDAP-DESC                 "Sleep time between subsequent mailbox purges. 0 means that mailbox purging is disabled. . Must be in valid duration format: {digits}{time-unit}. digits: 0-9, time-unit: [hmsd]|ms. h - hours, m - minutes, s - seconds, d - days, ms - milliseconds. If time unit is not specified, the default is s(seconds)."
  ID                        id-at-zimbraMailPurgeSleepInterval }

zimbraMailPurgeSystemPolicy ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMailPurgeSystemPolicy"}
  LDAP-DESC                 "System purge policy, encoded as metadata. Users can apply these policy elements to their folders and tags. If the system policy changes, user settings are automatically updated with the change."
  ID                        id-at-zimbraMailPurgeSystemPolicy }

zimbraMailPurgeUseChangeDateForSpam ATTRIBUTE ::= {
  WITH SYNTAX               BOOLEAN
  EQUALITY MATCHING RULE    booleanMatch
  SINGLE VALUE              TRUE
  LDAP-SYNTAX               boolean.&id
  LDAP-NAME                 {"zimbraMailPurgeUseChangeDateForSpam"}
  LDAP-DESC                 "If TRUE, a message is purged from Spam based on the date that it was moved to the Spam folder. If FALSE, a message is purged from Spam based on the date that it was added to the mailbox."
  ID                        id-at-zimbraMailPurgeUseChangeDateForSpam }

zimbraMailPurgeUseChangeDateForTrash ATTRIBUTE ::= {
  WITH SYNTAX               BOOLEAN
  EQUALITY MATCHING RULE    booleanMatch
  SINGLE VALUE              TRUE
  LDAP-SYNTAX               boolean.&id
  LDAP-NAME                 {"zimbraMailPurgeUseChangeDateForTrash"}
  LDAP-DESC                 "If TRUE, a message is purged from trash based on the date that it was moved to the Trash folder. If FALSE, a message is purged from Trash based on the date that it was added to the mailbox."
  ID                        id-at-zimbraMailPurgeUseChangeDateForTrash }

zimbraMailQuota ATTRIBUTE ::= {
  WITH SYNTAX               INTEGER
  EQUALITY MATCHING RULE    integerMatch
  SINGLE VALUE              TRUE
  LDAP-SYNTAX               integer.&id
  LDAP-NAME                 {"zimbraMailQuota"}
  LDAP-DESC                 "mail quota in bytes"
  ID                        id-at-zimbraMailQuota }

zimbraMailRedirectSetEnvelopeSender ATTRIBUTE ::= {
  WITH SYNTAX               BOOLEAN
  EQUALITY MATCHING RULE    booleanMatch
  SINGLE VALUE              TRUE
  LDAP-SYNTAX               boolean.&id
  LDAP-NAME                 {"zimbraMailRedirectSetEnvelopeSender"}
  LDAP-DESC                 "If TRUE, the envelope sender of a message redirected by mail filters will be set to the users address. If FALSE, the envelope sender will be set to the From address of the redirected message."
  ID                        id-at-zimbraMailRedirectSetEnvelopeSender }

-- LDAP syntax length {32} rendered as DirectoryString{32}.
zimbraMailReferMode ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraMailReferMode"}
  LDAP-DESC                 "whether to send back a refer tag in an auth response to force a client redirect. always - always send refer wronghost - send refer if only if the account being authenticated does not live on this mail host reverse-proxied - reverse proxy is in place and should never send refer"
  ID                        id-at-zimbraMailReferMode }

-- LDAP syntax length {128} rendered as DirectoryString{128}.
zimbraMailSSLBindAddress ATTRIBUTE ::= {
  WITH SYNTAX               DirectoryString{128}
  EQUALITY MATCHING RULE    caseIgnoreMatch
  SUBSTRINGS MATCHING RULE  caseIgnoreSubstringsMatch
  SINGLE VALUE              TRUE
  LDAP-SYNTAX               directoryString.&id
  LDAP-NAME                 {"zimbraMailSSLBindAddress"}
  LDAP-DESC                 "interface address on which HTTPS server should listen; if empty, binds to all interfaces"
  ID                        id-at-zimbraMailSSLBindAddress }

-- LDAP syntax length {128} rendered as DirectoryString{128}.
zimbraMailSSLClientCertBindAddress ATTRIBUTE ::= {
  WITH SYNTAX               DirectoryString{128}
  EQUALITY MATCHING RULE    caseIgnoreMatch
  SUBSTRINGS MATCHING RULE  caseIgnoreSubstringsMatch
  SINGLE VALUE              TRUE
  LDAP-SYNTAX               directoryString.&id
  LDAP-NAME                 {"zimbraMailSSLClientCertBindAddress"}
  LDAP-DESC                 "interface address on which HTTPS server accepting client certificates should listen; if empty, binds to all interfaces"
  ID                        id-at-zimbraMailSSLClientCertBindAddress }

-- LDAP syntax length {32} rendered as DirectoryString{32}.
zimbraMailSSLClientCertMode ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraMailSSLClientCertMode"}
  LDAP-DESC                 "enable authentication via X.509 Client Certificate. Disabled: client authentication is disabled. NeedClientAuth: client authentication is required during SSL handshake on the SSL mutual authentication port(see zimbraMailSSLClientCertPort). The SSL handshake will fail if the client does not present a certificate to authenticate. WantClientAuth: client authentication is requested during SSL handshake on the SSL mutual authentication port(see zimbraMailSSLClientCertPort). The SSL handshake will still proceed if the client does not present a certificate to authenticate. In the case when client does not send a certificate, user will be redirected to the usual entry page of the requested webapp, where username/password is prompted."
  ID                        id-at-zimbraMailSSLClientCertMode }

zimbraMailSSLClientCertOCSPEnabled ATTRIBUTE ::= {
  WITH SYNTAX               BOOLEAN
  EQUALITY MATCHING RULE    booleanMatch
  SINGLE VALUE              TRUE
  LDAP-SYNTAX               boolean.&id
  LDAP-NAME                 {"zimbraMailSSLClientCertOCSPEnabled"}
  LDAP-DESC                 "enable OCSP support for two way authentication."
  ID                        id-at-zimbraMailSSLClientCertOCSPEnabled }

zimbraMailSSLClientCertPort ATTRIBUTE ::= {
  WITH SYNTAX               INTEGER
  EQUALITY MATCHING RULE    integerMatch
  SINGLE VALUE              TRUE
  LDAP-SYNTAX               integer.&id
  LDAP-NAME                 {"zimbraMailSSLClientCertPort"}
  LDAP-DESC                 "SSL port requesting client certificate for end-user UI"
  ID                        id-at-zimbraMailSSLClientCertPort }

zimbraMailSSLClientCertPrincipalMap ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMailSSLClientCertPrincipalMap"}
  LDAP-DESC                 "Map from a certificate field to a Zimbra account key that can uniquely identify a Zimbra account for client certificate authentication. Value is a comma-separated list of mapping rules, each mapping maps a certificate field to a Zimbra account key. Each is attempted in sequence until a unique account can be resolved. e.g. a value can be: SUBJECTALTNAME_OTHERNAME_UPN=zimbraForeignPrincipal,(uid=%{SUBJECT_CN}) value: comma-separated mapping-rule mapping-rule: {cert-field-to-zimbra-key-map} | {LDAP-filter} cert-field-to-zimbra-key-map: {certificate-field}={Zimbra-account-key} certificate-field: SUBJECT_{an RDN attr, e.g. CN}: a RND in DN of Subject SUBJECT_DN: entire DN of Subject SUBJECTALTNAME_OTHERNAME_UPN: UPN(aka Principal Name) in otherName in subjectAltName extension SUBJECTALTNAME_RFC822NAME: rfc822Name in subjectAltName extension Zimbra-account-key: name: primary name or any of the aliases of an account zimbraId: zimbraId of an account zimbraForeignPrincipal: zimbraForeignPrincipal of an account. The matching value on the zimbraForeignPrincipal must be prefixed with ""cert {supported-certificate-filed}:"" e.g. cert SUBJECTALTNAME_OTHERNAME_UPN:123456@mydomain LDAP-filter: An LDAP filter template with placeholders to be substituted by certificate field values. (objectClass=zimbraAccount) is internally ANDed with the supplied filter. e.g. (|(uid=%{SUBJECT_CN})(mail=%{SUBJECTALTNAME_RFC822NAME})) Note: it is recommended not to use LDAP-filter rule, as it will trigger an LDAP search for each cert auth request. LDAP-filter is disabled by default. To enable it globally, set zimbraMailSSLClientCertPrincipalMapLdapFilterEnabled on global config to TRUE. If LDAP-filter is not enabled, all client certificate authentication will fail on domains configured with LDAP-filter."
  ID                        id-at-zimbraMailSSLClientCertPrincipalMap }

zimbraMailSSLClientCertPrincipalMapLdapFilterEnabled ATTRIBUTE ::= {
  WITH SYNTAX               BOOLEAN
  EQUALITY MATCHING RULE    booleanMatch
  SINGLE VALUE              TRUE
  LDAP-SYNTAX               boolean.&id
  LDAP-NAME                 {"zimbraMailSSLClientCertPrincipalMapLdapFilterEnabled"}
  LDAP-DESC                 "whether to enable LDAP-filter in zimbraMailSSLClientCertPrincipalMap"
  ID                        id-at-zimbraMailSSLClientCertPrincipalMapLdapFilterEnabled }

zimbraMailSSLPort ATTRIBUTE ::= {
  WITH SYNTAX               INTEGER
  EQUALITY MATCHING RULE    integerMatch
  SINGLE VALUE              TRUE
  LDAP-SYNTAX               integer.&id
  LDAP-NAME                 {"zimbraMailSSLPort"}
  LDAP-DESC                 "SSL port for end-user UI"
  ID                        id-at-zimbraMailSSLPort }

zimbraMailSSLProxyClientCertPort ATTRIBUTE ::= {
  WITH SYNTAX               INTEGER
  EQUALITY MATCHING RULE    integerMatch
  SINGLE VALUE              TRUE
  LDAP-SYNTAX               integer.&id
  LDAP-NAME                 {"zimbraMailSSLProxyClientCertPort"}
  LDAP-DESC                 "SSL client certificate port for HTTP proxy"
  ID                        id-at-zimbraMailSSLProxyClientCertPort }

zimbraMailSSLProxyPort ATTRIBUTE ::= {
  WITH SYNTAX               INTEGER
  EQUALITY MATCHING RULE    integerMatch
  SINGLE VALUE              TRUE
  LDAP-SYNTAX               integer.&id
  LDAP-NAME                 {"zimbraMailSSLProxyPort"}
  LDAP-DESC                 "SSL port HTTP proxy"
  ID                        id-at-zimbraMailSSLProxyPort }

zimbraMailSieveScript ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMailSieveScript"}
  LDAP-DESC                 "sieve script generated from user filter rules"
  ID                        id-at-zimbraMailSieveScript }

zimbraMailSignatureMaxLength ATTRIBUTE ::= {
  WITH SYNTAX               INTEGER
  EQUALITY MATCHING RULE    integerMatch
  SINGLE VALUE              TRUE
  LDAP-SYNTAX               integer.&id
  LDAP-NAME                 {"zimbraMailSignatureMaxLength"}
  LDAP-DESC                 "maximum length of mail signature, 0 means unlimited."
  ID                        id-at-zimbraMailSignatureMaxLength }

zimbraMailSpamLifetime ATTRIBUTE ::= {
  WITH SYNTAX               IA5String(SIZE (1..32))
  EQUALITY MATCHING RULE    caseIgnoreIA5Match
  SINGLE VALUE              TRUE
  LDAP-SYNTAX               ia5String.&id
  LDAP-NAME                 {"zimbraMailSpamLifetime"}
  LDAP-DESC                 "Retention period of messages in the Junk folder. 0 means that all messages will be retained. This admin-modifiable attribute works in conjunction with zimbraPrefJunkLifetime, which is user-modifiable. The shorter duration is used. . Must be in valid duration format: {digits}{time-unit}. digits: 0-9, time-unit: [hmsd]|ms. h - hours, m - minutes, s - seconds, d - days, ms - milliseconds. If time unit is not specified, the default is s(seconds)."
  ID                        id-at-zimbraMailSpamLifetime }

-- LDAP syntax length {32} rendered as DirectoryString{32}.
zimbraMailStatus ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraMailStatus"}
  LDAP-DESC                 "mail delivery status (enabled/disabled)"
  ID                        id-at-zimbraMailStatus }

-- LDAP syntax length {32} rendered as DirectoryString{32}.
zimbraMailThreadingAlgorithm ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraMailThreadingAlgorithm"}
  LDAP-DESC                 "The algorithm to use when aggregating new messages into conversations. Possible values are: - ""none"": no conversation threading is performed. - ""subject"": the message will be threaded based solely on its normalized subject. - ""strict"": only the threading message headers (References, In-Reply-To, Message-ID, and Resent-Message-ID) are used to correlate messages. No checking of normalized subjects is performed. - ""references"": the same logic as ""strict"" with the constraints slightly altered so that the non-standard Thread-Index header is considered when threading messages and that a reply message lacking References and In-Reply-To headers will fall back to using subject-based threading. - ""subjrefs"": the same logic as ""references"" with the further caveat that changes in the normalized subject will break a thread in two."
  ID                        id-at-zimbraMailThreadingAlgorithm }

zimbraMailTransport ATTRIBUTE ::= {
  WITH SYNTAX               IA5String(SIZE (1..320))
  EQUALITY MATCHING RULE    caseIgnoreIA5Match
  SUBSTRINGS MATCHING RULE  caseIgnoreSubstringsMatch
  SINGLE VALUE              TRUE
  LDAP-SYNTAX               ia5String.&id
  LDAP-NAME                 {"zimbraMailTransport"}
  LDAP-DESC                 "where to deliver parameter for use in postfix transport_maps"
  ID                        id-at-zimbraMailTransport }

zimbraMailTrashLifetime ATTRIBUTE ::= {
  WITH SYNTAX               IA5String(SIZE (1..32))
  EQUALITY MATCHING RULE    caseIgnoreIA5Match
  SINGLE VALUE              TRUE
  LDAP-SYNTAX               ia5String.&id
  LDAP-NAME                 {"zimbraMailTrashLifetime"}
  LDAP-DESC                 "Retention period of messages in the Trash folder. 0 means that all messages will be retained. This admin-modifiable attribute works in conjunction with zimbraPrefTrashLifetime, which is user-modifiable. The shorter duration is used. . Must be in valid duration format: {digits}{time-unit}. digits: 0-9, time-unit: [hmsd]|ms. h - hours, m - minutes, s - seconds, d - days, ms - milliseconds. If time unit is not specified, the default is s(seconds)."
  ID                        id-at-zimbraMailTrashLifetime }

zimbraMailTrustedIP ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraMailTrustedIP"}
  LDAP-DESC                 "In our web app, AJAX and standard html client, we have support for adding the HTTP client IP address as X-Originating-IP in an outbound message. We also use the HTTP client IP address in our logging. In the case of standard client making connections to the SOAP layer, the JSP layer tells the SOAP layer in a http header what the remote HTTP client address is. In the case where nginx or some other proxy layer is fronting our webapps, the proxy tells the SOAP/JSP layers in a http header what the real HTTP client s address is. Our SOAP/JSP layers will trust the client/proxy only if the IP address of the client/proxy is one of the IPs listed in this attribute."
  ID                        id-at-zimbraMailTrustedIP }

zimbraMailTrustedSenderListMaxNumEntries ATTRIBUTE ::= {
  WITH SYNTAX               INTEGER
  EQUALITY MATCHING RULE    integerMatch
  SINGLE VALUE              TRUE
  LDAP-SYNTAX               integer.&id
  LDAP-NAME                 {"zimbraMailTrustedSenderListMaxNumEntries"}
  LDAP-DESC                 "Maximum number of entries for zimbraPrefMailTrustedSenderList."
  ID                        id-at-zimbraMailTrustedSenderListMaxNumEntries }

-- LDAP syntax length {1024} rendered as DirectoryString{1024}.
zimbraMailURL ATTRIBUTE ::= {
  WITH SYNTAX               DirectoryString{1024}
  EQUALITY MATCHING RULE    caseIgnoreMatch
  SUBSTRINGS MATCHING RULE  caseIgnoreSubstringsMatch
  SINGLE VALUE              TRUE
  LDAP-SYNTAX               directoryString.&id
  LDAP-NAME                 {"zimbraMailURL"}
  LDAP-DESC                 "URL prefix for where the zimbra app resides on this server"
  ID                        id-at-zimbraMailURL }

zimbraMailUncompressedCacheMaxBytes ATTRIBUTE ::= {
  WITH SYNTAX               INTEGER
  EQUALITY MATCHING RULE    integerMatch
  SINGLE VALUE              TRUE
  LDAP-SYNTAX               integer.&id
  LDAP-NAME                 {"zimbraMailUncompressedCacheMaxBytes"}
  LDAP-DESC                 "Deprecated since: 6.0.7. Deprecated per bug 43497. The number of uncompressed files on disk will never exceed zimbraMailFileDescriptorCacheSize.. Orig desc: max number of bytes stored in the uncompressed blob cache on disk"
  ID                        id-at-zimbraMailUncompressedCacheMaxBytes }

zimbraMailUncompressedCacheMaxFiles ATTRIBUTE ::= {
  WITH SYNTAX               INTEGER
  EQUALITY MATCHING RULE    integerMatch
  SINGLE VALUE              TRUE
  LDAP-SYNTAX               integer.&id
  LDAP-NAME                 {"zimbraMailUncompressedCacheMaxFiles"}
  LDAP-DESC                 "Deprecated since: 6.0.7. Deprecated per bug 43497. The number of uncompressed files on disk will never exceed zimbraMailFileDescriptorCacheSize.. Orig desc: max number of files in the uncompressed blob cache on disk"
  ID                        id-at-zimbraMailUncompressedCacheMaxFiles }

zimbraMailUseDirectBuffers ATTRIBUTE ::= {
  WITH SYNTAX               BOOLEAN
  EQUALITY MATCHING RULE    booleanMatch
  SINGLE VALUE              TRUE
  LDAP-SYNTAX               boolean.&id
  LDAP-NAME                 {"zimbraMailUseDirectBuffers"}
  LDAP-DESC                 "Used to control whether Java NIO direct buffers are used. Value is propagated to Jetty configuration. In the future, other NIO pieces (IMAP/POP/LMTP) will also honor this."
  ID                        id-at-zimbraMailUseDirectBuffers }

zimbraMailWhitelistMaxNumEntries ATTRIBUTE ::= {
  WITH SYNTAX               INTEGER
  EQUALITY MATCHING RULE    integerMatch
  SINGLE VALUE              TRUE
  LDAP-SYNTAX               integer.&id
  LDAP-NAME                 {"zimbraMailWhitelistMaxNumEntries"}
  LDAP-DESC                 "Maximum number of entries for per user white list. This restricts the number of values that can be set on the amavisWhitelistSender attribute of an account. If set to 0, the per user white list feature is disabled."
  ID                        id-at-zimbraMailWhitelistMaxNumEntries }

zimbraMailboxLocationBeforeMove ATTRIBUTE ::= {
  WITH SYNTAX               IA5String(SIZE (1..256))
  EQUALITY MATCHING RULE    caseIgnoreIA5Match
  SUBSTRINGS MATCHING RULE  caseIgnoreSubstringsMatch
  SINGLE VALUE              TRUE
  LDAP-SYNTAX               ia5String.&id
  LDAP-NAME                 {"zimbraMailboxLocationBeforeMove"}
  LDAP-DESC                 "serverId:mboxId of mailbox before being moved"
  ID                        id-at-zimbraMailboxLocationBeforeMove }

zimbraMailboxMoveSkipBlobs ATTRIBUTE ::= {
  WITH SYNTAX               BOOLEAN
  EQUALITY MATCHING RULE    booleanMatch
  SINGLE VALUE              TRUE
  LDAP-SYNTAX               boolean.&id
  LDAP-NAME                 {"zimbraMailboxMoveSkipBlobs"}
  LDAP-DESC                 "if true, exclude blobs (HSM or not) from mailbox move"
  ID                        id-at-zimbraMailboxMoveSkipBlobs }

zimbraMailboxMoveSkipHsmBlobs ATTRIBUTE ::= {
  WITH SYNTAX               BOOLEAN
  EQUALITY MATCHING RULE    booleanMatch
  SINGLE VALUE              TRUE
  LDAP-SYNTAX               boolean.&id
  LDAP-NAME                 {"zimbraMailboxMoveSkipHsmBlobs"}
  LDAP-DESC                 "if true, exclude blobs on secondary (HSM) volumes from mailbox move"
  ID                        id-at-zimbraMailboxMoveSkipHsmBlobs }

zimbraMailboxMoveSkipSearchIndex ATTRIBUTE ::= {
  WITH SYNTAX               BOOLEAN
  EQUALITY MATCHING RULE    booleanMatch
  SINGLE VALUE              TRUE
  LDAP-SYNTAX               boolean.&id
  LDAP-NAME                 {"zimbraMailboxMoveSkipSearchIndex"}
  LDAP-DESC                 "if true, exclude search index from mailbox move"
  ID                        id-at-zimbraMailboxMoveSkipSearchIndex }

zimbraMailboxMoveTempDir ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMailboxMoveTempDir"}
  LDAP-DESC                 "temp directory for mailbox move"
  ID                        id-at-zimbraMailboxMoveTempDir }

zimbraMailboxdSSLProtocols ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraMailboxdSSLProtocols"}
  LDAP-DESC                 "List of SSL/TLS protocols (as documented by SunJSSE Provider Protocols and used in setEnabledProtocols) to be enabled in Jetty for HTTPS, IMAPS, POP3S, and STARTTLS (including LMTP)"
  ID                        id-at-zimbraMailboxdSSLProtocols }

zimbraMaxContactsPerPage ATTRIBUTE ::= {
  WITH SYNTAX               INTEGER
  EQUALITY MATCHING RULE    integerMatch
  SINGLE VALUE              TRUE
  LDAP-SYNTAX               integer.&id
  LDAP-NAME                 {"zimbraMaxContactsPerPage"}
  LDAP-DESC                 "max number of contacts per page, Web client (not server) verifies that zimbraPrefContactsPerPage should not exceed this attribute."
  ID                        id-at-zimbraMaxContactsPerPage }

zimbraMaxMailItemsPerPage ATTRIBUTE ::= {
  WITH SYNTAX               INTEGER
  EQUALITY MATCHING RULE    integerMatch
  SINGLE VALUE              TRUE
  LDAP-SYNTAX               integer.&id
  LDAP-NAME                 {"zimbraMaxMailItemsPerPage"}
  LDAP-DESC                 "max number of messages/conversations per page, Web client (not server) verifies that zimbraPrefMailItemsPerPage should not exceed this attribute."
  ID                        id-at-zimbraMaxMailItemsPerPage }

zimbraMaxVoiceItemsPerPage ATTRIBUTE ::= {
  WITH SYNTAX               INTEGER
  EQUALITY MATCHING RULE    integerMatch
  SINGLE VALUE              TRUE
  LDAP-SYNTAX               integer.&id
  LDAP-NAME                 {"zimbraMaxVoiceItemsPerPage"}
  LDAP-DESC                 "max number of voice items per page, Web client (not server) verifies that zimbraPrefVoiceItemsPerPage should not exceed this attribute."
  ID                        id-at-zimbraMaxVoiceItemsPerPage }

-- LDAP syntax length {256} rendered as DirectoryString{256}.
zimbraMemberOf ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraMemberOf"}
  LDAP-DESC                 "dynamic group membership"
  ID                        id-at-zimbraMemberOf }

-- LDAP syntax length {128} rendered as DirectoryString{128}.
zimbraMemcachedBindAddress ATTRIBUTE ::= {
  WITH SYNTAX               DirectoryString{128}
  EQUALITY MATCHING RULE    caseIgnoreMatch
  SUBSTRINGS MATCHING RULE  caseIgnoreSubstringsMatch
  LDAP-SYNTAX               directoryString.&id
  LDAP-NAME                 {"zimbraMemcachedBindAddress"}
  LDAP-DESC                 "interface address on which memcached server should listen"
  ID                        id-at-zimbraMemcachedBindAddress }

zimbraMemcachedBindPort ATTRIBUTE ::= {
  WITH SYNTAX               INTEGER
  EQUALITY MATCHING RULE    integerMatch
  SINGLE VALUE              TRUE
  LDAP-SYNTAX               integer.&id
  LDAP-NAME                 {"zimbraMemcachedBindPort"}
  LDAP-DESC                 "port number on which memcached server should listen"
  ID                        id-at-zimbraMemcachedBindPort }

zimbraMemcachedClientBinaryProtocolEnabled ATTRIBUTE ::= {
  WITH SYNTAX               BOOLEAN
  EQUALITY MATCHING RULE    booleanMatch
  SINGLE VALUE              TRUE
  LDAP-SYNTAX               boolean.&id
  LDAP-NAME                 {"zimbraMemcachedClientBinaryProtocolEnabled"}
  LDAP-DESC                 "if true, use binary protocol of memcached; if false, use ascii protocol"
  ID                        id-at-zimbraMemcachedClientBinaryProtocolEnabled }

zimbraMemcachedClientExpirySeconds ATTRIBUTE ::= {
  WITH SYNTAX               INTEGER
  EQUALITY MATCHING RULE    integerMatch
  SINGLE VALUE              TRUE
  LDAP-SYNTAX               integer.&id
  LDAP-NAME                 {"zimbraMemcachedClientExpirySeconds"}
  LDAP-DESC                 "default expiration time in seconds for memcached values; default is 1 day"
  ID                        id-at-zimbraMemcachedClientExpirySeconds }

zimbraMemcachedClientHashAlgorithm ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMemcachedClientHashAlgorithm"}
  LDAP-DESC                 "memcached hash algorithm"
  ID                        id-at-zimbraMemcachedClientHashAlgorithm }

zimbraMemcachedClientServerList ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraMemcachedClientServerList"}
  LDAP-DESC                 "list of host:port for memcached servers; set to empty value to disable the use of memcached"
  ID                        id-at-zimbraMemcachedClientServerList }

zimbraMemcachedClientTimeoutMillis ATTRIBUTE ::= {
  WITH SYNTAX               INTEGER
  EQUALITY MATCHING RULE    integerMatch
  SINGLE VALUE              TRUE
  LDAP-SYNTAX               integer.&id
  LDAP-NAME                 {"zimbraMemcachedClientTimeoutMillis"}
  LDAP-DESC                 "default timeout in milliseconds for async memcached operations"
  ID                        id-at-zimbraMemcachedClientTimeoutMillis }

zimbraMessageCacheSize ATTRIBUTE ::= {
  WITH SYNTAX               INTEGER
  EQUALITY MATCHING RULE    integerMatch
  SINGLE VALUE              TRUE
  LDAP-SYNTAX               integer.&id
  LDAP-NAME                 {"zimbraMessageCacheSize"}
  LDAP-DESC                 "Maximum number of JavaMail MimeMessage objects in the message cache."
  ID                        id-at-zimbraMessageCacheSize }

zimbraMessageChannelEnabled ATTRIBUTE ::= {
  WITH SYNTAX               BOOLEAN
  EQUALITY MATCHING RULE    booleanMatch
  SINGLE VALUE              TRUE
  LDAP-SYNTAX               boolean.&id
  LDAP-NAME                 {"zimbraMessageChannelEnabled"}
  LDAP-DESC                 "whether message channel service is enabled on this server"
  ID                        id-at-zimbraMessageChannelEnabled }

zimbraMessageChannelPort ATTRIBUTE ::= {
  WITH SYNTAX               INTEGER
  EQUALITY MATCHING RULE    integerMatch
  SINGLE VALUE              TRUE
  LDAP-SYNTAX               integer.&id
  LDAP-NAME                 {"zimbraMessageChannelPort"}
  LDAP-DESC                 "port number on which message channel should listen"
  ID                        id-at-zimbraMessageChannelPort }

zimbraMessageIdDedupeCacheSize ATTRIBUTE ::= {
  WITH SYNTAX               INTEGER
  EQUALITY MATCHING RULE    integerMatch
  SINGLE VALUE              TRUE
  LDAP-SYNTAX               integer.&id
  LDAP-NAME                 {"zimbraMessageIdDedupeCacheSize"}
  LDAP-DESC                 "Number of Message-Id header values to keep in the LMTP dedupe cache. Subsequent attempts to deliver a message with a matching Message-Id to the same mailbox will be ignored. A value of 0 disables deduping."
  ID                        id-at-zimbraMessageIdDedupeCacheSize }

zimbraMessageIdDedupeCacheTimeout ATTRIBUTE ::= {
  WITH SYNTAX               IA5String(SIZE (1..32))
  EQUALITY MATCHING RULE    caseIgnoreIA5Match
  SINGLE VALUE              TRUE
  LDAP-SYNTAX               ia5String.&id
  LDAP-NAME                 {"zimbraMessageIdDedupeCacheTimeout"}
  LDAP-DESC                 "Timeout for a Message-Id entry in the LMTP dedupe cache. A value of 0 indicates no timeout. zimbraMessageIdDedupeCacheSize limit is ignored when this is set to a non-zero value. . Must be in valid duration format: {digits}{time-unit}. digits: 0-9, time-unit: [hmsd]|ms. h - hours, m - minutes, s - seconds, d - days, ms - milliseconds. If time unit is not specified, the default is s(seconds)."
  ID                        id-at-zimbraMessageIdDedupeCacheTimeout }

-- LDAP syntax length {128} rendered as DirectoryString{128}.
zimbraMilterBindAddress ATTRIBUTE ::= {
  WITH SYNTAX               DirectoryString{128}
  EQUALITY MATCHING RULE    caseIgnoreMatch
  SUBSTRINGS MATCHING RULE  caseIgnoreSubstringsMatch
  LDAP-SYNTAX               directoryString.&id
  LDAP-NAME                 {"zimbraMilterBindAddress"}
  LDAP-DESC                 "interface address on which milter server should listen; if not specified, binds to 127.0.0.1"
  ID                        id-at-zimbraMilterBindAddress }

zimbraMilterBindPort ATTRIBUTE ::= {
  WITH SYNTAX               INTEGER
  EQUALITY MATCHING RULE    integerMatch
  SINGLE VALUE              TRUE
  LDAP-SYNTAX               integer.&id
  LDAP-NAME                 {"zimbraMilterBindPort"}
  LDAP-DESC                 "port number on which milter server should listen"
  ID                        id-at-zimbraMilterBindPort }

zimbraMilterMaxConnections ATTRIBUTE ::= {
  WITH SYNTAX               INTEGER
  EQUALITY MATCHING RULE    integerMatch
  SINGLE VALUE              TRUE
  LDAP-SYNTAX               integer.&id
  LDAP-NAME                 {"zimbraMilterMaxConnections"}
  LDAP-DESC                 "Maximum number of concurrent MILTER connections allowed. New connections exceeding this limit are rejected."
  ID                        id-at-zimbraMilterMaxConnections }

zimbraMilterNumThreads ATTRIBUTE ::= {
  WITH SYNTAX               INTEGER
  EQUALITY MATCHING RULE    integerMatch
  SINGLE VALUE              TRUE
  LDAP-SYNTAX               integer.&id
  LDAP-NAME                 {"zimbraMilterNumThreads"}
  LDAP-DESC                 "number of milter handler threads"
  ID                        id-at-zimbraMilterNumThreads }

zimbraMilterServerEnabled ATTRIBUTE ::= {
  WITH SYNTAX               BOOLEAN
  EQUALITY MATCHING RULE    booleanMatch
  SINGLE VALUE              TRUE
  LDAP-SYNTAX               boolean.&id
  LDAP-NAME                 {"zimbraMilterServerEnabled"}
  LDAP-DESC                 "whether milter server is enabled for a given server"
  ID                        id-at-zimbraMilterServerEnabled }

zimbraMimeFileExtension ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraMimeFileExtension"}
  LDAP-DESC                 "the file extension (without the .)"
  ID                        id-at-zimbraMimeFileExtension }

zimbraMimeHandlerClass ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"zimbraMimeHandlerClass"}
  LDAP-DESC                 "the handler class for the mime type"
  ID                        id-at-zimbraMimeHandlerClass }

zimbraMimeHandlerExtension ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"zimbraMimeHandlerExtension"}
  LDAP-DESC                 "the name of the zimbra extension where the handler class for the mime type lives"
  ID                        id-at-zimbraMimeHandlerExtension }

zimbraMimeIndexingEnabled ATTRIBUTE ::= {
  WITH SYNTAX               BOOLEAN
  EQUALITY MATCHING RULE    booleanMatch
  SINGLE VALUE              TRUE
  LDAP-SYNTAX               boolean.&id
  LDAP-NAME                 {"zimbraMimeIndexingEnabled"}
  LDAP-DESC                 "whether or not indexing is enabled for this type"
  ID                        id-at-zimbraMimeIndexingEnabled }

zimbraMimePriority ATTRIBUTE ::= {
  WITH SYNTAX               INTEGER
  EQUALITY MATCHING RULE    integerMatch
  SINGLE VALUE              TRUE
  LDAP-SYNTAX               integer.&id
  LDAP-NAME                 {"zimbraMimePriority"}
  LDAP-DESC                 "The priority that this MIME type will be chosen, in the case that more than one MIME type object matches a given type or filename extension."
  ID                        id-at-zimbraMimePriority }

zimbraMimeType ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraMimeType"}
  LDAP-DESC                 "the MIME type (type/substype) or a regular expression"
  ID                        id-at-zimbraMimeType }

zimbraMobileAttachSkippedItemEnabled ATTRIBUTE ::= {
  WITH SYNTAX               BOOLEAN
  EQUALITY MATCHING RULE    booleanMatch
  SINGLE VALUE              TRUE
  LDAP-SYNTAX               boolean.&id
  LDAP-NAME                 {"zimbraMobileAttachSkippedItemEnabled"}
  LDAP-DESC                 "whether mobile sync should zip the skipped item and attach it to the notification mail"
  ID                        id-at-zimbraMobileAttachSkippedItemEnabled }

zimbraMobileForceProtocol25 ATTRIBUTE ::= {
  WITH SYNTAX               BOOLEAN
  EQUALITY MATCHING RULE    booleanMatch
  SINGLE VALUE              TRUE
  LDAP-SYNTAX               boolean.&id
  LDAP-NAME                 {"zimbraMobileForceProtocol25"}
  LDAP-DESC                 "Whether to force devices using Active Sync 2.5"
  ID                        id-at-zimbraMobileForceProtocol25 }

zimbraMobileForceSamsungProtocol25 ATTRIBUTE ::= {
  WITH SYNTAX               BOOLEAN
  EQUALITY MATCHING RULE    booleanMatch
  SINGLE VALUE              TRUE
  LDAP-SYNTAX               boolean.&id
  LDAP-NAME                 {"zimbraMobileForceSamsungProtocol25"}
  LDAP-DESC                 "Whether to force Samsung devices using Active Sync 2.5"
  ID                        id-at-zimbraMobileForceSamsungProtocol25 }

-- LDAP syntax length {30} rendered as DirectoryString{30}.
zimbraMobileItemsToTrackPerFolderMaxSize ATTRIBUTE ::= {
  WITH SYNTAX               DirectoryString{30}
  EQUALITY MATCHING RULE    caseIgnoreMatch
  SUBSTRINGS MATCHING RULE  caseIgnoreSubstringsMatch
  LDAP-SYNTAX               directoryString.&id
  LDAP-NAME                 {"zimbraMobileItemsToTrackPerFolderMaxSize"}
  LDAP-DESC                 "Max size of items in a folder that server tracks, categorized by collection type (Email,Calendar,Contacts,Tasks). e.g. Email:3000 makes the max size of items to track for an Email folder to be 3000. If not specify, default value is Integer.MAX_VALUE"
  ID                        id-at-zimbraMobileItemsToTrackPerFolderMaxSize }

zimbraMobileMaxMessageSize ATTRIBUTE ::= {
  WITH SYNTAX               INTEGER
  EQUALITY MATCHING RULE    integerMatch
  SINGLE VALUE              TRUE
  LDAP-SYNTAX               integer.&id
  LDAP-NAME                 {"zimbraMobileMaxMessageSize"}
  LDAP-DESC                 "Maximum total size of a mail message that can be synced to device without truncation. It cannot be larger than zimbraMTAMaxMessageSize. 0 means zimbraMTAMaxMessageSize or INTEGER_MAX, whichever is smaller"
  ID                        id-at-zimbraMobileMaxMessageSize }

zimbraMobileMetadataMaxSizeEnabled ATTRIBUTE ::= {
  WITH SYNTAX               BOOLEAN
  EQUALITY MATCHING RULE    booleanMatch
  SINGLE VALUE              TRUE
  LDAP-SYNTAX               boolean.&id
  LDAP-NAME                 {"zimbraMobileMetadataMaxSizeEnabled"}
  LDAP-DESC                 "whether or not to enable truncating on client metadata size, if enabled server will only track recent items on client device instead of all"
  ID                        id-at-zimbraMobileMetadataMaxSizeEnabled }

zimbraMobileMetadataRetentionPolicy ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMobileMetadataRetentionPolicy"}
  LDAP-DESC                 "Retention policy for stale mobile metadata. Format is ""aa:bb:c"", ""aa"" being the number of days to define stale data. e.g. 180 means if device's last_used_date is 180 days ago, its metadata need to be removed. ""bb"" being the days between two retentions are run, e.g. 30 means to run retention every 30 days. ""hh"" being the hour of day to run retention, from 0 to 23. e.g. 1 means to run retention at some time between 1am and 2am."
  ID                        id-at-zimbraMobileMetadataRetentionPolicy }

zimbraMobileNotificationAdminAddress ATTRIBUTE ::= {
  WITH SYNTAX               IA5String(SIZE (1..256))
  EQUALITY MATCHING RULE    caseIgnoreIA5Match
  SUBSTRINGS MATCHING RULE  caseIgnoreSubstringsMatch
  SINGLE VALUE              TRUE
  LDAP-SYNTAX               ia5String.&id
  LDAP-NAME                 {"zimbraMobileNotificationAdminAddress"}
  LDAP-DESC                 "admin email address used for receiving notifications"
  ID                        id-at-zimbraMobileNotificationAdminAddress }

zimbraMobileNotificationEnabled ATTRIBUTE ::= {
  WITH SYNTAX               BOOLEAN
  EQUALITY MATCHING RULE    booleanMatch
  SINGLE VALUE              TRUE
  LDAP-SYNTAX               boolean.&id
  LDAP-NAME                 {"zimbraMobileNotificationEnabled"}
  LDAP-DESC                 "whether mobile sync notification enabled or not"
  ID                        id-at-zimbraMobileNotificationEnabled }

zimbraMobileOutlookSyncEnabled ATTRIBUTE ::= {
  WITH SYNTAX               BOOLEAN
  EQUALITY MATCHING RULE    booleanMatch
  SINGLE VALUE              TRUE
  LDAP-SYNTAX               boolean.&id
  LDAP-NAME                 {"zimbraMobileOutlookSyncEnabled"}
  LDAP-DESC                 "Whether to permit Outlook to sync via Active Sync"
  ID                        id-at-zimbraMobileOutlookSyncEnabled }

zimbraMobilePolicyAllowBluetooth ATTRIBUTE ::= {
  WITH SYNTAX               INTEGER
  EQUALITY MATCHING RULE    integerMatch
  SINGLE VALUE              TRUE
  LDAP-SYNTAX               integer.&id
  LDAP-NAME                 {"zimbraMobilePolicyAllowBluetooth"}
  LDAP-DESC                 "whether the Bluetooth capabilities are allowed on the device. The available options are Disable, HandsfreeOnly, and Allow. 0 - DISABLE 1 - HANDSFREE 2 - ALLOW ignored if zimbraFeatureMobilePolicyEnabled=FALSE or zimbraMobilePolicyAllowBluetooth value is set to -1"
  ID                        id-at-zimbraMobilePolicyAllowBluetooth }

zimbraMobilePolicyAllowBrowser ATTRIBUTE ::= {
  WITH SYNTAX               INTEGER
  EQUALITY MATCHING RULE    integerMatch
  SINGLE VALUE              TRUE
  LDAP-SYNTAX               integer.&id
  LDAP-NAME                 {"zimbraMobilePolicyAllowBrowser"}
  LDAP-DESC                 "whether Microsoft Pocket Internet Explorer is allowed on the mobile phone. This parameter doesn't affect third-party browsers. ignored if zimbraFeatureMobilePolicyEnabled=FALSE or zimbraMobilePolicyAllowBrowser value is set to -1"
  ID                        id-at-zimbraMobilePolicyAllowBrowser }

zimbraMobilePolicyAllowCamera ATTRIBUTE ::= {
  WITH SYNTAX               INTEGER
  EQUALITY MATCHING RULE    integerMatch
  SINGLE VALUE              TRUE
  LDAP-SYNTAX               integer.&id
  LDAP-NAME                 {"zimbraMobilePolicyAllowCamera"}
  LDAP-DESC                 "whether to allow camera on device; ignored if zimbraFeatureMobilePolicyEnabled=FALSE or zimbraMobilePolicyAllowCamera value is set to -1"
  ID                        id-at-zimbraMobilePolicyAllowCamera }

zimbraMobilePolicyAllowConsumerEmail ATTRIBUTE ::= {
  WITH SYNTAX               INTEGER
  EQUALITY MATCHING RULE    integerMatch
  SINGLE VALUE              TRUE
  LDAP-SYNTAX               integer.&id
  LDAP-NAME                 {"zimbraMobilePolicyAllowConsumerEmail"}
  LDAP-DESC                 "whether the device user can configure a personal e-mail account on the mobile phone. This parameter doesn't control access to e-mails using third-party mobile phone e-mail programs. ignored if zimbraFeatureMobilePolicyEnabled=FALSE or zimbraMobilePolicyAllowConsumerEmail value is set to -1"
  ID                        id-at-zimbraMobilePolicyAllowConsumerEmail }

zimbraMobilePolicyAllowDesktopSync ATTRIBUTE ::= {
  WITH SYNTAX               INTEGER
  EQUALITY MATCHING RULE    integerMatch
  SINGLE VALUE              TRUE
  LDAP-SYNTAX               integer.&id
  LDAP-NAME                 {"zimbraMobilePolicyAllowDesktopSync"}
  LDAP-DESC                 "whether the device can synchronize with a desktop computer through a cable; ignored if zimbraFeatureMobilePolicyEnabled=FALSE or zimbraMobilePolicyAllowDesktopSync value is set to -1"
  ID                        id-at-zimbraMobilePolicyAllowDesktopSync }

zimbraMobilePolicyAllowHTMLEmail ATTRIBUTE ::= {
  WITH SYNTAX               INTEGER
  EQUALITY MATCHING RULE    integerMatch
  SINGLE VALUE              TRUE
  LDAP-SYNTAX               integer.&id
  LDAP-NAME                 {"zimbraMobilePolicyAllowHTMLEmail"}
  LDAP-DESC                 "whether HTML e-mail is enabled on the device. If set to 0, all e-mail will be converted to plain text before synchronization occurs. ignored if zimbraFeatureMobilePolicyEnabled=FALSE or zimbraMobilePolicyAllowHTMLEmail value is set to -1"
  ID                        id-at-zimbraMobilePolicyAllowHTMLEmail }

zimbraMobilePolicyAllowInternetSharing ATTRIBUTE ::= {
  WITH SYNTAX               INTEGER
  EQUALITY MATCHING RULE    integerMatch
  SINGLE VALUE              TRUE
  LDAP-SYNTAX               integer.&id
  LDAP-NAME                 {"zimbraMobilePolicyAllowInternetSharing"}
  LDAP-DESC                 "whether the mobile device can be used as a modem to connect a computer to the Internet; ignored if zimbraFeatureMobilePolicyEnabled=FALSE or zimbraMobilePolicyAllowInternetSharing value is set to -1"
  ID                        id-at-zimbraMobilePolicyAllowInternetSharing }

zimbraMobilePolicyAllowIrDA ATTRIBUTE ::= {
  WITH SYNTAX               INTEGER
  EQUALITY MATCHING RULE    integerMatch
  SINGLE VALUE              TRUE
  LDAP-SYNTAX               integer.&id
  LDAP-NAME                 {"zimbraMobilePolicyAllowIrDA"}
  LDAP-DESC                 "whether infrared connections are allowed to the device; ignored if zimbraFeatureMobilePolicyEnabled=FALSE or zimbraMobilePolicyAllowIrDA value is set to -1"
  ID                        id-at-zimbraMobilePolicyAllowIrDA }

zimbraMobilePolicyAllowNonProvisionableDevices ATTRIBUTE ::= {
  WITH SYNTAX               BOOLEAN
  EQUALITY MATCHING RULE    booleanMatch
  SINGLE VALUE              TRUE
  LDAP-SYNTAX               boolean.&id
  LDAP-NAME                 {"zimbraMobilePolicyAllowNonProvisionableDevices"}
  LDAP-DESC                 "whether to allow non-provisionable devices; ignored if zimbraFeatureMobilePolicyEnabled=FALSE"
  ID                        id-at-zimbraMobilePolicyAllowNonProvisionableDevices }

zimbraMobilePolicyAllowPOPIMAPEmail ATTRIBUTE ::= {
  WITH SYNTAX               INTEGER
  EQUALITY MATCHING RULE    integerMatch
  SINGLE VALUE              TRUE
  LDAP-SYNTAX               integer.&id
  LDAP-NAME                 {"zimbraMobilePolicyAllowPOPIMAPEmail"}
  LDAP-DESC                 "whether the user can configure a POP3 or IMAP4 e-mail account on the device. This parameter doesn't control access by third-party e-mail programs. ignored if zimbraFeatureMobilePolicyEnabled=FALSE or zimbraMobilePolicyAllowPOPIMAPEmail value is set to -1"
  ID                        id-at-zimbraMobilePolicyAllowPOPIMAPEmail }

zimbraMobilePolicyAllowPartialProvisioning ATTRIBUTE ::= {
  WITH SYNTAX               BOOLEAN
  EQUALITY MATCHING RULE    booleanMatch
  SINGLE VALUE              TRUE
  LDAP-SYNTAX               boolean.&id
  LDAP-NAME                 {"zimbraMobilePolicyAllowPartialProvisioning"}
  LDAP-DESC                 "whether to allow partial policy enforcement on device; ignored if zimbraFeatureMobilePolicyEnabled=FALSE"
  ID                        id-at-zimbraMobilePolicyAllowPartialProvisioning }

zimbraMobilePolicyAllowRemoteDesktop ATTRIBUTE ::= {
  WITH SYNTAX               INTEGER
  EQUALITY MATCHING RULE    integerMatch
  SINGLE VALUE              TRUE
  LDAP-SYNTAX               integer.&id
  LDAP-NAME                 {"zimbraMobilePolicyAllowRemoteDesktop"}
  LDAP-DESC                 "whether the mobile device can initiate a remote desktop connection; ignored if zimbraFeatureMobilePolicyEnabled=FALSE or zimbraMobilePolicyAllowRemoteDesktop value is set to -1"
  ID                        id-at-zimbraMobilePolicyAllowRemoteDesktop }

zimbraMobilePolicyAllowSMIMEEncryptionAlgorithmNegotiation ATTRIBUTE ::= {
  WITH SYNTAX               INTEGER
  EQUALITY MATCHING RULE    integerMatch
  SINGLE VALUE              TRUE
  LDAP-SYNTAX               integer.&id
  LDAP-NAME                 {"zimbraMobilePolicyAllowSMIMEEncryptionAlgorithmNegotiation"}
  LDAP-DESC                 "whether the messaging application on the device can negotiate the encryption algorithm if a recipient's certificate doesn't support the specified encryption algorithm; 0 - BlockNegotiation 1 - OnlyStrongAlgorithmNegotiation 2 - AllowAnyAlgorithmNegotiation ignored if zimbraFeatureMobilePolicyEnabled=FALSE or zimbraMobilePolicyAllowSMIMEEncryptionAlgorithmNegotiation value is set to -1"
  ID                        id-at-zimbraMobilePolicyAllowSMIMEEncryptionAlgorithmNegotiation }

zimbraMobilePolicyAllowSMIMESoftCerts ATTRIBUTE ::= {
  WITH SYNTAX               INTEGER
  EQUALITY MATCHING RULE    integerMatch
  SINGLE VALUE              TRUE
  LDAP-SYNTAX               integer.&id
  LDAP-NAME                 {"zimbraMobilePolicyAllowSMIMESoftCerts"}
  LDAP-DESC                 "whether S/MIME software certificates are allowed; ignored if zimbraFeatureMobilePolicyEnabled=FALSE or zimbraMobilePolicyAllowSMIMESoftCerts value is set to -1"
  ID                        id-at-zimbraMobilePolicyAllowSMIMESoftCerts }

zimbraMobilePolicyAllowSimpleDevicePassword ATTRIBUTE ::= {
  WITH SYNTAX               BOOLEAN
  EQUALITY MATCHING RULE    booleanMatch
  SINGLE VALUE              TRUE
  LDAP-SYNTAX               boolean.&id
  LDAP-NAME                 {"zimbraMobilePolicyAllowSimpleDevicePassword"}
  LDAP-DESC                 "whether to allow simple password; ignored if zimbraFeatureMobilePolicyEnabled=FALSE or zimbraMobilePolicyDevicePasswordEnabled=FALSE"
  ID                        id-at-zimbraMobilePolicyAllowSimpleDevicePassword }

zimbraMobilePolicyAllowStorageCard ATTRIBUTE ::= {
  WITH SYNTAX               INTEGER
  EQUALITY MATCHING RULE    integerMatch
  SINGLE VALUE              TRUE
  LDAP-SYNTAX               integer.&id
  LDAP-NAME                 {"zimbraMobilePolicyAllowStorageCard"}
  LDAP-DESC                 "whether to allow removable storage on device; ignored if zimbraFeatureMobilePolicyEnabled=FALSE or zimbraMobilePolicyAllowStorageCard value is set to -1"
  ID                        id-at-zimbraMobilePolicyAllowStorageCard }

zimbraMobilePolicyAllowTextMessaging ATTRIBUTE ::= {
  WITH SYNTAX               INTEGER
  EQUALITY MATCHING RULE    integerMatch
  SINGLE VALUE              TRUE
  LDAP-SYNTAX               integer.&id
  LDAP-NAME                 {"zimbraMobilePolicyAllowTextMessaging"}
  LDAP-DESC                 "whether text messaging is allowed from the device; ignored if zimbraFeatureMobilePolicyEnabled=FALSE or zimbraMobilePolicyAllowTextMessaging value is set to -1"
  ID                        id-at-zimbraMobilePolicyAllowTextMessaging }

zimbraMobilePolicyAllowUnsignedApplications ATTRIBUTE ::= {
  WITH SYNTAX               INTEGER
  EQUALITY MATCHING RULE    integerMatch
  SINGLE VALUE              TRUE
  LDAP-SYNTAX               integer.&id
  LDAP-NAME                 {"zimbraMobilePolicyAllowUnsignedApplications"}
  LDAP-DESC                 "whether unsigned applications are allowed on device; ignored if zimbraFeatureMobilePolicyEnabled=FALSE or zimbraMobilePolicyAllowUnsignedApplications value is set to -1"
  ID                        id-at-zimbraMobilePolicyAllowUnsignedApplications }

zimbraMobilePolicyAllowUnsignedInstallationPackages ATTRIBUTE ::= {
  WITH SYNTAX               INTEGER
  EQUALITY MATCHING RULE    integerMatch
  SINGLE VALUE              TRUE
  LDAP-SYNTAX               integer.&id
  LDAP-NAME                 {"zimbraMobilePolicyAllowUnsignedInstallationPackages"}
  LDAP-DESC                 "whether unsigned installation packages are allowed on device; ignored if zimbraFeatureMobilePolicyEnabled=FALSE or zimbraMobilePolicyAllowUnsignedInstallationPackages value is set to -1"
  ID                        id-at-zimbraMobilePolicyAllowUnsignedInstallationPackages }

zimbraMobilePolicyAllowWiFi ATTRIBUTE ::= {
  WITH SYNTAX               INTEGER
  EQUALITY MATCHING RULE    integerMatch
  SINGLE VALUE              TRUE
  LDAP-SYNTAX               integer.&id
  LDAP-NAME                 {"zimbraMobilePolicyAllowWiFi"}
  LDAP-DESC                 "whether wireless Internet access is allowed on the device; ignored if zimbraFeatureMobilePolicyEnabled=FALSE or zimbraMobilePolicyAllowWiFi value is set to -1"
  ID                        id-at-zimbraMobilePolicyAllowWiFi }

zimbraMobilePolicyAlphanumericDevicePasswordRequired ATTRIBUTE ::= {
  WITH SYNTAX               BOOLEAN
  EQUALITY MATCHING RULE    booleanMatch
  SINGLE VALUE              TRUE
  LDAP-SYNTAX               boolean.&id
  LDAP-NAME                 {"zimbraMobilePolicyAlphanumericDevicePasswordRequired"}
  LDAP-DESC                 "whether to require alpha-numeric password as device pin; ignored if zimbraFeatureMobilePolicyEnabled=FALSE or zimbraMobilePolicyDevicePasswordEnabled=FALSE"
  ID                        id-at-zimbraMobilePolicyAlphanumericDevicePasswordRequired }

-- LDAP syntax length {256} rendered as DirectoryString{256}.
zimbraMobilePolicyApprovedApplication ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraMobilePolicyApprovedApplication"}
  LDAP-DESC                 "approved application for the mobile device the value contains a SHA1 hash (typically 40 characters long) for the application file (.exe, .dll etc) ignored if zimbraFeatureMobilePolicyEnabled=FALSE"
  ID                        id-at-zimbraMobilePolicyApprovedApplication }

-- LDAP syntax length {256} rendered as DirectoryString{256}.
zimbraMobilePolicyApprovedApplicationList ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraMobilePolicyApprovedApplicationList"}
  LDAP-DESC                 "This is the internal attr for ""zimbraMobilePolicyApprovedApplication"" which can only store app hash (to keep consistent with ActiveSync specification. This attr's format is ""app_name"":""app_hash"", and is used for showing both the app name and hash in admin console UI"
  ID                        id-at-zimbraMobilePolicyApprovedApplicationList }

zimbraMobilePolicyDeviceEncryptionEnabled ATTRIBUTE ::= {
  WITH SYNTAX               BOOLEAN
  EQUALITY MATCHING RULE    booleanMatch
  SINGLE VALUE              TRUE
  LDAP-SYNTAX               boolean.&id
  LDAP-NAME                 {"zimbraMobilePolicyDeviceEncryptionEnabled"}
  LDAP-DESC                 "Deprecated since: 8.5.0. Use zimbraMobilePolicyRequireStorageCardEncryption. Orig desc: require data encryption on device; ignored if zimbraFeatureMobilePolicyEnabled=FALSE"
  ID                        id-at-zimbraMobilePolicyDeviceEncryptionEnabled }

zimbraMobilePolicyDevicePasswordEnabled ATTRIBUTE ::= {
  WITH SYNTAX               BOOLEAN
  EQUALITY MATCHING RULE    booleanMatch
  SINGLE VALUE              TRUE
  LDAP-SYNTAX               boolean.&id
  LDAP-NAME                 {"zimbraMobilePolicyDevicePasswordEnabled"}
  LDAP-DESC                 "whether to force pin on device; ignored if zimbraFeatureMobilePolicyEnabled=FALSE"
  ID                        id-at-zimbraMobilePolicyDevicePasswordEnabled }

zimbraMobilePolicyDevicePasswordExpiration ATTRIBUTE ::= {
  WITH SYNTAX               INTEGER
  EQUALITY MATCHING RULE    integerMatch
  SINGLE VALUE              TRUE
  LDAP-SYNTAX               integer.&id
  LDAP-NAME                 {"zimbraMobilePolicyDevicePasswordExpiration"}
  LDAP-DESC                 "number of days before device pin must expire; ignored if zimbraFeatureMobilePolicyEnabled=FALSE or zimbraMobilePolicyDevicePasswordEnabled=FALSE"
  ID                        id-at-zimbraMobilePolicyDevicePasswordExpiration }

zimbraMobilePolicyDevicePasswordHistory ATTRIBUTE ::= {
  WITH SYNTAX               INTEGER
  EQUALITY MATCHING RULE    integerMatch
  SINGLE VALUE              TRUE
  LDAP-SYNTAX               integer.&id
  LDAP-NAME                 {"zimbraMobilePolicyDevicePasswordHistory"}
  LDAP-DESC                 "number of previously used password stored in history; ignored if zimbraFeatureMobilePolicyEnabled=FALSE or zimbraMobilePolicyDevicePasswordEnabled=FALSE or zimbraMobilePolicyDevicePasswordExpiration=0"
  ID                        id-at-zimbraMobilePolicyDevicePasswordHistory }

zimbraMobilePolicyMaxCalendarAgeFilter ATTRIBUTE ::= {
  WITH SYNTAX               INTEGER
  EQUALITY MATCHING RULE    integerMatch
  SINGLE VALUE              TRUE
  LDAP-SYNTAX               integer.&id
  LDAP-NAME                 {"zimbraMobilePolicyMaxCalendarAgeFilter"}
  LDAP-DESC                 "the maximum range of calendar days that can be synchronized to the device; 0 - PAST ALL 4 - Two Weeks 5 - One Month 6 - Three Months 7 - Six Months ignored if zimbraFeatureMobilePolicyEnabled=FALSE or zimbraMobilePolicyMaxCalendarAgeFilter value is set to -1, 1, 2 or, 3"
  ID                        id-at-zimbraMobilePolicyMaxCalendarAgeFilter }

zimbraMobilePolicyMaxDevicePasswordFailedAttempts ATTRIBUTE ::= {
  WITH SYNTAX               INTEGER
  EQUALITY MATCHING RULE    integerMatch
  SINGLE VALUE              TRUE
  LDAP-SYNTAX               integer.&id
  LDAP-NAME                 {"zimbraMobilePolicyMaxDevicePasswordFailedAttempts"}
  LDAP-DESC                 "number of consecutive incorrect pin input before device is wiped; ignored if zimbraFeatureMobilePolicyEnabled=FALSE or zimbraMobilePolicyDevicePasswordEnabled=FALSE"
  ID                        id-at-zimbraMobilePolicyMaxDevicePasswordFailedAttempts }

zimbraMobilePolicyMaxEmailAgeFilter ATTRIBUTE ::= {
  WITH SYNTAX               INTEGER
  EQUALITY MATCHING RULE    integerMatch
  SINGLE VALUE              TRUE
  LDAP-SYNTAX               integer.&id
  LDAP-NAME                 {"zimbraMobilePolicyMaxEmailAgeFilter"}
  LDAP-DESC                 "the maximum number of days of e-mail items to synchronize to the device; 0 - PAST ALL 1 - One Day 2 - Three Days 3 - One Week 4 - Two Weeks 5 - One Month ignored if zimbraFeatureMobilePolicyEnabled=FALSE or zimbraMobilePolicyMaxEmailAgeFilter value is set to -1"
  ID                        id-at-zimbraMobilePolicyMaxEmailAgeFilter }

zimbraMobilePolicyMaxEmailBodyTruncationSize ATTRIBUTE ::= {
  WITH SYNTAX               INTEGER
  EQUALITY MATCHING RULE    integerMatch
  SINGLE VALUE              TRUE
  LDAP-SYNTAX               integer.&id
  LDAP-NAME                 {"zimbraMobilePolicyMaxEmailBodyTruncationSize"}
  LDAP-DESC                 "the maximum size at which e-mail messages are truncated when synchronized to the device; The value is specified in kilobytes (KB). ignored if zimbraFeatureMobilePolicyEnabled=FALSE"
  ID                        id-at-zimbraMobilePolicyMaxEmailBodyTruncationSize }

zimbraMobilePolicyMaxEmailHTMLBodyTruncationSize ATTRIBUTE ::= {
  WITH SYNTAX               INTEGER
  EQUALITY MATCHING RULE    integerMatch
  SINGLE VALUE              TRUE
  LDAP-SYNTAX               integer.&id
  LDAP-NAME                 {"zimbraMobilePolicyMaxEmailHTMLBodyTruncationSize"}
  LDAP-DESC                 "the maximum size at which HTML-formatted e-mail messages are synchronized to the devices. The value is specified in KB. ignored if zimbraFeatureMobilePolicyEnabled=FALSE"
  ID                        id-at-zimbraMobilePolicyMaxEmailHTMLBodyTruncationSize }

zimbraMobilePolicyMaxInactivityTimeDeviceLock ATTRIBUTE ::= {
  WITH SYNTAX               INTEGER
  EQUALITY MATCHING RULE    integerMatch
  SINGLE VALUE              TRUE
  LDAP-SYNTAX               integer.&id
  LDAP-NAME                 {"zimbraMobilePolicyMaxInactivityTimeDeviceLock"}
  LDAP-DESC                 "max idle time in minutes before device is locked; ignored if zimbraFeatureMobilePolicyEnabled=FALSE or zimbraMobilePolicyDevicePasswordEnabled=FALSE"
  ID                        id-at-zimbraMobilePolicyMaxInactivityTimeDeviceLock }

zimbraMobilePolicyMinDevicePasswordComplexCharacters ATTRIBUTE ::= {
  WITH SYNTAX               INTEGER
  EQUALITY MATCHING RULE    integerMatch
  SINGLE VALUE              TRUE
  LDAP-SYNTAX               integer.&id
  LDAP-NAME                 {"zimbraMobilePolicyMinDevicePasswordComplexCharacters"}
  LDAP-DESC                 "least number of complex characters must be included in device pin; ignored if zimbraFeatureMobilePolicyEnabled=FALSE or zimbraMobilePolicyDevicePasswordEnabled=FALSE"
  ID                        id-at-zimbraMobilePolicyMinDevicePasswordComplexCharacters }

zimbraMobilePolicyMinDevicePasswordLength ATTRIBUTE ::= {
  WITH SYNTAX               INTEGER
  EQUALITY MATCHING RULE    integerMatch
  SINGLE VALUE              TRUE
  LDAP-SYNTAX               integer.&id
  LDAP-NAME                 {"zimbraMobilePolicyMinDevicePasswordLength"}
  LDAP-DESC                 "min length for device pin; ignored if zimbraFeatureMobilePolicyEnabled=FALSE or zimbraMobilePolicyDevicePasswordEnabled=FALSE"
  ID                        id-at-zimbraMobilePolicyMinDevicePasswordLength }

zimbraMobilePolicyPasswordRecoveryEnabled ATTRIBUTE ::= {
  WITH SYNTAX               BOOLEAN
  EQUALITY MATCHING RULE    booleanMatch
  SINGLE VALUE              TRUE
  LDAP-SYNTAX               boolean.&id
  LDAP-NAME                 {"zimbraMobilePolicyPasswordRecoveryEnabled"}
  LDAP-DESC                 "support device pin recovery; ignored if zimbraFeatureMobilePolicyEnabled=FALSE or zimbraMobilePolicyDevicePasswordEnabled=FALSE"
  ID                        id-at-zimbraMobilePolicyPasswordRecoveryEnabled }

zimbraMobilePolicyRefreshInterval ATTRIBUTE ::= {
  WITH SYNTAX               INTEGER
  EQUALITY MATCHING RULE    integerMatch
  SINGLE VALUE              TRUE
  LDAP-SYNTAX               integer.&id
  LDAP-NAME                 {"zimbraMobilePolicyRefreshInterval"}
  LDAP-DESC                 "time interval in minutes before forcing device to refresh policy; ignored if zimbraFeatureMobilePolicyEnabled=FALSE"
  ID                        id-at-zimbraMobilePolicyRefreshInterval }

zimbraMobilePolicyRequireDeviceEncryption ATTRIBUTE ::= {
  WITH SYNTAX               INTEGER
  EQUALITY MATCHING RULE    integerMatch
  SINGLE VALUE              TRUE
  LDAP-SYNTAX               integer.&id
  LDAP-NAME                 {"zimbraMobilePolicyRequireDeviceEncryption"}
  LDAP-DESC                 "whether encryption on device is required; ignored if zimbraFeatureMobilePolicyEnabled=FALSE or zimbraMobilePolicyRequireDeviceEncryption value is set to -1"
  ID                        id-at-zimbraMobilePolicyRequireDeviceEncryption }

zimbraMobilePolicyRequireEncryptedSMIMEMessages ATTRIBUTE ::= {
  WITH SYNTAX               INTEGER
  EQUALITY MATCHING RULE    integerMatch
  SINGLE VALUE              TRUE
  LDAP-SYNTAX               integer.&id
  LDAP-NAME                 {"zimbraMobilePolicyRequireEncryptedSMIMEMessages"}
  LDAP-DESC                 "whether you must encrypt S/MIME messages; ignored if zimbraFeatureMobilePolicyEnabled=FALSE or zimbraMobilePolicyRequireEncryptedSMIMEMessages value is set to -1"
  ID                        id-at-zimbraMobilePolicyRequireEncryptedSMIMEMessages }

zimbraMobilePolicyRequireEncryptionSMIMEAlgorithm ATTRIBUTE ::= {
  WITH SYNTAX               INTEGER
  EQUALITY MATCHING RULE    integerMatch
  SINGLE VALUE              TRUE
  LDAP-SYNTAX               integer.&id
  LDAP-NAME                 {"zimbraMobilePolicyRequireEncryptionSMIMEAlgorithm"}
  LDAP-DESC                 "what required algorithm must be used when encrypting a message; ignored if zimbraFeatureMobilePolicyEnabled=FALSE or zimbraMobilePolicyRequireEncryptionSMIMEAlgorithm value is set to -1"
  ID                        id-at-zimbraMobilePolicyRequireEncryptionSMIMEAlgorithm }

zimbraMobilePolicyRequireManualSyncWhenRoaming ATTRIBUTE ::= {
  WITH SYNTAX               INTEGER
  EQUALITY MATCHING RULE    integerMatch
  SINGLE VALUE              TRUE
  LDAP-SYNTAX               integer.&id
  LDAP-NAME                 {"zimbraMobilePolicyRequireManualSyncWhenRoaming"}
  LDAP-DESC                 "whether the mobile device must synchronize manually while roaming; ignored if zimbraFeatureMobilePolicyEnabled=FALSE or zimbraMobilePolicyRequireManualSyncWhenRoaming value is set to -1"
  ID                        id-at-zimbraMobilePolicyRequireManualSyncWhenRoaming }

zimbraMobilePolicyRequireSignedSMIMEAlgorithm ATTRIBUTE ::= {
  WITH SYNTAX               INTEGER
  EQUALITY MATCHING RULE    integerMatch
  SINGLE VALUE              TRUE
  LDAP-SYNTAX               integer.&id
  LDAP-NAME                 {"zimbraMobilePolicyRequireSignedSMIMEAlgorithm"}
  LDAP-DESC                 "what required algorithm must be used when signing a message; ignored if zimbraFeatureMobilePolicyEnabled=FALSE or zimbraMobilePolicyRequireSignedSMIMEAlgorithm value is set to -1"
  ID                        id-at-zimbraMobilePolicyRequireSignedSMIMEAlgorithm }

zimbraMobilePolicyRequireSignedSMIMEMessages ATTRIBUTE ::= {
  WITH SYNTAX               INTEGER
  EQUALITY MATCHING RULE    integerMatch
  SINGLE VALUE              TRUE
  LDAP-SYNTAX               integer.&id
  LDAP-NAME                 {"zimbraMobilePolicyRequireSignedSMIMEMessages"}
  LDAP-DESC                 "whether the device must send signed S/MIME messages; ignored if zimbraFeatureMobilePolicyEnabled=FALSE or zimbraMobilePolicyRequireSignedSMIMEMessages value is set to -1"
  ID                        id-at-zimbraMobilePolicyRequireSignedSMIMEMessages }

zimbraMobilePolicyRequireStorageCardEncryption ATTRIBUTE ::= {
  WITH SYNTAX               BOOLEAN
  EQUALITY MATCHING RULE    booleanMatch
  SINGLE VALUE              TRUE
  LDAP-SYNTAX               boolean.&id
  LDAP-NAME                 {"zimbraMobilePolicyRequireStorageCardEncryption"}
  LDAP-DESC                 "require data encryption on storage card; ignored if zimbraFeatureMobilePolicyEnabled=FALSE"
  ID                        id-at-zimbraMobilePolicyRequireStorageCardEncryption }

zimbraMobilePolicySuppressDeviceEncryption ATTRIBUTE ::= {
  WITH SYNTAX               BOOLEAN
  EQUALITY MATCHING RULE    booleanMatch
  SINGLE VALUE              TRUE
  LDAP-SYNTAX               boolean.&id
  LDAP-NAME                 {"zimbraMobilePolicySuppressDeviceEncryption"}
  LDAP-DESC                 "when set to TRUE, suppresses DeviceEncryptionEnabled to be sent down to the device; Some devices choke when DeviceEncryptionEnabled policy is downloaded irrespective of their value set to 0 or, 1 ignored if zimbraFeatureMobilePolicyEnabled=FALSE"
  ID                        id-at-zimbraMobilePolicySuppressDeviceEncryption }

-- LDAP syntax length {512} rendered as DirectoryString{512}.
zimbraMobilePolicyUnapprovedInROMApplication ATTRIBUTE ::= {
  WITH SYNTAX               DirectoryString{512}
  EQUALITY MATCHING RULE    caseIgnoreMatch
  SUBSTRINGS MATCHING RULE  caseIgnoreSubstringsMatch
  LDAP-SYNTAX               directoryString.&id
  LDAP-NAME                 {"zimbraMobilePolicyUnapprovedInROMApplication"}
  LDAP-DESC                 "application that can't be run in device ROM; ignored if zimbraFeatureMobilePolicyEnabled=FALSE"
  ID                        id-at-zimbraMobilePolicyUnapprovedInROMApplication }

zimbraMobileShareContactEnabled ATTRIBUTE ::= {
  WITH SYNTAX               BOOLEAN
  EQUALITY MATCHING RULE    booleanMatch
  SINGLE VALUE              TRUE
  LDAP-SYNTAX               boolean.&id
  LDAP-NAME                 {"zimbraMobileShareContactEnabled"}
  LDAP-DESC                 "Whether to permit syncing shared contact folders"
  ID                        id-at-zimbraMobileShareContactEnabled }

zimbraMobileSmartForwardRFC822Enabled ATTRIBUTE ::= {
  WITH SYNTAX               BOOLEAN
  EQUALITY MATCHING RULE    booleanMatch
  SINGLE VALUE              TRUE
  LDAP-SYNTAX               boolean.&id
  LDAP-NAME                 {"zimbraMobileSmartForwardRFC822Enabled"}
  LDAP-DESC                 "indicates whether the application can forward original email as RFC 822 .eml attachment. Note: this setting is applicable only to the devices using activesync smart forward for forwarding email messages."
  ID                        id-at-zimbraMobileSmartForwardRFC822Enabled }

zimbraMobileSyncKeyFormatConvertedFolders ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraMobileSyncKeyFormatConvertedFolders"}
  LDAP-DESC                 "folders whose sync key are already converted, each device has a list of folders. e.g. ApplDN6GJSQJDFHW:0,2,10 meaning device ApplDN6GJSQJDFHW's folders, inbox and calendar folder sync key format are converted, use 0 for FolderSync"
  ID                        id-at-zimbraMobileSyncKeyFormatConvertedFolders }

zimbraMobileSyncRedoMaxAttempts ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraMobileSyncRedoMaxAttempts"}
  LDAP-DESC                 "number of times allowed to retry the same sync version before going into penalty. In general, windows phone should be set to 2, iOS should be set to 1. example of config values: windows:2, ios:1, android:1, default:1"
  ID                        id-at-zimbraMobileSyncRedoMaxAttempts }

zimbraMobileTombstoneEnabled ATTRIBUTE ::= {
  WITH SYNTAX               BOOLEAN
  EQUALITY MATCHING RULE    booleanMatch
  SINGLE VALUE              TRUE
  LDAP-SYNTAX               boolean.&id
  LDAP-NAME                 {"zimbraMobileTombstoneEnabled"}
  LDAP-DESC                 "whether to enable tombstone syncing. If disabled, changes of tombstones won't be synced to device"
  ID                        id-at-zimbraMobileTombstoneEnabled }

zimbraMtaAddressVerifyNegativeRefreshTime ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaAddressVerifyNegativeRefreshTime"}
  LDAP-DESC                 "Value for postconf address_verify_negative_refresh_time"
  ID                        id-at-zimbraMtaAddressVerifyNegativeRefreshTime }

zimbraMtaAddressVerifyPollCount ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaAddressVerifyPollCount"}
  LDAP-DESC                 "Value for postconf address_verify_poll_count"
  ID                        id-at-zimbraMtaAddressVerifyPollCount }

zimbraMtaAddressVerifyPollDelay ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaAddressVerifyPollDelay"}
  LDAP-DESC                 "Value for postconf address_verify_poll_delay"
  ID                        id-at-zimbraMtaAddressVerifyPollDelay }

zimbraMtaAddressVerifyPositiveRefreshTime ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaAddressVerifyPositiveRefreshTime"}
  LDAP-DESC                 "Value for postconf address_verify_positive_refresh_time"
  ID                        id-at-zimbraMtaAddressVerifyPositiveRefreshTime }

zimbraMtaAliasMaps ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaAliasMaps"}
  LDAP-DESC                 "Value for postconf alias_maps. Comma separated list."
  ID                        id-at-zimbraMtaAliasMaps }

-- LDAP syntax length {32} rendered as DirectoryString{32}.
zimbraMtaAlwaysAddMissingHeaders ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraMtaAlwaysAddMissingHeaders"}
  LDAP-DESC                 "Value for postconf always_add_missing_headers"
  ID                        id-at-zimbraMtaAlwaysAddMissingHeaders }

zimbraMtaAntiSpamLockMethod ATTRIBUTE ::= {
  WITH SYNTAX               IA5String(SIZE (1..64))
  EQUALITY MATCHING RULE    caseIgnoreIA5Match
  SUBSTRINGS MATCHING RULE  caseIgnoreSubstringsMatch
  SINGLE VALUE              TRUE
  LDAP-SYNTAX               ia5String.&id
  LDAP-NAME                 {"zimbraMtaAntiSpamLockMethod"}
  LDAP-DESC                 "mta anti spam lock method."
  ID                        id-at-zimbraMtaAntiSpamLockMethod }

zimbraMtaAuthEnabled ATTRIBUTE ::= {
  WITH SYNTAX               BOOLEAN
  EQUALITY MATCHING RULE    booleanMatch
  SINGLE VALUE              TRUE
  LDAP-SYNTAX               boolean.&id
  LDAP-NAME                 {"zimbraMtaAuthEnabled"}
  LDAP-DESC                 "Deprecated since: 6.0.0_BETA1. deprecated in favor of zimbraMtaTlsSecurityLevel and zimbraMtaSaslAuthEnable. Orig desc: Value for postconf smtpd_tls_security_level"
  ID                        id-at-zimbraMtaAuthEnabled }

zimbraMtaAuthHost ATTRIBUTE ::= {
  WITH SYNTAX               IA5String(SIZE (1..256))
  EQUALITY MATCHING RULE    caseIgnoreIA5Match
  SUBSTRINGS MATCHING RULE  caseIgnoreSubstringsMatch
  LDAP-SYNTAX               ia5String.&id
  LDAP-NAME                 {"zimbraMtaAuthHost"}
  LDAP-DESC                 "Deprecated since: 8.6. Formally deprecated in 8.6 but has been unused since at least 7.0. MTA now uses all servers which have zimbraMtaAuthTarget set to TRUE. Orig desc: Host running SOAP service for use by MTA auth. Setting this sets zimbraMtaAuthURL via attr callback mechanism."
  ID                        id-at-zimbraMtaAuthHost }

zimbraMtaAuthTarget ATTRIBUTE ::= {
  WITH SYNTAX               BOOLEAN
  EQUALITY MATCHING RULE    booleanMatch
  SINGLE VALUE              TRUE
  LDAP-SYNTAX               boolean.&id
  LDAP-NAME                 {"zimbraMtaAuthTarget"}
  LDAP-DESC                 "whether this server is a mta auth target"
  ID                        id-at-zimbraMtaAuthTarget }

zimbraMtaAuthURL ATTRIBUTE ::= {
  WITH SYNTAX               IA5String(SIZE (1..256))
  EQUALITY MATCHING RULE    caseIgnoreIA5Match
  SUBSTRINGS MATCHING RULE  caseIgnoreSubstringsMatch
  LDAP-SYNTAX               ia5String.&id
  LDAP-NAME                 {"zimbraMtaAuthURL"}
  LDAP-DESC                 "Deprecated since: 8.6. Formally deprecated in 8.6 but has been unused since at least 7.0. MTA now uses all servers which have zimbraMtaAuthTarget set to TRUE. Orig desc: URL at which this MTA (via zimbra saslauthd) should authenticate. Set by setting zimbraMtaAuthHost."
  ID                        id-at-zimbraMtaAuthURL }

-- LDAP syntax length {64} rendered as DirectoryString{64}.
zimbraMtaBlockedExtension ATTRIBUTE ::= {
  WITH SYNTAX               DirectoryString{64}
  EQUALITY MATCHING RULE    caseIgnoreMatch
  SUBSTRINGS MATCHING RULE  caseIgnoreSubstringsMatch
  LDAP-SYNTAX               directoryString.&id
  LDAP-NAME                 {"zimbraMtaBlockedExtension"}
  LDAP-DESC                 "Attachment file extensions that are blocked"
  ID                        id-at-zimbraMtaBlockedExtension }

zimbraMtaBlockedExtensionWarnAdmin ATTRIBUTE ::= {
  WITH SYNTAX               BOOLEAN
  EQUALITY MATCHING RULE    booleanMatch
  SINGLE VALUE              TRUE
  LDAP-SYNTAX               boolean.&id
  LDAP-NAME                 {"zimbraMtaBlockedExtensionWarnAdmin"}
  LDAP-DESC                 "Whether to email admin on detection of attachment with blocked extension"
  ID                        id-at-zimbraMtaBlockedExtensionWarnAdmin }

zimbraMtaBlockedExtensionWarnRecipient ATTRIBUTE ::= {
  WITH SYNTAX               BOOLEAN
  EQUALITY MATCHING RULE    booleanMatch
  SINGLE VALUE              TRUE
  LDAP-SYNTAX               boolean.&id
  LDAP-NAME                 {"zimbraMtaBlockedExtensionWarnRecipient"}
  LDAP-DESC                 "Whether to email recipient on detection of attachment with blocked extension"
  ID                        id-at-zimbraMtaBlockedExtensionWarnRecipient }

zimbraMtaBounceNoticeRecipient ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaBounceNoticeRecipient"}
  LDAP-DESC                 "Value for postconf bounce_notice_recipient"
  ID                        id-at-zimbraMtaBounceNoticeRecipient }

zimbraMtaBounceQueueLifetime ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaBounceQueueLifetime"}
  LDAP-DESC                 "Value for postconf bounce_queue_lifetime"
  ID                        id-at-zimbraMtaBounceQueueLifetime }

-- LDAP syntax length {32} rendered as DirectoryString{32}.
zimbraMtaBrokenSaslAuthClients ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraMtaBrokenSaslAuthClients"}
  LDAP-DESC                 "Value for postconf broken_sasl_auth_clients"
  ID                        id-at-zimbraMtaBrokenSaslAuthClients }

zimbraMtaCommandDirectory ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaCommandDirectory"}
  LDAP-DESC                 "Value for postconf command_directory"
  ID                        id-at-zimbraMtaCommandDirectory }

-- LDAP syntax length {64} rendered as DirectoryString{64}.
zimbraMtaCommonBlockedExtension ATTRIBUTE ::= {
  WITH SYNTAX               DirectoryString{64}
  EQUALITY MATCHING RULE    caseIgnoreMatch
  SUBSTRINGS MATCHING RULE  caseIgnoreSubstringsMatch
  LDAP-SYNTAX               directoryString.&id
  LDAP-NAME                 {"zimbraMtaCommonBlockedExtension"}
  LDAP-DESC                 "Commonly blocked attachment file extensions"
  ID                        id-at-zimbraMtaCommonBlockedExtension }

zimbraMtaDaemonDirectory ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaDaemonDirectory"}
  LDAP-DESC                 "Value for postconf daemon_directory"
  ID                        id-at-zimbraMtaDaemonDirectory }

zimbraMtaDefaultProcessLimit ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaDefaultProcessLimit"}
  LDAP-DESC                 "Value for postconf default_process_limit"
  ID                        id-at-zimbraMtaDefaultProcessLimit }

zimbraMtaDelayWarningTime ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaDelayWarningTime"}
  LDAP-DESC                 "Value for postconf delay_warning_time"
  ID                        id-at-zimbraMtaDelayWarningTime }

zimbraMtaDnsLookupsEnabled ATTRIBUTE ::= {
  WITH SYNTAX               BOOLEAN
  EQUALITY MATCHING RULE    booleanMatch
  SINGLE VALUE              TRUE
  LDAP-SYNTAX               boolean.&id
  LDAP-NAME                 {"zimbraMtaDnsLookupsEnabled"}
  LDAP-DESC                 "Value for postconf disable_dns_lookups (note enable v. disable)"
  ID                        id-at-zimbraMtaDnsLookupsEnabled }

zimbraMtaEnableSmtpdPolicyd ATTRIBUTE ::= {
  WITH SYNTAX               BOOLEAN
  EQUALITY MATCHING RULE    booleanMatch
  SINGLE VALUE              TRUE
  LDAP-SYNTAX               boolean.&id
  LDAP-NAME                 {"zimbraMtaEnableSmtpdPolicyd"}
  LDAP-DESC                 "Whether or not to enable zmpostfixpolicyd with MTA. Defaults to FALSE"
  ID                        id-at-zimbraMtaEnableSmtpdPolicyd }

zimbraMtaFallbackRelayHost ATTRIBUTE ::= {
  WITH SYNTAX               IA5String(SIZE (1..256))
  EQUALITY MATCHING RULE    caseIgnoreIA5Match
  SUBSTRINGS MATCHING RULE  caseIgnoreSubstringsMatch
  SINGLE VALUE              TRUE
  LDAP-SYNTAX               ia5String.&id
  LDAP-NAME                 {"zimbraMtaFallbackRelayHost"}
  LDAP-DESC                 "Fallback value for postconf relayhost."
  ID                        id-at-zimbraMtaFallbackRelayHost }

zimbraMtaHeaderChecks ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraMtaHeaderChecks"}
  LDAP-DESC                 "Value for postconf header_checks"
  ID                        id-at-zimbraMtaHeaderChecks }

zimbraMtaImportEnvironment ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraMtaImportEnvironment"}
  LDAP-DESC                 "Value for postconf import_environment"
  ID                        id-at-zimbraMtaImportEnvironment }

zimbraMtaInFlowDelay ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaInFlowDelay"}
  LDAP-DESC                 "Value for postconf in_flow_delay"
  ID                        id-at-zimbraMtaInFlowDelay }

zimbraMtaLmdbMapSize ATTRIBUTE ::= {
  WITH SYNTAX               INTEGER
  EQUALITY MATCHING RULE    integerMatch
  SINGLE VALUE              TRUE
  LDAP-SYNTAX               integer.&id
  LDAP-NAME                 {"zimbraMtaLmdbMapSize"}
  LDAP-DESC                 "Maximum Map size for MTA LMDB dbs. Defaults to 16777216 (16MB). Databases will not grow beyond this point."
  ID                        id-at-zimbraMtaLmdbMapSize }

zimbraMtaLmtpConnectionCacheDestinations ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraMtaLmtpConnectionCacheDestinations"}
  LDAP-DESC                 "Value for postconf lmtp_connection_cache_destinations"
  ID                        id-at-zimbraMtaLmtpConnectionCacheDestinations }

zimbraMtaLmtpConnectionCacheTimeLimit ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaLmtpConnectionCacheTimeLimit"}
  LDAP-DESC                 "Value for postconf lmtp_connection_cache_time_limit"
  ID                        id-at-zimbraMtaLmtpConnectionCacheTimeLimit }

-- LDAP syntax length {32} rendered as DirectoryString{32}.
zimbraMtaLmtpHostLookup ATTRIBUTE ::= {
  WITH SYNTAX               DirectoryString{32}
  EQUALITY MATCHING RULE    caseIgnoreMatch
  SUBSTRINGS MATCHING RULE  caseIgnoreSubstringsMatch
  LDAP-SYNTAX               directoryString.&id
  LDAP-NAME                 {"zimbraMtaLmtpHostLookup"}
  LDAP-DESC                 "Value for postconf lmtp_host_lookup"
  ID                        id-at-zimbraMtaLmtpHostLookup }

zimbraMtaLmtpTlsCAfile ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaLmtpTlsCAfile"}
  LDAP-DESC                 "Value for postconf lmtp_tls_CAfile"
  ID                        id-at-zimbraMtaLmtpTlsCAfile }

zimbraMtaLmtpTlsCApath ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaLmtpTlsCApath"}
  LDAP-DESC                 "Value for postconf lmtp_tls_CApath"
  ID                        id-at-zimbraMtaLmtpTlsCApath }

-- LDAP syntax length {32} rendered as DirectoryString{32}.
zimbraMtaLmtpTlsCiphers ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraMtaLmtpTlsCiphers"}
  LDAP-DESC                 "Value for postconf lmtp_tls_ciphers"
  ID                        id-at-zimbraMtaLmtpTlsCiphers }

zimbraMtaLmtpTlsExcludeCiphers ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaLmtpTlsExcludeCiphers"}
  LDAP-DESC                 "Value for postconf lmtp_tls_exclude_ciphers"
  ID                        id-at-zimbraMtaLmtpTlsExcludeCiphers }

zimbraMtaLmtpTlsLoglevel ATTRIBUTE ::= {
  WITH SYNTAX               INTEGER
  EQUALITY MATCHING RULE    integerMatch
  SINGLE VALUE              TRUE
  LDAP-SYNTAX               integer.&id
  LDAP-NAME                 {"zimbraMtaLmtpTlsLoglevel"}
  LDAP-DESC                 "Value for postconf lmtp_tls_loglevel. Defaults to 0. Valid range is 0-4"
  ID                        id-at-zimbraMtaLmtpTlsLoglevel }

-- LDAP syntax length {32} rendered as DirectoryString{32}.
zimbraMtaLmtpTlsMandatoryCiphers ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraMtaLmtpTlsMandatoryCiphers"}
  LDAP-DESC                 "Value for postconf lmtp_tls_mandatory_ciphers"
  ID                        id-at-zimbraMtaLmtpTlsMandatoryCiphers }

zimbraMtaLmtpTlsProtocols ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaLmtpTlsProtocols"}
  LDAP-DESC                 "Value for postconf lmtp_tls_protocols"
  ID                        id-at-zimbraMtaLmtpTlsProtocols }

-- LDAP syntax length {32} rendered as DirectoryString{32}.
zimbraMtaLmtpTlsSecurityLevel ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraMtaLmtpTlsSecurityLevel"}
  LDAP-DESC                 "Value for postconf lmtp_tls_security_level"
  ID                        id-at-zimbraMtaLmtpTlsSecurityLevel }

zimbraMtaMailqPath ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaMailqPath"}
  LDAP-DESC                 "Value for postconf mailq_path"
  ID                        id-at-zimbraMtaMailqPath }

zimbraMtaManpageDirectory ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaManpageDirectory"}
  LDAP-DESC                 "Value for postconf manpage_directory"
  ID                        id-at-zimbraMtaManpageDirectory }

zimbraMtaMaxMessageSize ATTRIBUTE ::= {
  WITH SYNTAX               INTEGER
  EQUALITY MATCHING RULE    integerMatch
  SINGLE VALUE              TRUE
  LDAP-SYNTAX               integer.&id
  LDAP-NAME                 {"zimbraMtaMaxMessageSize"}
  LDAP-DESC                 "Maximum total size of a mail message. Enforced in mailbox server and also used as value for postconf message_size_limit. 0 means ""no limit"""
  ID                        id-at-zimbraMtaMaxMessageSize }

zimbraMtaMaxUse ATTRIBUTE ::= {
  WITH SYNTAX               INTEGER
  EQUALITY MATCHING RULE    integerMatch
  SINGLE VALUE              TRUE
  LDAP-SYNTAX               integer.&id
  LDAP-NAME                 {"zimbraMtaMaxUse"}
  LDAP-DESC                 "Value for postconf max_use"
  ID                        id-at-zimbraMtaMaxUse }

zimbraMtaMaximalBackoffTime ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaMaximalBackoffTime"}
  LDAP-DESC                 "Value for postconf maximal_backoff_time"
  ID                        id-at-zimbraMtaMaximalBackoffTime }

zimbraMtaMilterCommandTimeout ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaMilterCommandTimeout"}
  LDAP-DESC                 "Value for postconf milter_command_timeout"
  ID                        id-at-zimbraMtaMilterCommandTimeout }

zimbraMtaMilterConnectTimeout ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaMilterConnectTimeout"}
  LDAP-DESC                 "Value for postconf milter_connect_timeout"
  ID                        id-at-zimbraMtaMilterConnectTimeout }

zimbraMtaMilterContentTimeout ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaMilterContentTimeout"}
  LDAP-DESC                 "Value for postconf milter_content_timeout"
  ID                        id-at-zimbraMtaMilterContentTimeout }

-- LDAP syntax length {32} rendered as DirectoryString{32}.
zimbraMtaMilterDefaultAction ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraMtaMilterDefaultAction"}
  LDAP-DESC                 "Value for postconf milter_default_action"
  ID                        id-at-zimbraMtaMilterDefaultAction }

zimbraMtaMinimalBackoffTime ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaMinimalBackoffTime"}
  LDAP-DESC                 "Value for postconf minimal_backoff_time"
  ID                        id-at-zimbraMtaMinimalBackoffTime }

zimbraMtaMyDestination ATTRIBUTE ::= {
  WITH SYNTAX               IA5String(SIZE (1..256))
  EQUALITY MATCHING RULE    caseIgnoreIA5Match
  SUBSTRINGS MATCHING RULE  caseIgnoreSubstringsMatch
  SINGLE VALUE              TRUE
  LDAP-SYNTAX               ia5String.&id
  LDAP-NAME                 {"zimbraMtaMyDestination"}
  LDAP-DESC                 "value of postfix mydestination"
  ID                        id-at-zimbraMtaMyDestination }

zimbraMtaMyHostname ATTRIBUTE ::= {
  WITH SYNTAX               IA5String(SIZE (1..256))
  EQUALITY MATCHING RULE    caseIgnoreIA5Match
  SUBSTRINGS MATCHING RULE  caseIgnoreSubstringsMatch
  SINGLE VALUE              TRUE
  LDAP-SYNTAX               ia5String.&id
  LDAP-NAME                 {"zimbraMtaMyHostname"}
  LDAP-DESC                 "value of postfix myhostname"
  ID                        id-at-zimbraMtaMyHostname }

zimbraMtaMyNetworks ATTRIBUTE ::= {
  WITH SYNTAX               IA5String(SIZE (1..10240))
  EQUALITY MATCHING RULE    caseIgnoreIA5Match
  SUBSTRINGS MATCHING RULE  caseIgnoreSubstringsMatch
  LDAP-SYNTAX               ia5String.&id
  LDAP-NAME                 {"zimbraMtaMyNetworks"}
  LDAP-DESC                 "value of postfix mynetworks"
  ID                        id-at-zimbraMtaMyNetworks }

zimbraMtaMyOrigin ATTRIBUTE ::= {
  WITH SYNTAX               IA5String(SIZE (1..256))
  EQUALITY MATCHING RULE    caseIgnoreIA5Match
  SUBSTRINGS MATCHING RULE  caseIgnoreSubstringsMatch
  SINGLE VALUE              TRUE
  LDAP-SYNTAX               ia5String.&id
  LDAP-NAME                 {"zimbraMtaMyOrigin"}
  LDAP-DESC                 "value of postfix myorigin"
  ID                        id-at-zimbraMtaMyOrigin }

zimbraMtaNewaliasesPath ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaNewaliasesPath"}
  LDAP-DESC                 "Value for postconf newaliases_path"
  ID                        id-at-zimbraMtaNewaliasesPath }

-- LDAP syntax length {1024} rendered as DirectoryString{1024}.
zimbraMtaNonSmtpdMilters ATTRIBUTE ::= {
  WITH SYNTAX               DirectoryString{1024}
  EQUALITY MATCHING RULE    caseIgnoreMatch
  SUBSTRINGS MATCHING RULE  caseIgnoreSubstringsMatch
  SINGLE VALUE              TRUE
  LDAP-SYNTAX               directoryString.&id
  LDAP-NAME                 {"zimbraMtaNonSmtpdMilters"}
  LDAP-DESC                 "value for postfix non_smtpd_milters"
  ID                        id-at-zimbraMtaNonSmtpdMilters }

-- LDAP syntax length {32} rendered as DirectoryString{32}.
zimbraMtaNotifyClasses ATTRIBUTE ::= {
  WITH SYNTAX               DirectoryString{32}
  EQUALITY MATCHING RULE    caseIgnoreMatch
  SUBSTRINGS MATCHING RULE  caseIgnoreSubstringsMatch
  LDAP-SYNTAX               directoryString.&id
  LDAP-NAME                 {"zimbraMtaNotifyClasses"}
  LDAP-DESC                 "Value for postconf notify_classes"
  ID                        id-at-zimbraMtaNotifyClasses }

zimbraMtaPolicyTimeLimit ATTRIBUTE ::= {
  WITH SYNTAX               INTEGER
  EQUALITY MATCHING RULE    integerMatch
  SINGLE VALUE              TRUE
  LDAP-SYNTAX               integer.&id
  LDAP-NAME                 {"zimbraMtaPolicyTimeLimit"}
  LDAP-DESC                 "Value for postconf policy_time_limit"
  ID                        id-at-zimbraMtaPolicyTimeLimit }

-- LDAP syntax length {32} rendered as DirectoryString{32}.
zimbraMtaPropagateUnmatchedExtensions ATTRIBUTE ::= {
  WITH SYNTAX               DirectoryString{32}
  EQUALITY MATCHING RULE    caseIgnoreMatch
  SUBSTRINGS MATCHING RULE  caseIgnoreSubstringsMatch
  LDAP-SYNTAX               directoryString.&id
  LDAP-NAME                 {"zimbraMtaPropagateUnmatchedExtensions"}
  LDAP-DESC                 "Value for postconf propagate_unmatched_extensions"
  ID                        id-at-zimbraMtaPropagateUnmatchedExtensions }

zimbraMtaQueueDirectory ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaQueueDirectory"}
  LDAP-DESC                 "Value for postconf queue_directory"
  ID                        id-at-zimbraMtaQueueDirectory }

zimbraMtaQueueRunDelay ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaQueueRunDelay"}
  LDAP-DESC                 "Value for postconf queue_run_delay"
  ID                        id-at-zimbraMtaQueueRunDelay }

zimbraMtaRecipientDelimiter ATTRIBUTE ::= {
  WITH SYNTAX               IA5String(SIZE (1..256))
  EQUALITY MATCHING RULE    caseIgnoreIA5Match
  SUBSTRINGS MATCHING RULE  caseIgnoreSubstringsMatch
  LDAP-SYNTAX               ia5String.&id
  LDAP-NAME                 {"zimbraMtaRecipientDelimiter"}
  LDAP-DESC                 "Value for postconf recipient_delimiter. Also used by ZCS LMTP server to check if it should accept messages to addresses with extensions."
  ID                        id-at-zimbraMtaRecipientDelimiter }

zimbraMtaRelayHost ATTRIBUTE ::= {
  WITH SYNTAX               IA5String(SIZE (1..256))
  EQUALITY MATCHING RULE    caseIgnoreIA5Match
  SUBSTRINGS MATCHING RULE  caseIgnoreSubstringsMatch
  LDAP-SYNTAX               ia5String.&id
  LDAP-NAME                 {"zimbraMtaRelayHost"}
  LDAP-DESC                 "Value for postconf relayhost. Note: there can be only one value on this attribute, see bug 50697."
  ID                        id-at-zimbraMtaRelayHost }

-- LDAP syntax length {2048} rendered as DirectoryString{2048}.
zimbraMtaRestriction ATTRIBUTE ::= {
  WITH SYNTAX               DirectoryString{2048}
  EQUALITY MATCHING RULE    caseIgnoreMatch
  SUBSTRINGS MATCHING RULE  caseIgnoreSubstringsMatch
  LDAP-SYNTAX               directoryString.&id
  LDAP-NAME                 {"zimbraMtaRestriction"}
  LDAP-DESC                 "smtpd_recipient_restrictions used to reject email in various scenarios"
  ID                        id-at-zimbraMtaRestriction }

-- LDAP syntax length {32} rendered as DirectoryString{32}.
zimbraMtaSaslAuthEnable ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraMtaSaslAuthEnable"}
  LDAP-DESC                 "Value for postconf smtpd_sasl_auth_enable"
  ID                        id-at-zimbraMtaSaslAuthEnable }

zimbraMtaSaslSmtpdMechList ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraMtaSaslSmtpdMechList"}
  LDAP-DESC                 "Supported SASL mechanisms for use with the MTA. One attribute value per mechanism."
  ID                        id-at-zimbraMtaSaslSmtpdMechList }

zimbraMtaSenderCanonicalMaps ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaSenderCanonicalMaps"}
  LDAP-DESC                 "Value for postconf sender_canonical_maps. Comma separated list."
  ID                        id-at-zimbraMtaSenderCanonicalMaps }

zimbraMtaSendmailPath ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaSendmailPath"}
  LDAP-DESC                 "Value for postconf sendmail_path"
  ID                        id-at-zimbraMtaSendmailPath }

-- LDAP syntax length {32} rendered as DirectoryString{32}.
zimbraMtaSmtpCnameOverridesServername ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraMtaSmtpCnameOverridesServername"}
  LDAP-DESC                 "Value for postconf smtp_cname_overrides_servername"
  ID                        id-at-zimbraMtaSmtpCnameOverridesServername }

zimbraMtaSmtpGenericMaps ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaSmtpGenericMaps"}
  LDAP-DESC                 "Value for postconf smtp_generic_maps"
  ID                        id-at-zimbraMtaSmtpGenericMaps }

zimbraMtaSmtpHeloName ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaSmtpHeloName"}
  LDAP-DESC                 "Value for postconf smtp_helo_name"
  ID                        id-at-zimbraMtaSmtpHeloName }

-- LDAP syntax length {32} rendered as DirectoryString{32}.
zimbraMtaSmtpSaslAuthEnable ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraMtaSmtpSaslAuthEnable"}
  LDAP-DESC                 "Value for postconf smtp_sasl_auth_enable"
  ID                        id-at-zimbraMtaSmtpSaslAuthEnable }

zimbraMtaSmtpSaslMechanismFilter ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraMtaSmtpSaslMechanismFilter"}
  LDAP-DESC                 "Value for postconf smtp_sasl_mechanism_filter"
  ID                        id-at-zimbraMtaSmtpSaslMechanismFilter }

zimbraMtaSmtpSaslPasswordMaps ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaSmtpSaslPasswordMaps"}
  LDAP-DESC                 "Value for postconf smtp_sasl_password_maps. Comma separated list."
  ID                        id-at-zimbraMtaSmtpSaslPasswordMaps }

-- LDAP syntax length {32} rendered as DirectoryString{32}.
zimbraMtaSmtpSaslSecurityOptions ATTRIBUTE ::= {
  WITH SYNTAX               DirectoryString{32}
  EQUALITY MATCHING RULE    caseIgnoreMatch
  SUBSTRINGS MATCHING RULE  caseIgnoreSubstringsMatch
  LDAP-SYNTAX               directoryString.&id
  LDAP-NAME                 {"zimbraMtaSmtpSaslSecurityOptions"}
  LDAP-DESC                 "Value for postconf smtp_sasl_security_options"
  ID                        id-at-zimbraMtaSmtpSaslSecurityOptions }

zimbraMtaSmtpTlsCAfile ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaSmtpTlsCAfile"}
  LDAP-DESC                 "Value for postconf smtp_tls_CAfile"
  ID                        id-at-zimbraMtaSmtpTlsCAfile }

zimbraMtaSmtpTlsCApath ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaSmtpTlsCApath"}
  LDAP-DESC                 "Value for postconf smtp_tls_CApath"
  ID                        id-at-zimbraMtaSmtpTlsCApath }

-- LDAP syntax length {32} rendered as DirectoryString{32}.
zimbraMtaSmtpTlsCiphers ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraMtaSmtpTlsCiphers"}
  LDAP-DESC                 "Value for postconf smtp_tls_ciphers"
  ID                        id-at-zimbraMtaSmtpTlsCiphers }

zimbraMtaSmtpTlsLoglevel ATTRIBUTE ::= {
  WITH SYNTAX               INTEGER
  EQUALITY MATCHING RULE    integerMatch
  SINGLE VALUE              TRUE
  LDAP-SYNTAX               integer.&id
  LDAP-NAME                 {"zimbraMtaSmtpTlsLoglevel"}
  LDAP-DESC                 "Value for postconf smtp_tls_loglevel. Defaults to 0. Valid range is 0-4"
  ID                        id-at-zimbraMtaSmtpTlsLoglevel }

-- LDAP syntax length {32} rendered as DirectoryString{32}.
zimbraMtaSmtpTlsMandatoryCiphers ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraMtaSmtpTlsMandatoryCiphers"}
  LDAP-DESC                 "Value for postconf smtp_tls_mandatory_ciphers"
  ID                        id-at-zimbraMtaSmtpTlsMandatoryCiphers }

zimbraMtaSmtpTlsProtocols ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaSmtpTlsProtocols"}
  LDAP-DESC                 "Value for postconf smtp_tls_protocols"
  ID                        id-at-zimbraMtaSmtpTlsProtocols }

-- LDAP syntax length {32} rendered as DirectoryString{32}.
zimbraMtaSmtpTlsSecurityLevel ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraMtaSmtpTlsSecurityLevel"}
  LDAP-DESC                 "Value for postconf smtp_tls_security_level"
  ID                        id-at-zimbraMtaSmtpTlsSecurityLevel }

zimbraMtaSmtpdBanner ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaSmtpdBanner"}
  LDAP-DESC                 "Value for postconf smtpd_banner"
  ID                        id-at-zimbraMtaSmtpdBanner }

-- LDAP syntax length {32} rendered as DirectoryString{32}.
zimbraMtaSmtpdClientPortLogging ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraMtaSmtpdClientPortLogging"}
  LDAP-DESC                 "Value for postconf smtpd_client_port_logging. Defaults to no"
  ID                        id-at-zimbraMtaSmtpdClientPortLogging }

zimbraMtaSmtpdClientRestrictions ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaSmtpdClientRestrictions"}
  LDAP-DESC                 "Value for postconf smtpd_client_restrictions"
  ID                        id-at-zimbraMtaSmtpdClientRestrictions }

zimbraMtaSmtpdDataRestrictions ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaSmtpdDataRestrictions"}
  LDAP-DESC                 "Value for postconf smtpd_data_restrictions"
  ID                        id-at-zimbraMtaSmtpdDataRestrictions }

zimbraMtaSmtpdErrorSleepTime ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaSmtpdErrorSleepTime"}
  LDAP-DESC                 "Value for postconf smtpd_error_sleep_time"
  ID                        id-at-zimbraMtaSmtpdErrorSleepTime }

zimbraMtaSmtpdHardErrorLimit ATTRIBUTE ::= {
  WITH SYNTAX               INTEGER
  EQUALITY MATCHING RULE    integerMatch
  SINGLE VALUE              TRUE
  LDAP-SYNTAX               integer.&id
  LDAP-NAME                 {"zimbraMtaSmtpdHardErrorLimit"}
  LDAP-DESC                 "Value for postconf smtpd_hard_error_limit"
  ID                        id-at-zimbraMtaSmtpdHardErrorLimit }

-- LDAP syntax length {32} rendered as DirectoryString{32}.
zimbraMtaSmtpdHeloRequired ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraMtaSmtpdHeloRequired"}
  LDAP-DESC                 "Value for postconf smtpd_helo_required"
  ID                        id-at-zimbraMtaSmtpdHeloRequired }

-- LDAP syntax length {1024} rendered as DirectoryString{1024}.
zimbraMtaSmtpdMilters ATTRIBUTE ::= {
  WITH SYNTAX               DirectoryString{1024}
  EQUALITY MATCHING RULE    caseIgnoreMatch
  SUBSTRINGS MATCHING RULE  caseIgnoreSubstringsMatch
  SINGLE VALUE              TRUE
  LDAP-SYNTAX               directoryString.&id
  LDAP-NAME                 {"zimbraMtaSmtpdMilters"}
  LDAP-DESC                 "value for postfix smtpd_milters"
  ID                        id-at-zimbraMtaSmtpdMilters }

zimbraMtaSmtpdProxyTimeout ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaSmtpdProxyTimeout"}
  LDAP-DESC                 "Value for postconf smtpd_proxy_timeout"
  ID                        id-at-zimbraMtaSmtpdProxyTimeout }

-- LDAP syntax length {32} rendered as DirectoryString{32}.
zimbraMtaSmtpdRejectUnlistedRecipient ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraMtaSmtpdRejectUnlistedRecipient"}
  LDAP-DESC                 "Value for postconf smtpd_reject_unlisted_recipient"
  ID                        id-at-zimbraMtaSmtpdRejectUnlistedRecipient }

-- LDAP syntax length {32} rendered as DirectoryString{32}.
zimbraMtaSmtpdRejectUnlistedSender ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraMtaSmtpdRejectUnlistedSender"}
  LDAP-DESC                 "Value for postconf smtpd_reject_unlisted_sender"
  ID                        id-at-zimbraMtaSmtpdRejectUnlistedSender }

-- LDAP syntax length {32} rendered as DirectoryString{32}.
zimbraMtaSmtpdSaslAuthenticatedHeader ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraMtaSmtpdSaslAuthenticatedHeader"}
  LDAP-DESC                 "Value for postconf smtpd_sasl_authenticated_header"
  ID                        id-at-zimbraMtaSmtpdSaslAuthenticatedHeader }

-- LDAP syntax length {32} rendered as DirectoryString{32}.
zimbraMtaSmtpdSaslSecurityOptions ATTRIBUTE ::= {
  WITH SYNTAX               DirectoryString{32}
  EQUALITY MATCHING RULE    caseIgnoreMatch
  SUBSTRINGS MATCHING RULE  caseIgnoreSubstringsMatch
  LDAP-SYNTAX               directoryString.&id
  LDAP-NAME                 {"zimbraMtaSmtpdSaslSecurityOptions"}
  LDAP-DESC                 "Value for postconf smtpd_sasl_security_options"
  ID                        id-at-zimbraMtaSmtpdSaslSecurityOptions }

zimbraMtaSmtpdSaslTlsSecurityOptions ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraMtaSmtpdSaslTlsSecurityOptions"}
  LDAP-DESC                 "Value for postconf smtpd_sasl_tls_security_options"
  ID                        id-at-zimbraMtaSmtpdSaslTlsSecurityOptions }

zimbraMtaSmtpdSenderLoginMaps ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaSmtpdSenderLoginMaps"}
  LDAP-DESC                 "Value for postconf smtpd_sender_login_maps"
  ID                        id-at-zimbraMtaSmtpdSenderLoginMaps }

zimbraMtaSmtpdSenderRestrictions ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaSmtpdSenderRestrictions"}
  LDAP-DESC                 "Value for postconf smtpd_sender_restrictions"
  ID                        id-at-zimbraMtaSmtpdSenderRestrictions }

-- LDAP syntax length {32} rendered as DirectoryString{32}.
zimbraMtaSmtpdTlsAskCcert ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraMtaSmtpdTlsAskCcert"}
  LDAP-DESC                 "Value for postconf smtpd_tls_ask_ccert"
  ID                        id-at-zimbraMtaSmtpdTlsAskCcert }

zimbraMtaSmtpdTlsCAfile ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaSmtpdTlsCAfile"}
  LDAP-DESC                 "Value for postconf smtpd_tls_CAfile"
  ID                        id-at-zimbraMtaSmtpdTlsCAfile }

zimbraMtaSmtpdTlsCApath ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaSmtpdTlsCApath"}
  LDAP-DESC                 "Value for postconf smtpd_tls_CApath"
  ID                        id-at-zimbraMtaSmtpdTlsCApath }

zimbraMtaSmtpdTlsCcertVerifydepth ATTRIBUTE ::= {
  WITH SYNTAX               INTEGER
  EQUALITY MATCHING RULE    integerMatch
  SINGLE VALUE              TRUE
  LDAP-SYNTAX               integer.&id
  LDAP-NAME                 {"zimbraMtaSmtpdTlsCcertVerifydepth"}
  LDAP-DESC                 "Value for postconf smtpd_tls_ccert_verifydepth"
  ID                        id-at-zimbraMtaSmtpdTlsCcertVerifydepth }

-- LDAP syntax length {32} rendered as DirectoryString{32}.
zimbraMtaSmtpdTlsCiphers ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraMtaSmtpdTlsCiphers"}
  LDAP-DESC                 "Value for postconf smtpd_tls_ciphers"
  ID                        id-at-zimbraMtaSmtpdTlsCiphers }

zimbraMtaSmtpdTlsExcludeCiphers ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaSmtpdTlsExcludeCiphers"}
  LDAP-DESC                 "Value for postconf smtpd_tls_exclude_ciphers"
  ID                        id-at-zimbraMtaSmtpdTlsExcludeCiphers }

zimbraMtaSmtpdTlsLoglevel ATTRIBUTE ::= {
  WITH SYNTAX               INTEGER
  EQUALITY MATCHING RULE    integerMatch
  SINGLE VALUE              TRUE
  LDAP-SYNTAX               integer.&id
  LDAP-NAME                 {"zimbraMtaSmtpdTlsLoglevel"}
  LDAP-DESC                 "Value for postconf smtpd_tls_loglevel. Default is 1. Valid range is 1-4."
  ID                        id-at-zimbraMtaSmtpdTlsLoglevel }

-- LDAP syntax length {32} rendered as DirectoryString{32}.
zimbraMtaSmtpdTlsMandatoryCiphers ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraMtaSmtpdTlsMandatoryCiphers"}
  LDAP-DESC                 "Value for postconf smtpd_tls_mandatory_ciphers"
  ID                        id-at-zimbraMtaSmtpdTlsMandatoryCiphers }

zimbraMtaSmtpdTlsProtocols ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaSmtpdTlsProtocols"}
  LDAP-DESC                 "Value for postconf smtpd_tls_protocols"
  ID                        id-at-zimbraMtaSmtpdTlsProtocols }

zimbraMtaSmtpdVirtualTransport ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaSmtpdVirtualTransport"}
  LDAP-DESC                 "Value for postconf virtual_transport"
  ID                        id-at-zimbraMtaSmtpdVirtualTransport }

zimbraMtaStpdSoftErrorLimit ATTRIBUTE ::= {
  WITH SYNTAX               INTEGER
  EQUALITY MATCHING RULE    integerMatch
  SINGLE VALUE              TRUE
  LDAP-SYNTAX               integer.&id
  LDAP-NAME                 {"zimbraMtaStpdSoftErrorLimit"}
  LDAP-DESC                 "Value for postconf smtpd_soft_error_limit"
  ID                        id-at-zimbraMtaStpdSoftErrorLimit }

-- LDAP syntax length {32} rendered as DirectoryString{32}.
zimbraMtaTlsAppendDefaultCA ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraMtaTlsAppendDefaultCA"}
  LDAP-DESC                 "Value for postconf tls_append_default_CA"
  ID                        id-at-zimbraMtaTlsAppendDefaultCA }

zimbraMtaTlsAuthOnly ATTRIBUTE ::= {
  WITH SYNTAX               BOOLEAN
  EQUALITY MATCHING RULE    booleanMatch
  SINGLE VALUE              TRUE
  LDAP-SYNTAX               boolean.&id
  LDAP-NAME                 {"zimbraMtaTlsAuthOnly"}
  LDAP-DESC                 "Value for postconf smtpd_tls_auth_only"
  ID                        id-at-zimbraMtaTlsAuthOnly }

-- LDAP syntax length {32} rendered as DirectoryString{32}.
zimbraMtaTlsSecurityLevel ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraMtaTlsSecurityLevel"}
  LDAP-DESC                 "Value for postconf smtpd_tls_security_level"
  ID                        id-at-zimbraMtaTlsSecurityLevel }

zimbraMtaTransportMaps ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaTransportMaps"}
  LDAP-DESC                 "Value for postconf transport_maps. Comma separated list."
  ID                        id-at-zimbraMtaTransportMaps }

zimbraMtaUnverifiedRecipientDeferCode ATTRIBUTE ::= {
  WITH SYNTAX               INTEGER
  EQUALITY MATCHING RULE    integerMatch
  SINGLE VALUE              TRUE
  LDAP-SYNTAX               integer.&id
  LDAP-NAME                 {"zimbraMtaUnverifiedRecipientDeferCode"}
  LDAP-DESC                 "Value for postconf unverified_recipient_defer_code"
  ID                        id-at-zimbraMtaUnverifiedRecipientDeferCode }

zimbraMtaVirtualAliasDomains ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaVirtualAliasDomains"}
  LDAP-DESC                 "Value for postconf virtual_alias_domains. Comma separated list."
  ID                        id-at-zimbraMtaVirtualAliasDomains }

zimbraMtaVirtualAliasExpansionLimit ATTRIBUTE ::= {
  WITH SYNTAX               INTEGER
  EQUALITY MATCHING RULE    integerMatch
  SINGLE VALUE              TRUE
  LDAP-SYNTAX               integer.&id
  LDAP-NAME                 {"zimbraMtaVirtualAliasExpansionLimit"}
  LDAP-DESC                 "Value for postconf virtual_alias_expansion_limit"
  ID                        id-at-zimbraMtaVirtualAliasExpansionLimit }

zimbraMtaVirtualAliasMaps ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaVirtualAliasMaps"}
  LDAP-DESC                 "Value for postconf virtual_alias_maps. Comma separated list."
  ID                        id-at-zimbraMtaVirtualAliasMaps }

zimbraMtaVirtualMailboxDomains ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaVirtualMailboxDomains"}
  LDAP-DESC                 "Value for postconf virtual_mailbox_domains. Comma separated list."
  ID                        id-at-zimbraMtaVirtualMailboxDomains }

zimbraMtaVirtualMailboxMaps ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraMtaVirtualMailboxMaps"}
  LDAP-DESC                 "Value for postconf virtual_mailbox_maps. Comma separated list."
  ID                        id-at-zimbraMtaVirtualMailboxMaps }

zimbraMyoneloginSamlSigningCert ATTRIBUTE ::= {
  WITH SYNTAX               IA5String
  EQUALITY MATCHING RULE    caseIgnoreIA5Match
  SUBSTRINGS MATCHING RULE  caseIgnoreSubstringsMatch
  SINGLE VALUE              TRUE
  LDAP-SYNTAX               ia5String.&id
  LDAP-NAME                 {"zimbraMyoneloginSamlSigningCert"}
  LDAP-DESC                 "certificate to be used for validating the SAML assertions received from myonelogin (tricipher)"
  ID                        id-at-zimbraMyoneloginSamlSigningCert }

zimbraNetworkActivation ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraNetworkActivation"}
  LDAP-DESC                 "A signed activation key that authorizes this installation."
  ID                        id-at-zimbraNetworkActivation }

zimbraNetworkLicense ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraNetworkLicense"}
  LDAP-DESC                 "Contents of a signed Zimbra license key - an XML string."
  ID                        id-at-zimbraNetworkLicense }

-- LDAP syntax length {10000} rendered as DirectoryString{10000}.
zimbraNewMailNotificationBody ATTRIBUTE ::= {
  WITH SYNTAX               DirectoryString{10000}
  EQUALITY MATCHING RULE    caseIgnoreMatch
  SUBSTRINGS MATCHING RULE  caseIgnoreSubstringsMatch
  SINGLE VALUE              TRUE
  LDAP-SYNTAX               directoryString.&id
  LDAP-NAME                 {"zimbraNewMailNotificationBody"}
  LDAP-DESC                 "template used to construct the body of an email notification message"
  ID                        id-at-zimbraNewMailNotificationBody }

-- LDAP syntax length {1000} rendered as DirectoryString{1000}.
zimbraNewMailNotificationFrom ATTRIBUTE ::= {
  WITH SYNTAX               DirectoryString{1000}
  EQUALITY MATCHING RULE    caseIgnoreMatch
  SUBSTRINGS MATCHING RULE  caseIgnoreSubstringsMatch
  SINGLE VALUE              TRUE
  LDAP-SYNTAX               directoryString.&id
  LDAP-NAME                 {"zimbraNewMailNotificationFrom"}
  LDAP-DESC                 "template used to construct the sender of an email notification message"
  ID                        id-at-zimbraNewMailNotificationFrom }

-- LDAP syntax length {1000} rendered as DirectoryString{1000}.
zimbraNewMailNotificationSubject ATTRIBUTE ::= {
  WITH SYNTAX               DirectoryString{1000}
  EQUALITY MATCHING RULE    caseIgnoreMatch
  SUBSTRINGS MATCHING RULE  caseIgnoreSubstringsMatch
  SINGLE VALUE              TRUE
  LDAP-SYNTAX               directoryString.&id
  LDAP-NAME                 {"zimbraNewMailNotificationSubject"}
  LDAP-DESC                 "template used to construct the subject of an email notification message"
  ID                        id-at-zimbraNewMailNotificationSubject }

-- LDAP syntax length {256} rendered as DirectoryString{256}.
zimbraNotebookAccount ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraNotebookAccount"}
  LDAP-DESC                 "Deprecated since: 7.0.0. See bug 39647. Orig desc: Account for storing templates and providing space for public wiki"
  ID                        id-at-zimbraNotebookAccount }

zimbraNotebookFolderCacheSize ATTRIBUTE ::= {
  WITH SYNTAX               INTEGER
  EQUALITY MATCHING RULE    integerMatch
  SINGLE VALUE              TRUE
  LDAP-SYNTAX               integer.&id
  LDAP-NAME                 {"zimbraNotebookFolderCacheSize"}
  LDAP-DESC                 "Deprecated since: 6.0.0_BETA1. deprecated. Orig desc: The size of Wiki / Notebook folder cache on the server."
  ID                        id-at-zimbraNotebookFolderCacheSize }

zimbraNotebookMaxCachedTemplatesPerFolder ATTRIBUTE ::= {
  WITH SYNTAX               INTEGER
  EQUALITY MATCHING RULE    integerMatch
  SINGLE VALUE              TRUE
  LDAP-SYNTAX               integer.&id
  LDAP-NAME                 {"zimbraNotebookMaxCachedTemplatesPerFolder"}
  LDAP-DESC                 "Deprecated since: 6.0.0_BETA1. deprecated. Orig desc: The maximum number of cached templates in each Wiki / Notebook folder cache."
  ID                        id-at-zimbraNotebookMaxCachedTemplatesPerFolder }

zimbraNotebookMaxRevisions ATTRIBUTE ::= {
  WITH SYNTAX               INTEGER
  EQUALITY MATCHING RULE    integerMatch
  SINGLE VALUE              TRUE
  LDAP-SYNTAX               integer.&id
  LDAP-NAME                 {"zimbraNotebookMaxRevisions"}
  LDAP-DESC                 "maximum number of revisions to keep for wiki pages and documents. 0 means unlimited."
  ID                        id-at-zimbraNotebookMaxRevisions }

zimbraNotebookPageCacheSize ATTRIBUTE ::= {
  WITH SYNTAX               INTEGER
  EQUALITY MATCHING RULE    integerMatch
  SINGLE VALUE              TRUE
  LDAP-SYNTAX               integer.&id
  LDAP-NAME                 {"zimbraNotebookPageCacheSize"}
  LDAP-DESC                 "The size of composed Wiki / Notebook page cache on the server."
  ID                        id-at-zimbraNotebookPageCacheSize }

zimbraNotebookSanitizeHtml ATTRIBUTE ::= {
  WITH SYNTAX               BOOLEAN
  EQUALITY MATCHING RULE    booleanMatch
  SINGLE VALUE              TRUE
  LDAP-SYNTAX               boolean.&id
  LDAP-NAME                 {"zimbraNotebookSanitizeHtml"}
  LDAP-DESC                 "whether to strip off potentially harming HTML tags in Wiki and HTML Documents."
  ID                        id-at-zimbraNotebookSanitizeHtml }

-- LDAP syntax length {1024} rendered as DirectoryString{1024}.
zimbraNotes ATTRIBUTE ::= {
  WITH SYNTAX               DirectoryString{1024}
  EQUALITY MATCHING RULE    caseIgnoreMatch
  SUBSTRINGS MATCHING RULE  caseIgnoreSubstringsMatch
  SINGLE VALUE              TRUE
  LDAP-SYNTAX               directoryString.&id
  LDAP-NAME                 {"zimbraNotes"}
  LDAP-DESC                 "administrative notes"
  ID                        id-at-zimbraNotes }

-- LDAP syntax length {128} rendered as DirectoryString{128}.
zimbraNotifyBindAddress ATTRIBUTE ::= {
  WITH SYNTAX               DirectoryString{128}
  EQUALITY MATCHING RULE    caseIgnoreMatch
  SUBSTRINGS MATCHING RULE  caseIgnoreSubstringsMatch
  LDAP-SYNTAX               directoryString.&id
  LDAP-NAME                 {"zimbraNotifyBindAddress"}
  LDAP-DESC                 "Deprecated since: 4.0. was experimental and never part of any shipping feature. Orig desc: Network interface on which notification server should listen; if empty, binds to all interfaces."
  ID                        id-at-zimbraNotifyBindAddress }

zimbraNotifyBindPort ATTRIBUTE ::= {
  WITH SYNTAX               INTEGER
  EQUALITY MATCHING RULE    integerMatch
  SINGLE VALUE              TRUE
  LDAP-SYNTAX               integer.&id
  LDAP-NAME                 {"zimbraNotifyBindPort"}
  LDAP-DESC                 "Deprecated since: 4.0. was experimental and never part of any shipping feature. Orig desc: Port number on which notification server should listen."
  ID                        id-at-zimbraNotifyBindPort }

-- LDAP syntax length {128} rendered as DirectoryString{128}.
zimbraNotifySSLBindAddress ATTRIBUTE ::= {
  WITH SYNTAX               DirectoryString{128}
  EQUALITY MATCHING RULE    caseIgnoreMatch
  SUBSTRINGS MATCHING RULE  caseIgnoreSubstringsMatch
  LDAP-SYNTAX               directoryString.&id
  LDAP-NAME                 {"zimbraNotifySSLBindAddress"}
  LDAP-DESC                 "Deprecated since: 4.0. was experimental and never part of any shipping feature. Orig desc: Network interface on which SSL notification server should listen; if empty, binds to all interfaces"
  ID                        id-at-zimbraNotifySSLBindAddress }

zimbraNotifySSLBindPort ATTRIBUTE ::= {
  WITH SYNTAX               INTEGER
  EQUALITY MATCHING RULE    integerMatch
  SINGLE VALUE              TRUE
  LDAP-SYNTAX               integer.&id
  LDAP-NAME                 {"zimbraNotifySSLBindPort"}
  LDAP-DESC                 "Deprecated since: 4.0. was experimental and never part of any shipping feature. Orig desc: Port number on which notification server should listen."
  ID                        id-at-zimbraNotifySSLBindPort }

zimbraNotifySSLServerEnabled ATTRIBUTE ::= {
  WITH SYNTAX               BOOLEAN
  EQUALITY MATCHING RULE    booleanMatch
  SINGLE VALUE              TRUE
  LDAP-SYNTAX               boolean.&id
  LDAP-NAME                 {"zimbraNotifySSLServerEnabled"}
  LDAP-DESC                 "Deprecated since: 4.0. was experimental and never part of any shipping feature. Orig desc: Whether SSL notification server should be enabled."
  ID                        id-at-zimbraNotifySSLServerEnabled }

zimbraNotifyServerEnabled ATTRIBUTE ::= {
  WITH SYNTAX               BOOLEAN
  EQUALITY MATCHING RULE    booleanMatch
  SINGLE VALUE              TRUE
  LDAP-SYNTAX               boolean.&id
  LDAP-NAME                 {"zimbraNotifyServerEnabled"}
  LDAP-DESC                 "Deprecated since: 4.0. was experimental and never part of any shipping feature. Orig desc: Whether notification server should be enabled."
  ID                        id-at-zimbraNotifyServerEnabled }

-- LDAP syntax length {1024} rendered as DirectoryString{1024}.
zimbraOAuthConsumerCredentials ATTRIBUTE ::= {
  WITH SYNTAX               DirectoryString{1024}
  EQUALITY MATCHING RULE    caseIgnoreMatch
  SUBSTRINGS MATCHING RULE  caseIgnoreSubstringsMatch
  LDAP-SYNTAX               directoryString.&id
  LDAP-NAME                 {"zimbraOAuthConsumerCredentials"}
  LDAP-DESC                 "OAuth consumer ids and secrets. It is in the format of {consumer-id]:{secrets}"
  ID                        id-at-zimbraOAuthConsumerCredentials }

zimbraObjectHandlerClass ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"zimbraObjectHandlerClass"}
  LDAP-DESC                 "the handler class for the object type"
  ID                        id-at-zimbraObjectHandlerClass }

zimbraObjectHandlerConfig ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraObjectHandlerConfig"}
  LDAP-DESC                 "config for this type"
  ID                        id-at-zimbraObjectHandlerConfig }

zimbraObjectIndexingEnabled ATTRIBUTE ::= {
  WITH SYNTAX               BOOLEAN
  EQUALITY MATCHING RULE    booleanMatch
  SINGLE VALUE              TRUE
  LDAP-SYNTAX               boolean.&id
  LDAP-NAME                 {"zimbraObjectIndexingEnabled"}
  LDAP-DESC                 "whether or not indexing is enabled for this type"
  ID                        id-at-zimbraObjectIndexingEnabled }

zimbraObjectStoreMatched ATTRIBUTE ::= {
  WITH SYNTAX               BOOLEAN
  EQUALITY MATCHING RULE    booleanMatch
  SINGLE VALUE              TRUE
  LDAP-SYNTAX               boolean.&id
  LDAP-NAME                 {"zimbraObjectStoreMatched"}
  LDAP-DESC                 "whether or not store is matched for this type"
  ID                        id-at-zimbraObjectStoreMatched }

zimbraObjectType ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraObjectType"}
  LDAP-DESC                 "the object type"
  ID                        id-at-zimbraObjectType }

-- LDAP syntax length {256} rendered as DirectoryString{256}.
zimbraOpenidConsumerAllowedOPEndpointURL ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraOpenidConsumerAllowedOPEndpointURL"}
  LDAP-DESC                 "allowed OpenID Provider Endpoint URLs for authentication"
  ID                        id-at-zimbraOpenidConsumerAllowedOPEndpointURL }

zimbraOpenidConsumerStatelessModeEnabled ATTRIBUTE ::= {
  WITH SYNTAX               BOOLEAN
  EQUALITY MATCHING RULE    booleanMatch
  SINGLE VALUE              TRUE
  LDAP-SYNTAX               boolean.&id
  LDAP-NAME                 {"zimbraOpenidConsumerStatelessModeEnabled"}
  LDAP-DESC                 "whether stateless mode (not establishing an association with the OpenID Provider) in OpenID Consumer is enabled"
  ID                        id-at-zimbraOpenidConsumerStatelessModeEnabled }

-- LDAP syntax length {1024} rendered as DirectoryString{1024}.
zimbraPasswordAllowedChars ATTRIBUTE ::= {
  WITH SYNTAX               DirectoryString{1024}
  EQUALITY MATCHING RULE    caseExactMatch
  SUBSTRINGS MATCHING RULE  caseExactSubstringsMatch
  SINGLE VALUE              TRUE
  LDAP-SYNTAX               directoryString.&id
  LDAP-NAME                 {"zimbraPasswordAllowedChars"}
  LDAP-DESC                 "regex of allowed characters in password"
  ID                        id-at-zimbraPasswordAllowedChars }

-- LDAP syntax length {64} rendered as DirectoryString{64}.
zimbraPasswordAllowedPunctuationChars ATTRIBUTE ::= {
  WITH SYNTAX               DirectoryString{64}
  EQUALITY MATCHING RULE    caseExactMatch
  SUBSTRINGS MATCHING RULE  caseExactSubstringsMatch
  SINGLE VALUE              TRUE
  LDAP-SYNTAX               directoryString.&id
  LDAP-NAME                 {"zimbraPasswordAllowedPunctuationChars"}
  LDAP-DESC                 "regex of allowed punctuation characters in password"
  ID                        id-at-zimbraPasswordAllowedPunctuationChars }

-- LDAP syntax length {256} rendered as DirectoryString{256}.
zimbraPasswordChangeListener ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraPasswordChangeListener"}
  LDAP-DESC                 "registered change password listener name"
  ID                        id-at-zimbraPasswordChangeListener }

zimbraPasswordEnforceHistory ATTRIBUTE ::= {
  WITH SYNTAX               INTEGER
  EQUALITY MATCHING RULE    integerMatch
  SINGLE VALUE              TRUE
  LDAP-SYNTAX               integer.&id
  LDAP-NAME                 {"zimbraPasswordEnforceHistory"}
  LDAP-DESC                 "whether or not to enforce password history. Number of unique passwords a user must have before being allowed to re-use an old one. A value of 0 means no password history."
  ID                        id-at-zimbraPasswordEnforceHistory }

zimbraPasswordHistory ATTRIBUTE ::= {
  WITH SYNTAX               OCTET STRING (SIZE (1..128))
  EQUALITY MATCHING RULE    octetStringMatch
  LDAP-SYNTAX               octetString.&id
  LDAP-NAME                 {"zimbraPasswordHistory"}
  LDAP-DESC                 "historical password values"
  ID                        id-at-zimbraPasswordHistory }

zimbraPasswordLocked ATTRIBUTE ::= {
  WITH SYNTAX               BOOLEAN
  EQUALITY MATCHING RULE    booleanMatch
  SINGLE VALUE              TRUE
  LDAP-SYNTAX               boolean.&id
  LDAP-NAME                 {"zimbraPasswordLocked"}
  LDAP-DESC                 "user is unable to change password"
  ID                        id-at-zimbraPasswordLocked }

zimbraPasswordLockoutDuration ATTRIBUTE ::= {
  WITH SYNTAX               IA5String(SIZE (1..32))
  EQUALITY MATCHING RULE    caseIgnoreIA5Match
  SINGLE VALUE              TRUE
  LDAP-SYNTAX               ia5String.&id
  LDAP-NAME                 {"zimbraPasswordLockoutDuration"}
  LDAP-DESC                 "how long an account is locked out. Use 0 to lockout an account until admin resets it. Must be in valid duration format: {digits}{time-unit}. digits: 0-9, time-unit: [hmsd]|ms. h - hours, m - minutes, s - seconds, d - days, ms - milliseconds. If time unit is not specified, the default is s(seconds)."
  ID                        id-at-zimbraPasswordLockoutDuration }

zimbraPasswordLockoutEnabled ATTRIBUTE ::= {
  WITH SYNTAX               BOOLEAN
  EQUALITY MATCHING RULE    booleanMatch
  SINGLE VALUE              TRUE
  LDAP-SYNTAX               boolean.&id
  LDAP-NAME                 {"zimbraPasswordLockoutEnabled"}
  LDAP-DESC                 "whether or not account lockout is enabled."
  ID                        id-at-zimbraPasswordLockoutEnabled }

zimbraPasswordLockoutFailureLifetime ATTRIBUTE ::= {
  WITH SYNTAX               IA5String(SIZE (1..32))
  EQUALITY MATCHING RULE    caseIgnoreIA5Match
  SINGLE VALUE              TRUE
  LDAP-SYNTAX               ia5String.&id
  LDAP-NAME                 {"zimbraPasswordLockoutFailureLifetime"}
  LDAP-DESC                 "the duration after which old consecutive failed login attempts are purged from the list, even though no successful authentication has occurred. Must be in valid duration format: {digits}{time-unit}. digits: 0-9, time-unit: [hmsd]|ms. h - hours, m - minutes, s - seconds, d - days, ms - milliseconds. If time unit is not specified, the default is s(seconds)."
  ID                        id-at-zimbraPasswordLockoutFailureLifetime }

zimbraPasswordLockoutFailureTime ATTRIBUTE ::= {
  WITH SYNTAX               GeneralizedTime
  EQUALITY MATCHING RULE    generalizedTimeMatch
  ORDERING MATCHING RULE    generalizedTimeOrderingMatch
  LDAP-SYNTAX               generalizedTime.&id
  LDAP-NAME                 {"zimbraPasswordLockoutFailureTime"}
  LDAP-DESC                 "this attribute contains the timestamps of each of the consecutive authentication failures made on an account"
  ID                        id-at-zimbraPasswordLockoutFailureTime }

zimbraPasswordLockoutLockedTime ATTRIBUTE ::= {
  WITH SYNTAX               GeneralizedTime
  EQUALITY MATCHING RULE    generalizedTimeMatch
  ORDERING MATCHING RULE    generalizedTimeOrderingMatch
  SINGLE VALUE              TRUE
  LDAP-SYNTAX               generalizedTime.&id
  LDAP-NAME                 {"zimbraPasswordLockoutLockedTime"}
  LDAP-DESC                 "the time at which an account was locked"
  ID                        id-at-zimbraPasswordLockoutLockedTime }

zimbraPasswordLockoutMaxFailures ATTRIBUTE ::= {
  WITH SYNTAX               INTEGER
  EQUALITY MATCHING RULE    integerMatch
  SINGLE VALUE              TRUE
  LDAP-SYNTAX               integer.&id
  LDAP-NAME                 {"zimbraPasswordLockoutMaxFailures"}
  LDAP-DESC                 "number of consecutive failed login attempts until an account is locked out"
  ID                        id-at-zimbraPasswordLockoutMaxFailures }

zimbraPasswordMaxAge ATTRIBUTE ::= {
  WITH SYNTAX               INTEGER
  EQUALITY MATCHING RULE    integerMatch
  SINGLE VALUE              TRUE
  LDAP-SYNTAX               integer.&id
  LDAP-NAME                 {"zimbraPasswordMaxAge"}
  LDAP-DESC                 "maximum days between password changes"
  ID                        id-at-zimbraPasswordMaxAge }

zimbraPasswordMaxLength ATTRIBUTE ::= {
  WITH SYNTAX               INTEGER
  EQUALITY MATCHING RULE    integerMatch
  SINGLE VALUE              TRUE
  LDAP-SYNTAX               integer.&id
  LDAP-NAME                 {"zimbraPasswordMaxLength"}
  LDAP-DESC                 "max length of a password"
  ID                        id-at-zimbraPasswordMaxLength }

zimbraPasswordMinAge ATTRIBUTE ::= {
  WITH SYNTAX               INTEGER
  EQUALITY MATCHING RULE    integerMatch
  SINGLE VALUE              TRUE
  LDAP-SYNTAX               integer.&id
  LDAP-NAME                 {"zimbraPasswordMinAge"}
  LDAP-DESC                 "minimum days between password changes"
  ID                        id-at-zimbraPasswordMinAge }

zimbraPasswordMinAlphaChars ATTRIBUTE ::= {
  WITH SYNTAX               INTEGER
  EQUALITY MATCHING RULE    integerMatch
  SINGLE VALUE              TRUE
  LDAP-SYNTAX               integer.&id
  LDAP-NAME                 {"zimbraPasswordMinAlphaChars"}
  LDAP-DESC                 "minimum number of alphabet characters required in a password"
  ID                        id-at-zimbraPasswordMinAlphaChars }

zimbraPasswordMinDigitsOrPuncs ATTRIBUTE ::= {
  WITH SYNTAX               INTEGER
  EQUALITY MATCHING RULE    integerMatch
  SINGLE VALUE              TRUE
  LDAP-SYNTAX               integer.&id
  LDAP-NAME                 {"zimbraPasswordMinDigitsOrPuncs"}
  LDAP-DESC                 "minimum number of numeric or ascii punctuation characters required in a password"
  ID                        id-at-zimbraPasswordMinDigitsOrPuncs }

zimbraPasswordMinLength ATTRIBUTE ::= {
  WITH SYNTAX               INTEGER
  EQUALITY MATCHING RULE    integerMatch
  SINGLE VALUE              TRUE
  LDAP-SYNTAX               integer.&id
  LDAP-NAME                 {"zimbraPasswordMinLength"}
  LDAP-DESC                 "minimum length of a password"
  ID                        id-at-zimbraPasswordMinLength }

zimbraPasswordMinLowerCaseChars ATTRIBUTE ::= {
  WITH SYNTAX               INTEGER
  EQUALITY MATCHING RULE    integerMatch
  SINGLE VALUE              TRUE
  LDAP-SYNTAX               integer.&id
  LDAP-NAME                 {"zimbraPasswordMinLowerCaseChars"}
  LDAP-DESC                 "minimum number of lower case characters required in a password"
  ID                        id-at-zimbraPasswordMinLowerCaseChars }

zimbraPasswordMinNumericChars ATTRIBUTE ::= {
  WITH SYNTAX               INTEGER
  EQUALITY MATCHING RULE    integerMatch
  SINGLE VALUE              TRUE
  LDAP-SYNTAX               integer.&id
  LDAP-NAME                 {"zimbraPasswordMinNumericChars"}
  LDAP-DESC                 "minimum number of numeric characters required in a password"
  ID                        id-at-zimbraPasswordMinNumericChars }

zimbraPasswordMinPunctuationChars ATTRIBUTE ::= {
  WITH SYNTAX               INTEGER
  EQUALITY MATCHING RULE    integerMatch
  SINGLE VALUE              TRUE
  LDAP-SYNTAX               integer.&id
  LDAP-NAME                 {"zimbraPasswordMinPunctuationChars"}
  LDAP-DESC                 "minimum number of ascii punctuation characters required in a password"
  ID                        id-at-zimbraPasswordMinPunctuationChars }

zimbraPasswordMinUpperCaseChars ATTRIBUTE ::= {
  WITH SYNTAX               INTEGER
  EQUALITY MATCHING RULE    integerMatch
  SINGLE VALUE              TRUE
  LDAP-SYNTAX               integer.&id
  LDAP-NAME                 {"zimbraPasswordMinUpperCaseChars"}
  LDAP-DESC                 "minimum number of upper case characters required in a password"
  ID                        id-at-zimbraPasswordMinUpperCaseChars }

zimbraPasswordModifiedTime ATTRIBUTE ::= {
  WITH SYNTAX               GeneralizedTime
  EQUALITY MATCHING RULE    generalizedTimeMatch
  ORDERING MATCHING RULE    generalizedTimeOrderingMatch
  SINGLE VALUE              TRUE
  LDAP-SYNTAX               generalizedTime.&id
  LDAP-NAME                 {"zimbraPasswordModifiedTime"}
  LDAP-DESC                 "time password was last changed"
  ID                        id-at-zimbraPasswordModifiedTime }

zimbraPasswordMustChange ATTRIBUTE ::= {
  WITH SYNTAX               BOOLEAN
  EQUALITY MATCHING RULE    booleanMatch
  SINGLE VALUE              TRUE
  LDAP-SYNTAX               boolean.&id
  LDAP-NAME                 {"zimbraPasswordMustChange"}
  LDAP-DESC                 "must change password on auth"
  ID                        id-at-zimbraPasswordMustChange }

-- LDAP syntax length {256} rendered as DirectoryString{256}.
zimbraPhoneticCompany ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraPhoneticCompany"}
  LDAP-DESC                 "phonetic company name"
  ID                        id-at-zimbraPhoneticCompany }

-- LDAP syntax length {256} rendered as DirectoryString{256}.
zimbraPhoneticFirstName ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraPhoneticFirstName"}
  LDAP-DESC                 "phonetic first name"
  ID                        id-at-zimbraPhoneticFirstName }

-- LDAP syntax length {256} rendered as DirectoryString{256}.
zimbraPhoneticLastName ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraPhoneticLastName"}
  LDAP-DESC                 "phonetic last name"
  ID                        id-at-zimbraPhoneticLastName }

-- LDAP syntax length {128} rendered as DirectoryString{128}.
zimbraPop3AdvertisedName ATTRIBUTE ::= {
  WITH SYNTAX               DirectoryString{128}
  EQUALITY MATCHING RULE    caseIgnoreMatch
  SUBSTRINGS MATCHING RULE  caseIgnoreSubstringsMatch
  SINGLE VALUE              TRUE
  LDAP-SYNTAX               directoryString.&id
  LDAP-NAME                 {"zimbraPop3AdvertisedName"}
  LDAP-DESC                 "name to use in greeting and sign-off; if empty, uses hostname"
  ID                        id-at-zimbraPop3AdvertisedName }

-- LDAP syntax length {128} rendered as DirectoryString{128}.
zimbraPop3BindAddress ATTRIBUTE ::= {
  WITH SYNTAX               DirectoryString{128}
  EQUALITY MATCHING RULE    caseIgnoreMatch
  SUBSTRINGS MATCHING RULE  caseIgnoreSubstringsMatch
  LDAP-SYNTAX               directoryString.&id
  LDAP-NAME                 {"zimbraPop3BindAddress"}
  LDAP-DESC                 "interface address on which POP3 server should listen; if empty, binds to all interfaces"
  ID                        id-at-zimbraPop3BindAddress }

zimbraPop3BindOnStartup ATTRIBUTE ::= {
  WITH SYNTAX               BOOLEAN
  EQUALITY MATCHING RULE    booleanMatch
  SINGLE VALUE              TRUE
  LDAP-SYNTAX               boolean.&id
  LDAP-NAME                 {"zimbraPop3BindOnStartup"}
  LDAP-DESC                 "Whether to bind to port on startup irrespective of whether the server is enabled. Useful when port to bind is privileged and must be bound early."
  ID                        id-at-zimbraPop3BindOnStartup }

zimbraPop3BindPort ATTRIBUTE ::= {
  WITH SYNTAX               INTEGER
  EQUALITY MATCHING RULE    integerMatch
  SINGLE VALUE              TRUE
  LDAP-SYNTAX               integer.&id
  LDAP-NAME                 {"zimbraPop3BindPort"}
  LDAP-DESC                 "port number on which POP3 server should listen"
  ID                        id-at-zimbraPop3BindPort }

zimbraPop3CleartextLoginEnabled ATTRIBUTE ::= {
  WITH SYNTAX               BOOLEAN
  EQUALITY MATCHING RULE    booleanMatch
  SINGLE VALUE              TRUE
  LDAP-SYNTAX               boolean.&id
  LDAP-NAME                 {"zimbraPop3CleartextLoginEnabled"}
  LDAP-DESC                 "whether or not to allow cleartext logins over a non SSL/TLS connection"
  ID                        id-at-zimbraPop3CleartextLoginEnabled }

zimbraPop3Enabled ATTRIBUTE ::= {
  WITH SYNTAX               BOOLEAN
  EQUALITY MATCHING RULE    booleanMatch
  SINGLE VALUE              TRUE
  LDAP-SYNTAX               boolean.&id
  LDAP-NAME                 {"zimbraPop3Enabled"}
  LDAP-DESC                 "whether POP3 is enabled for an account"
  ID                        id-at-zimbraPop3Enabled }

zimbraPop3ExposeVersionOnBanner ATTRIBUTE ::= {
  WITH SYNTAX               BOOLEAN
  EQUALITY MATCHING RULE    booleanMatch
  SINGLE VALUE              TRUE
  LDAP-SYNTAX               boolean.&id
  LDAP-NAME                 {"zimbraPop3ExposeVersionOnBanner"}
  LDAP-DESC                 "Whether to expose version on POP3 banner"
  ID                        id-at-zimbraPop3ExposeVersionOnBanner }

zimbraPop3MaxConnections ATTRIBUTE ::= {
  WITH SYNTAX               INTEGER
  EQUALITY MATCHING RULE    integerMatch
  SINGLE VALUE              TRUE
  LDAP-SYNTAX               integer.&id
  LDAP-NAME                 {"zimbraPop3MaxConnections"}
  LDAP-DESC                 "Maximum number of concurrent POP3 connections allowed. New connections exceeding this limit are rejected."
  ID                        id-at-zimbraPop3MaxConnections }

zimbraPop3NumThreads ATTRIBUTE ::= {
  WITH SYNTAX               INTEGER
  EQUALITY MATCHING RULE    integerMatch
  SINGLE VALUE              TRUE
  LDAP-SYNTAX               integer.&id
  LDAP-NAME                 {"zimbraPop3NumThreads"}
  LDAP-DESC                 "number of handler threads"
  ID                        id-at-zimbraPop3NumThreads }

zimbraPop3ProxyBindPort ATTRIBUTE ::= {
  WITH SYNTAX               INTEGER
  EQUALITY MATCHING RULE    integerMatch
  SINGLE VALUE              TRUE
  LDAP-SYNTAX               integer.&id
  LDAP-NAME                 {"zimbraPop3ProxyBindPort"}
  LDAP-DESC                 "port number on which POP3 proxy server should listen"
  ID                        id-at-zimbraPop3ProxyBindPort }

-- LDAP syntax length {128} rendered as DirectoryString{128}.
zimbraPop3SSLBindAddress ATTRIBUTE ::= {
  WITH SYNTAX               DirectoryString{128}
  EQUALITY MATCHING RULE    caseIgnoreMatch
  SUBSTRINGS MATCHING RULE  caseIgnoreSubstringsMatch
  LDAP-SYNTAX               directoryString.&id
  LDAP-NAME                 {"zimbraPop3SSLBindAddress"}
  LDAP-DESC                 "interface address on which POP3 server should listen; if empty, binds to all interfaces"
  ID                        id-at-zimbraPop3SSLBindAddress }

zimbraPop3SSLBindOnStartup ATTRIBUTE ::= {
  WITH SYNTAX               BOOLEAN
  EQUALITY MATCHING RULE    booleanMatch
  SINGLE VALUE              TRUE
  LDAP-SYNTAX               boolean.&id
  LDAP-NAME                 {"zimbraPop3SSLBindOnStartup"}
  LDAP-DESC                 "Whether to bind to port on startup irrespective of whether the server is enabled. Useful when port to bind is privileged and must be bound early."
  ID                        id-at-zimbraPop3SSLBindOnStartup }

zimbraPop3SSLBindPort ATTRIBUTE ::= {
  WITH SYNTAX               INTEGER
  EQUALITY MATCHING RULE    integerMatch
  SINGLE VALUE              TRUE
  LDAP-SYNTAX               integer.&id
  LDAP-NAME                 {"zimbraPop3SSLBindPort"}
  LDAP-DESC                 "port number on which POP3 server should listen"
  ID                        id-at-zimbraPop3SSLBindPort }

zimbraPop3SSLProxyBindPort ATTRIBUTE ::= {
  WITH SYNTAX               INTEGER
  EQUALITY MATCHING RULE    integerMatch
  SINGLE VALUE              TRUE
  LDAP-SYNTAX               integer.&id
  LDAP-NAME                 {"zimbraPop3SSLProxyBindPort"}
  LDAP-DESC                 "port number on which POP3S proxy server should listen"
  ID                        id-at-zimbraPop3SSLProxyBindPort }

zimbraPop3SSLServerEnabled ATTRIBUTE ::= {
  WITH SYNTAX               BOOLEAN
  EQUALITY MATCHING RULE    booleanMatch
  SINGLE VALUE              TRUE
  LDAP-SYNTAX               boolean.&id
  LDAP-NAME                 {"zimbraPop3SSLServerEnabled"}
  LDAP-DESC                 "whether POP3 SSL server is enabled for a server"
  ID                        id-at-zimbraPop3SSLServerEnabled }

zimbraPop3SaslGssapiEnabled ATTRIBUTE ::= {
  WITH SYNTAX               BOOLEAN
  EQUALITY MATCHING RULE    booleanMatch
  SINGLE VALUE              TRUE
  LDAP-SYNTAX               boolean.&id
  LDAP-NAME                 {"zimbraPop3SaslGssapiEnabled"}
  LDAP-DESC                 "whether POP3 SASL GSSAPI is enabled for a given server"
  ID                        id-at-zimbraPop3SaslGssapiEnabled }

zimbraPop3ServerEnabled ATTRIBUTE ::= {
  WITH SYNTAX               BOOLEAN
  EQUALITY MATCHING RULE    booleanMatch
  SINGLE VALUE              TRUE
  LDAP-SYNTAX               boolean.&id
  LDAP-NAME                 {"zimbraPop3ServerEnabled"}
  LDAP-DESC                 "whether POP3 is enabled for a server"
  ID                        id-at-zimbraPop3ServerEnabled }

zimbraPop3ShutdownGraceSeconds ATTRIBUTE ::= {
  WITH SYNTAX               INTEGER
  EQUALITY MATCHING RULE    integerMatch
  SINGLE VALUE              TRUE
  LDAP-SYNTAX               integer.&id
  LDAP-NAME                 {"zimbraPop3ShutdownGraceSeconds"}
  LDAP-DESC                 "number of seconds to wait before forcing POP3 server shutdown"
  ID                        id-at-zimbraPop3ShutdownGraceSeconds }

-- LDAP syntax length {256} rendered as DirectoryString{256}.
zimbraPortalName ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraPortalName"}
  LDAP-DESC                 "portal name"
  ID                        id-at-zimbraPortalName }

zimbraPreAuthKey ATTRIBUTE ::= {
  WITH SYNTAX               OCTET STRING (SIZE (1..128))
  EQUALITY MATCHING RULE    octetStringMatch
  SINGLE VALUE              TRUE
  LDAP-SYNTAX               octetString.&id
  LDAP-NAME                 {"zimbraPreAuthKey"}
  LDAP-DESC                 "preauth secret key"
  ID                        id-at-zimbraPreAuthKey }

zimbraPrefAccountTreeOpen ATTRIBUTE ::= {
  WITH SYNTAX               BOOLEAN
  EQUALITY MATCHING RULE    booleanMatch
  SINGLE VALUE              TRUE
  LDAP-SYNTAX               boolean.&id
  LDAP-NAME                 {"zimbraPrefAccountTreeOpen"}
  LDAP-DESC                 "whether or not account tree is expanded"
  ID                        id-at-zimbraPrefAccountTreeOpen }

zimbraPrefAdminConsoleWarnOnExit ATTRIBUTE ::= {
  WITH SYNTAX               BOOLEAN
  EQUALITY MATCHING RULE    booleanMatch
  SINGLE VALUE              TRUE
  LDAP-SYNTAX               boolean.&id
  LDAP-NAME                 {"zimbraPrefAdminConsoleWarnOnExit"}
  LDAP-DESC                 "whether to display a warning when users try to navigate away from the admin console"
  ID                        id-at-zimbraPrefAdminConsoleWarnOnExit }

zimbraPrefAdvancedClientEnforceMinDisplay ATTRIBUTE ::= {
  WITH SYNTAX               BOOLEAN
  EQUALITY MATCHING RULE    booleanMatch
  SINGLE VALUE              TRUE
  LDAP-SYNTAX               boolean.&id
  LDAP-NAME                 {"zimbraPrefAdvancedClientEnforceMinDisplay"}
  LDAP-DESC                 "After login, whether the advanced client should enforce minimum display resolution"
  ID                        id-at-zimbraPrefAdvancedClientEnforceMinDisplay }

zimbraPrefAllowAddressForDelegatedSender ATTRIBUTE ::= {
  WITH SYNTAX               IA5String(SIZE (1..256))
  EQUALITY MATCHING RULE    caseIgnoreIA5Match
  SUBSTRINGS MATCHING RULE  caseIgnoreSubstringsMatch
  LDAP-SYNTAX               ia5String.&id
  LDAP-NAME                 {"zimbraPrefAllowAddressForDelegatedSender"}
  LDAP-DESC                 "Addresses of the account that can be used by allowed delegated senders as From and Sender address."
  ID                        id-at-zimbraPrefAllowAddressForDelegatedSender }

zimbraPrefAppleIcalDelegationEnabled ATTRIBUTE ::= {
  WITH SYNTAX               BOOLEAN
  EQUALITY MATCHING RULE    booleanMatch
  SINGLE VALUE              TRUE
  LDAP-SYNTAX               boolean.&id
  LDAP-NAME                 {"zimbraPrefAppleIcalDelegationEnabled"}
  LDAP-DESC                 "Use the iCal style delegation model for shared calendars for CalDAV interface when set to TRUE."
  ID                        id-at-zimbraPrefAppleIcalDelegationEnabled }

zimbraPrefAutoAddAddressEnabled ATTRIBUTE ::= {
  WITH SYNTAX               BOOLEAN
  EQUALITY MATCHING RULE    booleanMatch
  SINGLE VALUE              TRUE
  LDAP-SYNTAX               boolean.&id
  LDAP-NAME                 {"zimbraPrefAutoAddAddressEnabled"}
  LDAP-DESC                 "whether or not new address in outgoing email are auto added to address book"
  ID                        id-at-zimbraPrefAutoAddAddressEnabled }

zimbraPrefAutoCompleteQuickCompletionOnComma ATTRIBUTE ::= {
  WITH SYNTAX               BOOLEAN
  EQUALITY MATCHING RULE    booleanMatch
  SINGLE VALUE              TRUE
  LDAP-SYNTAX               boolean.&id
  LDAP-NAME                 {"zimbraPrefAutoCompleteQuickCompletionOnComma"}
  LDAP-DESC                 "whether to end auto-complete on comma"
  ID                        id-at-zimbraPrefAutoCompleteQuickCompletionOnComma }

zimbraPrefAutoSaveDraftInterval ATTRIBUTE ::= {
  WITH SYNTAX               IA5String(SIZE (1..32))
  EQUALITY MATCHING RULE    caseIgnoreIA5Match
  SINGLE VALUE              TRUE
  LDAP-SYNTAX               ia5String.&id
  LDAP-NAME                 {"zimbraPrefAutoSaveDraftInterval"}
  LDAP-DESC                 "time to wait before auto saving a draft. Must be in valid duration format: {digits}{time-unit}. digits: 0-9, time-unit: [hmsd]|ms. h - hours, m - minutes, s - seconds, d - days, ms - milliseconds. If time unit is not specified, the default is s(seconds)."
  ID                        id-at-zimbraPrefAutoSaveDraftInterval }

zimbraPrefAutocompleteAddressBubblesEnabled ATTRIBUTE ::= {
  WITH SYNTAX               BOOLEAN
  EQUALITY MATCHING RULE    booleanMatch
  SINGLE VALUE              TRUE
  LDAP-SYNTAX               boolean.&id
  LDAP-NAME                 {"zimbraPrefAutocompleteAddressBubblesEnabled"}
  LDAP-DESC                 "Deprecated since: 8.5.0. address bubbles always enabled since 8.5.0. Orig desc: whether actionable address objects result from autocomplete is enabled"
  ID                        id-at-zimbraPrefAutocompleteAddressBubblesEnabled }

-- LDAP syntax length {2048} rendered as DirectoryString{2048}.
zimbraPrefBccAddress ATTRIBUTE ::= {
  WITH SYNTAX               DirectoryString{2048}
  EQUALITY MATCHING RULE    caseIgnoreMatch
  SUBSTRINGS MATCHING RULE  caseIgnoreSubstringsMatch
  SINGLE VALUE              TRUE
  LDAP-SYNTAX               directoryString.&id
  LDAP-NAME                 {"zimbraPrefBccAddress"}
  LDAP-DESC                 "address that we will bcc when using sending mail with this identity (deprecatedSince 5.0 in identity)"
  ID                        id-at-zimbraPrefBccAddress }

-- LDAP syntax length {32} rendered as DirectoryString{32}.
zimbraPrefBriefcaseReadingPaneLocation ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraPrefBriefcaseReadingPaneLocation"}
  LDAP-DESC                 "where the reading pane is displayed for briefcase"
  ID                        id-at-zimbraPrefBriefcaseReadingPaneLocation }

-- LDAP syntax length {256} rendered as DirectoryString{256}.
zimbraPrefCalendarAcceptSignatureId ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraPrefCalendarAcceptSignatureId"}
  LDAP-DESC                 "calendar manual accept reply signature for account/identity/dataSource"
  ID                        id-at-zimbraPrefCalendarAcceptSignatureId }

zimbraPrefCalendarAllowCancelEmailToSelf ATTRIBUTE ::= {
  WITH SYNTAX               BOOLEAN
  EQUALITY MATCHING RULE    booleanMatch
  SINGLE VALUE              TRUE
  LDAP-SYNTAX               boolean.&id
  LDAP-NAME                 {"zimbraPrefCalendarAllowCancelEmailToSelf"}
  LDAP-DESC                 "whether to allow a cancel email sent to organizer of appointment"
  ID                        id-at-zimbraPrefCalendarAllowCancelEmailToSelf }

zimbraPrefCalendarAllowForwardedInvite ATTRIBUTE ::= {
  WITH SYNTAX               BOOLEAN
  EQUALITY MATCHING RULE    booleanMatch
  SINGLE VALUE              TRUE
  LDAP-SYNTAX               boolean.&id
  LDAP-NAME                 {"zimbraPrefCalendarAllowForwardedInvite"}
  LDAP-DESC                 "whether calendar invite part in a forwarded email is auto-added to calendar"
  ID                        id-at-zimbraPrefCalendarAllowForwardedInvite }

zimbraPrefCalendarAllowPublishMethodInvite ATTRIBUTE ::= {
  WITH SYNTAX               BOOLEAN
  EQUALITY MATCHING RULE    booleanMatch
  SINGLE VALUE              TRUE
  LDAP-SYNTAX               boolean.&id
  LDAP-NAME                 {"zimbraPrefCalendarAllowPublishMethodInvite"}
  LDAP-DESC                 "whether calendar invite part with PUBLISH method is auto-added to calendar"
  ID                        id-at-zimbraPrefCalendarAllowPublishMethodInvite }

-- LDAP syntax length {32} rendered as DirectoryString{32}.
zimbraPrefCalendarAllowedTargetsForInviteDeniedAutoReply ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraPrefCalendarAllowedTargetsForInviteDeniedAutoReply"}
  LDAP-DESC                 "Allowed recipients if ""zimbraPrefCalendarSendInviteDeniedAutoReply"" is TRUE: internal - Only send ""invite denied"" auto-response if the sender of the original invite is an internal user. sameDomain - Only send ""invite denied"" auto-response if the sender of the original invite is in the same domain as the invitee. all - No restrictions on who to send ""invite denied"" auto-responses to."
  ID                        id-at-zimbraPrefCalendarAllowedTargetsForInviteDeniedAutoReply }

zimbraPrefCalendarAlwaysShowMiniCal ATTRIBUTE ::= {
  WITH SYNTAX               BOOLEAN
  EQUALITY MATCHING RULE    booleanMatch
  SINGLE VALUE              TRUE
  LDAP-SYNTAX               boolean.&id
  LDAP-NAME                 {"zimbraPrefCalendarAlwaysShowMiniCal"}
  LDAP-DESC                 "always show the mini calendar"
  ID                        id-at-zimbraPrefCalendarAlwaysShowMiniCal }

zimbraPrefCalendarApptAllowAtendeeEdit ATTRIBUTE ::= {
  WITH SYNTAX               BOOLEAN
  EQUALITY MATCHING RULE    booleanMatch
  SINGLE VALUE              TRUE
  LDAP-SYNTAX               boolean.&id
  LDAP-NAME                 {"zimbraPrefCalendarApptAllowAtendeeEdit"}
  LDAP-DESC                 "Whether to allow attendees to make local edits to appointments. The change is only on the attendees copy of the message and changes from the organizer will overwrite the local changes."
  ID                        id-at-zimbraPrefCalendarApptAllowAtendeeEdit }

zimbraPrefCalendarApptReminderWarningTime ATTRIBUTE ::= {
  WITH SYNTAX               INTEGER
  EQUALITY MATCHING RULE    integerMatch
  SINGLE VALUE              TRUE
  LDAP-SYNTAX               integer.&id
  LDAP-NAME                 {"zimbraPrefCalendarApptReminderWarningTime"}
  LDAP-DESC                 "number of minutes (0 = never) before appt to show reminder dialog"
  ID                        id-at-zimbraPrefCalendarApptReminderWarningTime }

-- LDAP syntax length {32} rendered as DirectoryString{32}.
zimbraPrefCalendarApptVisibility ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraPrefCalendarApptVisibility"}
  LDAP-DESC                 "default visibility of the appointment when starting a new appointment in the UI"
  ID                        id-at-zimbraPrefCalendarApptVisibility }

-- LDAP syntax length {256} rendered as DirectoryString{256}.
zimbraPrefCalendarAutoAcceptSignatureId ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraPrefCalendarAutoAcceptSignatureId"}
  LDAP-DESC                 "calendar auto accept reply signature for account/identity/dataSource"
  ID                        id-at-zimbraPrefCalendarAutoAcceptSignatureId }

zimbraPrefCalendarAutoAddInvites ATTRIBUTE ::= {
  WITH SYNTAX               BOOLEAN
  EQUALITY MATCHING RULE    booleanMatch
  SINGLE VALUE              TRUE
  LDAP-SYNTAX               boolean.&id
  LDAP-NAME                 {"zimbraPrefCalendarAutoAddInvites"}
  LDAP-DESC                 "automatically add appointments when invited"
  ID                        id-at-zimbraPrefCalendarAutoAddInvites }

-- LDAP syntax length {256} rendered as DirectoryString{256}.
zimbraPrefCalendarAutoDeclineSignatureId ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraPrefCalendarAutoDeclineSignatureId"}
  LDAP-DESC                 "calendar auto decline reply signature id for account/identity/dataSource"
  ID                        id-at-zimbraPrefCalendarAutoDeclineSignatureId }

-- LDAP syntax length {256} rendered as DirectoryString{256}.
zimbraPrefCalendarAutoDenySignatureId ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraPrefCalendarAutoDenySignatureId"}
  LDAP-DESC                 "calendar auto deny reply signature id for account/identity/dataSource"
  ID                        id-at-zimbraPrefCalendarAutoDenySignatureId }

zimbraPrefCalendarDayHourEnd ATTRIBUTE ::= {
  WITH SYNTAX               INTEGER
  EQUALITY MATCHING RULE    integerMatch
  SINGLE VALUE              TRUE
  LDAP-SYNTAX               integer.&id
  LDAP-NAME                 {"zimbraPrefCalendarDayHourEnd"}
  LDAP-DESC                 "hour of day that the day view should end at, non-inclusive (16=4pm, 24 = midnight, etc)"
  ID                        id-at-zimbraPrefCalendarDayHourEnd }

zimbraPrefCalendarDayHourStart ATTRIBUTE ::= {
  WITH SYNTAX               INTEGER
  EQUALITY MATCHING RULE    integerMatch
  SINGLE VALUE              TRUE
  LDAP-SYNTAX               integer.&id
  LDAP-NAME                 {"zimbraPrefCalendarDayHourStart"}
  LDAP-DESC                 "hour of day that the day view should start at (1=1 AM, 8=8 AM, etc)"
  ID                        id-at-zimbraPrefCalendarDayHourStart }

-- LDAP syntax length {256} rendered as DirectoryString{256}.
zimbraPrefCalendarDeclineSignatureId ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraPrefCalendarDeclineSignatureId"}
  LDAP-DESC                 "calendar manual decline reply signature id for account/identity/dataSource"
  ID                        id-at-zimbraPrefCalendarDeclineSignatureId }

zimbraPrefCalendarDefaultApptDuration ATTRIBUTE ::= {
  WITH SYNTAX               IA5String(SIZE (1..32))
  EQUALITY MATCHING RULE    caseIgnoreIA5Match
  SINGLE VALUE              TRUE
  LDAP-SYNTAX               ia5String.&id
  LDAP-NAME                 {"zimbraPrefCalendarDefaultApptDuration"}
  LDAP-DESC                 "default appointment duration. Must be in valid duration format: {digits}{time-unit}. digits: 0-9, time-unit: [hmsd]|ms. h - hours, m - minutes, s - seconds, d - days, ms - milliseconds. If time unit is not specified, the default is s(seconds)."
  ID                        id-at-zimbraPrefCalendarDefaultApptDuration }

zimbraPrefCalendarFirstDayOfWeek ATTRIBUTE ::= {
  WITH SYNTAX               INTEGER
  EQUALITY MATCHING RULE    integerMatch
  SINGLE VALUE              TRUE
  LDAP-SYNTAX               integer.&id
  LDAP-NAME                 {"zimbraPrefCalendarFirstDayOfWeek"}
  LDAP-DESC                 "first day of week to show in calendar (0=sunday, 6=saturday)"
  ID                        id-at-zimbraPrefCalendarFirstDayOfWeek }

zimbraPrefCalendarForwardInvitesTo ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraPrefCalendarForwardInvitesTo"}
  LDAP-DESC                 "Forward a copy of calendar invites received to these users."
  ID                        id-at-zimbraPrefCalendarForwardInvitesTo }

zimbraPrefCalendarInitialCheckedCalendars ATTRIBUTE ::= {
  WITH SYNTAX               IA5String(SIZE (1..512))
  EQUALITY MATCHING RULE    caseIgnoreIA5Match
  SUBSTRINGS MATCHING RULE  caseIgnoreSubstringsMatch
  SINGLE VALUE              TRUE
  LDAP-SYNTAX               ia5String.&id
  LDAP-NAME                 {"zimbraPrefCalendarInitialCheckedCalendars"}
  LDAP-DESC                 "comma-sep list of calendars that are initially checked"
  ID                        id-at-zimbraPrefCalendarInitialCheckedCalendars }

-- LDAP syntax length {32} rendered as DirectoryString{32}.
zimbraPrefCalendarInitialView ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraPrefCalendarInitialView"}
  LDAP-DESC                 "initial calendar view to use"
  ID                        id-at-zimbraPrefCalendarInitialView }

zimbraPrefCalendarNotifyDelegatedChanges ATTRIBUTE ::= {
  WITH SYNTAX               BOOLEAN
  EQUALITY MATCHING RULE    booleanMatch
  SINGLE VALUE              TRUE
  LDAP-SYNTAX               boolean.&id
  LDAP-NAME                 {"zimbraPrefCalendarNotifyDelegatedChanges"}
  LDAP-DESC                 "If set to true, user is notified by email of changes made to her calendar by others via delegated calendar access."
  ID                        id-at-zimbraPrefCalendarNotifyDelegatedChanges }

-- LDAP syntax length {128} rendered as DirectoryString{128}.
zimbraPrefCalendarReminderDeviceInfo ATTRIBUTE ::= {
  WITH SYNTAX               DirectoryString{128}
  EQUALITY MATCHING RULE    caseIgnoreMatch
  SUBSTRINGS MATCHING RULE  caseIgnoreSubstringsMatch
  SINGLE VALUE              TRUE
  LDAP-SYNTAX               directoryString.&id
  LDAP-NAME                 {"zimbraPrefCalendarReminderDeviceInfo"}
  LDAP-DESC                 "device information entered by the user for receiving reminders for appointments and tasks"
  ID                        id-at-zimbraPrefCalendarReminderDeviceInfo }

zimbraPrefCalendarReminderDuration1 ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraPrefCalendarReminderDuration1"}
  LDAP-DESC                 "Deprecated since: 6.0.0_BETA1. was added for Yahoo calendar, no longer used. Orig desc: When to send the first reminder for an event."
  ID                        id-at-zimbraPrefCalendarReminderDuration1 }

zimbraPrefCalendarReminderDuration2 ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraPrefCalendarReminderDuration2"}
  LDAP-DESC                 "Deprecated since: 6.0.0_BETA1. was added for Yahoo calendar, no longer used. Orig desc: When to send the second reminder for an event."
  ID                        id-at-zimbraPrefCalendarReminderDuration2 }

zimbraPrefCalendarReminderEmail ATTRIBUTE ::= {
  WITH SYNTAX               IA5String(SIZE (1..256))
  EQUALITY MATCHING RULE    caseIgnoreIA5Match
  SUBSTRINGS MATCHING RULE  caseIgnoreSubstringsMatch
  SINGLE VALUE              TRUE
  LDAP-SYNTAX               ia5String.&id
  LDAP-NAME                 {"zimbraPrefCalendarReminderEmail"}
  LDAP-DESC                 "RFC822 email address for receiving reminders for appointments and tasks"
  ID                        id-at-zimbraPrefCalendarReminderEmail }

zimbraPrefCalendarReminderFlashTitle ATTRIBUTE ::= {
  WITH SYNTAX               BOOLEAN
  EQUALITY MATCHING RULE    booleanMatch
  SINGLE VALUE              TRUE
  LDAP-SYNTAX               boolean.&id
  LDAP-NAME                 {"zimbraPrefCalendarReminderFlashTitle"}
  LDAP-DESC                 "Flash title when on appointment reminder notification"
  ID                        id-at-zimbraPrefCalendarReminderFlashTitle }

zimbraPrefCalendarReminderMobile ATTRIBUTE ::= {
  WITH SYNTAX               BOOLEAN
  EQUALITY MATCHING RULE    booleanMatch
  SINGLE VALUE              TRUE
  LDAP-SYNTAX               boolean.&id
  LDAP-NAME                 {"zimbraPrefCalendarReminderMobile"}
  LDAP-DESC                 "Deprecated since: 6.0.0_BETA1. was added for Yahoo calendar, no longer used. Orig desc: The mobile device (phone) the reminder goes to."
  ID                        id-at-zimbraPrefCalendarReminderMobile }

zimbraPrefCalendarReminderSendEmail ATTRIBUTE ::= {
  WITH SYNTAX               BOOLEAN
  EQUALITY MATCHING RULE    booleanMatch
  SINGLE VALUE              TRUE
  LDAP-SYNTAX               boolean.&id
  LDAP-NAME                 {"zimbraPrefCalendarReminderSendEmail"}
  LDAP-DESC                 "Deprecated since: 6.0.0_BETA1. was added for Yahoo calendar, no longer used. Orig desc: whether or not email reminders for appointments and tasks are enabled"
  ID                        id-at-zimbraPrefCalendarReminderSendEmail }

zimbraPrefCalendarReminderSoundsEnabled ATTRIBUTE ::= {
  WITH SYNTAX               BOOLEAN
  EQUALITY MATCHING RULE    booleanMatch
  SINGLE VALUE              TRUE
  LDAP-SYNTAX               boolean.&id
  LDAP-NAME                 {"zimbraPrefCalendarReminderSoundsEnabled"}
  LDAP-DESC                 "whether audible alert is enabled when appointment notification is played"
  ID                        id-at-zimbraPrefCalendarReminderSoundsEnabled }

zimbraPrefCalendarReminderYMessenger ATTRIBUTE ::= {
  WITH SYNTAX               BOOLEAN
  EQUALITY MATCHING RULE    booleanMatch
  SINGLE VALUE              TRUE
  LDAP-SYNTAX               boolean.&id
  LDAP-NAME                 {"zimbraPrefCalendarReminderYMessenger"}
  LDAP-DESC                 "Deprecated since: 6.0.0_BETA1. was added for Yahoo calendar, no longer used. Orig desc: Send a reminder via YIM"
  ID                        id-at-zimbraPrefCalendarReminderYMessenger }

zimbraPrefCalendarSendInviteDeniedAutoReply ATTRIBUTE ::= {
  WITH SYNTAX               BOOLEAN
  EQUALITY MATCHING RULE    booleanMatch
  SINGLE VALUE              TRUE
  LDAP-SYNTAX               boolean.&id
  LDAP-NAME                 {"zimbraPrefCalendarSendInviteDeniedAutoReply"}
  LDAP-DESC                 "If an invite is received from an organizer who does not have permission to invite this user to a meeting, send an auto-decline reply. Note that zimbraPrefCalendarAllowedTargetsForInviteDeniedAutoReply may further restrict who can receive this reply."
  ID                        id-at-zimbraPrefCalendarSendInviteDeniedAutoReply }

zimbraPrefCalendarShowDeclinedMeetings ATTRIBUTE ::= {
  WITH SYNTAX               BOOLEAN
  EQUALITY MATCHING RULE    booleanMatch
  SINGLE VALUE              TRUE
  LDAP-SYNTAX               boolean.&id
  LDAP-NAME                 {"zimbraPrefCalendarShowDeclinedMeetings"}
  LDAP-DESC                 "whether to show declined meetings in calendar"
  ID                        id-at-zimbraPrefCalendarShowDeclinedMeetings }

zimbraPrefCalendarShowPastDueReminders ATTRIBUTE ::= {
  WITH SYNTAX               BOOLEAN
  EQUALITY MATCHING RULE    booleanMatch
  SINGLE VALUE              TRUE
  LDAP-SYNTAX               boolean.&id
  LDAP-NAME                 {"zimbraPrefCalendarShowPastDueReminders"}
  LDAP-DESC                 "whether to pop-up reminder for past due appointments in the UI"
  ID                        id-at-zimbraPrefCalendarShowPastDueReminders }

-- LDAP syntax length {256} rendered as DirectoryString{256}.
zimbraPrefCalendarTentativeSignatureId ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraPrefCalendarTentativeSignatureId"}
  LDAP-DESC                 "calendar manual tentative accept reply signature id for account/identity/dataSource"
  ID                        id-at-zimbraPrefCalendarTentativeSignatureId }

zimbraPrefCalendarToasterEnabled ATTRIBUTE ::= {
  WITH SYNTAX               BOOLEAN
  EQUALITY MATCHING RULE    booleanMatch
  SINGLE VALUE              TRUE
  LDAP-SYNTAX               boolean.&id
  LDAP-NAME                 {"zimbraPrefCalendarToasterEnabled"}
  LDAP-DESC                 "whether to enable toaster notification for new mail"
  ID                        id-at-zimbraPrefCalendarToasterEnabled }

zimbraPrefCalendarUseQuickAdd ATTRIBUTE ::= {
  WITH SYNTAX               BOOLEAN
  EQUALITY MATCHING RULE    booleanMatch
  SINGLE VALUE              TRUE
  LDAP-SYNTAX               boolean.&id
  LDAP-NAME                 {"zimbraPrefCalendarUseQuickAdd"}
  LDAP-DESC                 "whether or not use quick add dialog or go into full appt edit view"
  ID                        id-at-zimbraPrefCalendarUseQuickAdd }

zimbraPrefCalendarViewTimeInterval ATTRIBUTE ::= {
  WITH SYNTAX               IA5String(SIZE (1..32))
  EQUALITY MATCHING RULE    caseIgnoreIA5Match
  SINGLE VALUE              TRUE
  LDAP-SYNTAX               ia5String.&id
  LDAP-NAME                 {"zimbraPrefCalendarViewTimeInterval"}
  LDAP-DESC                 "time interval to display on calendar views. Must be in valid duration format: {digits}{time-unit}. digits: 0-9, time-unit: [hmsd]|ms. h - hours, m - minutes, s - seconds, d - days, ms - milliseconds. If time unit is not specified, the default is s(seconds)."
  ID                        id-at-zimbraPrefCalendarViewTimeInterval }

zimbraPrefCalendarWorkingHours ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraPrefCalendarWorkingHours"}
  LDAP-DESC                 "working hours for each day of the week"
  ID                        id-at-zimbraPrefCalendarWorkingHours }

-- LDAP syntax length {256} rendered as DirectoryString{256}.
zimbraPrefChildVisibleAccount ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraPrefChildVisibleAccount"}
  LDAP-DESC                 "Deprecated since: 8.5.0. family mailbox feature is deprecated. Orig desc: zimbraId of visible child accounts"
  ID                        id-at-zimbraPrefChildVisibleAccount }

-- LDAP syntax length {32} rendered as DirectoryString{32}.
zimbraPrefClientType ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraPrefClientType"}
  LDAP-DESC                 "user preference of client type"
  ID                        id-at-zimbraPrefClientType }

zimbraPrefColorMessagesEnabled ATTRIBUTE ::= {
  WITH SYNTAX               BOOLEAN
  EQUALITY MATCHING RULE    booleanMatch
  SINGLE VALUE              TRUE
  LDAP-SYNTAX               boolean.&id
  LDAP-NAME                 {"zimbraPrefColorMessagesEnabled"}
  LDAP-DESC                 "whether or not to use tag color as the color for message items"
  ID                        id-at-zimbraPrefColorMessagesEnabled }

-- LDAP syntax length {32} rendered as DirectoryString{32}.
zimbraPrefComposeDirection ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraPrefComposeDirection"}
  LDAP-DESC                 "direction for composing messages in the web client UI"
  ID                        id-at-zimbraPrefComposeDirection }

-- LDAP syntax length {32} rendered as DirectoryString{32}.
zimbraPrefComposeFormat ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraPrefComposeFormat"}
  LDAP-DESC                 "whether or not to compose in html or text."
  ID                        id-at-zimbraPrefComposeFormat }

zimbraPrefComposeInNewWindow ATTRIBUTE ::= {
  WITH SYNTAX               BOOLEAN
  EQUALITY MATCHING RULE    booleanMatch
  SINGLE VALUE              TRUE
  LDAP-SYNTAX               boolean.&id
  LDAP-NAME                 {"zimbraPrefComposeInNewWindow"}
  LDAP-DESC                 "whether or not compose messages in a new windows by default"
  ID                        id-at-zimbraPrefComposeInNewWindow }

zimbraPrefContactsDisableAutocompleteOnContactGroupMembers ATTRIBUTE ::= {
  WITH SYNTAX               BOOLEAN
  EQUALITY MATCHING RULE    booleanMatch
  SINGLE VALUE              TRUE
  LDAP-SYNTAX               boolean.&id
  LDAP-NAME                 {"zimbraPrefContactsDisableAutocompleteOnContactGroupMembers"}
  LDAP-DESC                 "Deprecated since: 8.0.0. Since 8.0.0, the contact group can contain member references, but member references are not searchable.. Orig desc: Disables autocomplete matching against the members email address."
  ID                        id-at-zimbraPrefContactsDisableAutocompleteOnContactGroupMembers }

zimbraPrefContactsExpandAppleContactGroups ATTRIBUTE ::= {
  WITH SYNTAX               BOOLEAN
  EQUALITY MATCHING RULE    booleanMatch
  SINGLE VALUE              TRUE
  LDAP-SYNTAX               boolean.&id
  LDAP-NAME                 {"zimbraPrefContactsExpandAppleContactGroups"}
  LDAP-DESC                 "Deprecated since: 8.0.0. deprecated now that Zimbra supports keeping member references in a contact group. Orig desc: Expand the contact groups in Apple Address Book format to Zimbra format over CardDAV."
  ID                        id-at-zimbraPrefContactsExpandAppleContactGroups }

-- LDAP syntax length {32} rendered as DirectoryString{32}.
zimbraPrefContactsInitialView ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraPrefContactsInitialView"}
  LDAP-DESC                 "Deprecated since: 6.0.5. We do not support cards view any more. See bug 47439. Orig desc: initial contact view to use"
  ID                        id-at-zimbraPrefContactsInitialView }

zimbraPrefContactsPerPage ATTRIBUTE ::= {
  WITH SYNTAX               INTEGER
  EQUALITY MATCHING RULE    integerMatch
  SINGLE VALUE              TRUE
  LDAP-SYNTAX               integer.&id
  LDAP-NAME                 {"zimbraPrefContactsPerPage"}
  LDAP-DESC                 "number of contacts per page"
  ID                        id-at-zimbraPrefContactsPerPage }

-- LDAP syntax length {32} rendered as DirectoryString{32}.
zimbraPrefConvReadingPaneLocation ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraPrefConvReadingPaneLocation"}
  LDAP-DESC                 "where the message reading pane is displayed in conv view"
  ID                        id-at-zimbraPrefConvReadingPaneLocation }

zimbraPrefConvShowCalendar ATTRIBUTE ::= {
  WITH SYNTAX               BOOLEAN
  EQUALITY MATCHING RULE    booleanMatch
  SINGLE VALUE              TRUE
  LDAP-SYNTAX               boolean.&id
  LDAP-NAME                 {"zimbraPrefConvShowCalendar"}
  LDAP-DESC                 "When displaying an invite in a conversation, show the day calendar immediately."
  ID                        id-at-zimbraPrefConvShowCalendar }

-- LDAP syntax length {32} rendered as DirectoryString{32}.
zimbraPrefConversationOrder ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraPrefConversationOrder"}
  LDAP-DESC                 "order of messages displayed within a conversation"
  ID                        id-at-zimbraPrefConversationOrder }

-- LDAP syntax length {32} rendered as DirectoryString{32}.
zimbraPrefDedupeMessagesSentToSelf ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraPrefDedupeMessagesSentToSelf"}
  LDAP-DESC                 "dedupeNone|secondCopyIfOnToOrCC|moveSentMessageToInbox|dedupeAll"
  ID                        id-at-zimbraPrefDedupeMessagesSentToSelf }

zimbraPrefDefaultPrintFontSize ATTRIBUTE ::= {
  WITH SYNTAX               IA5String(SIZE (1..32))
  EQUALITY MATCHING RULE    caseIgnoreIA5Match
  SUBSTRINGS MATCHING RULE  caseIgnoreSubstringsMatch
  SINGLE VALUE              TRUE
  LDAP-SYNTAX               ia5String.&id
  LDAP-NAME                 {"zimbraPrefDefaultPrintFontSize"}
  LDAP-DESC                 "default font size"
  ID                        id-at-zimbraPrefDefaultPrintFontSize }

zimbraPrefDefaultSignatureId ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraPrefDefaultSignatureId"}
  LDAP-DESC                 "default mail signature for account/identity/dataSource"
  ID                        id-at-zimbraPrefDefaultSignatureId }

-- LDAP syntax length {32} rendered as DirectoryString{32}.
zimbraPrefDelegatedSendSaveTarget ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraPrefDelegatedSendSaveTarget"}
  LDAP-DESC                 "Which mailbox to save messages sent via sendAs/sendOnBehalfOf delegation to."
  ID                        id-at-zimbraPrefDelegatedSendSaveTarget }

zimbraPrefDeleteInviteOnReply ATTRIBUTE ::= {
  WITH SYNTAX               BOOLEAN
  EQUALITY MATCHING RULE    booleanMatch
  SINGLE VALUE              TRUE
  LDAP-SYNTAX               boolean.&id
  LDAP-NAME                 {"zimbraPrefDeleteInviteOnReply"}
  LDAP-DESC                 "whether meeting invite emails are moved to Trash folder upon accept/decline"
  ID                        id-at-zimbraPrefDeleteInviteOnReply }

zimbraPrefDisabledZimlets ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraPrefDisabledZimlets"}
  LDAP-DESC                 "zimlets user does not want to see in the UI"
  ID                        id-at-zimbraPrefDisabledZimlets }

zimbraPrefDisplayExternalImages ATTRIBUTE ::= {
  WITH SYNTAX               BOOLEAN
  EQUALITY MATCHING RULE    booleanMatch
  SINGLE VALUE              TRUE
  LDAP-SYNTAX               boolean.&id
  LDAP-NAME                 {"zimbraPrefDisplayExternalImages"}
  LDAP-DESC                 "whether to display external images in HTML mail"
  ID                        id-at-zimbraPrefDisplayExternalImages }

-- LDAP syntax length {32} rendered as DirectoryString{32}.
zimbraPrefExternalSendersType ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraPrefExternalSendersType"}
  LDAP-DESC                 "Specifies the meaning of an external sender. ""ALL"" means users whose domain doesn't match the recipient's or zimbraInternalSendersDomain. ""ALLNOTINAB"" means ""ALL"" minus users who are in the recipient's address book. ""INAB"" Users/Addresses whose domain doesn't match the recipient's domain or zimbraInternalSendersDomain and which are present in recipient's address book."
  ID                        id-at-zimbraPrefExternalSendersType }

-- LDAP syntax length {32} rendered as DirectoryString{32}.
zimbraPrefFileSharingApplication ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraPrefFileSharingApplication"}
  LDAP-DESC                 "indicates which application to use for file sharing"
  ID                        id-at-zimbraPrefFileSharingApplication }

zimbraPrefFolderColorEnabled ATTRIBUTE ::= {
  WITH SYNTAX               BOOLEAN
  EQUALITY MATCHING RULE    booleanMatch
  SINGLE VALUE              TRUE
  LDAP-SYNTAX               boolean.&id
  LDAP-NAME                 {"zimbraPrefFolderColorEnabled"}
  LDAP-DESC                 "whether folder color is enabled"
  ID                        id-at-zimbraPrefFolderColorEnabled }

zimbraPrefFolderTreeOpen ATTRIBUTE ::= {
  WITH SYNTAX               BOOLEAN
  EQUALITY MATCHING RULE    booleanMatch
  SINGLE VALUE              TRUE
  LDAP-SYNTAX               boolean.&id
  LDAP-NAME                 {"zimbraPrefFolderTreeOpen"}
  LDAP-DESC                 "whether or not folder tree is expanded"
  ID                        id-at-zimbraPrefFolderTreeOpen }

zimbraPrefFont ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraPrefFont"}
  LDAP-DESC                 "the font for the web client"
  ID                        id-at-zimbraPrefFont }

zimbraPrefFontSize ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraPrefFontSize"}
  LDAP-DESC                 "the font size for the web client"
  ID                        id-at-zimbraPrefFontSize }

-- LDAP syntax length {32} rendered as DirectoryString{32}.
zimbraPrefForwardIncludeOriginalText ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraPrefForwardIncludeOriginalText"}
  LDAP-DESC                 "what part of the original message to include during forwards (deprecatedSince 5.0 in identity). The value includeBody has been deprecated since 6.0.6, use includeBodyAndHeaders instead."
  ID                        id-at-zimbraPrefForwardIncludeOriginalText }

-- LDAP syntax length {32} rendered as DirectoryString{32}.
zimbraPrefForwardReplyFormat ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraPrefForwardReplyFormat"}
  LDAP-DESC                 "what format we reply/forward messages in (deprecatedSince 5.0 in identity)"
  ID                        id-at-zimbraPrefForwardReplyFormat }

zimbraPrefForwardReplyInOriginalFormat ATTRIBUTE ::= {
  WITH SYNTAX               BOOLEAN
  EQUALITY MATCHING RULE    booleanMatch
  SINGLE VALUE              TRUE
  LDAP-SYNTAX               boolean.&id
  LDAP-NAME                 {"zimbraPrefForwardReplyInOriginalFormat"}
  LDAP-DESC                 "whether or not to use same format (text or html) of message we are replying to"
  ID                        id-at-zimbraPrefForwardReplyInOriginalFormat }

zimbraPrefForwardReplyPrefixChar ATTRIBUTE ::= {
  WITH SYNTAX               IA5String(SIZE (1..1))
  EQUALITY MATCHING RULE    caseIgnoreIA5Match
  SUBSTRINGS MATCHING RULE  caseIgnoreSubstringsMatch
  SINGLE VALUE              TRUE
  LDAP-SYNTAX               ia5String.&id
  LDAP-NAME                 {"zimbraPrefForwardReplyPrefixChar"}
  LDAP-DESC                 "prefix character to use during forward/reply (deprecatedSince 5.0 in identity)"
  ID                        id-at-zimbraPrefForwardReplyPrefixChar }

-- LDAP syntax length {256} rendered as DirectoryString{256}.
zimbraPrefForwardReplySignatureId ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraPrefForwardReplySignatureId"}
  LDAP-DESC                 "forward/reply signature id for account/identity/dataSource"
  ID                        id-at-zimbraPrefForwardReplySignatureId }

-- LDAP syntax length {256} rendered as DirectoryString{256}.
zimbraPrefFromAddress ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraPrefFromAddress"}
  LDAP-DESC                 "email address to put in from header. Deprecated on data source as of bug 67068."
  ID                        id-at-zimbraPrefFromAddress }

-- LDAP syntax length {32} rendered as DirectoryString{32}.
zimbraPrefFromAddressType ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraPrefFromAddressType"}
  LDAP-DESC                 "Type of the email address from header. (sendAs or sendOnBehalfOf)"
  ID                        id-at-zimbraPrefFromAddressType }

-- LDAP syntax length {256} rendered as DirectoryString{256}.
zimbraPrefFromDisplay ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraPrefFromDisplay"}
  LDAP-DESC                 "personal part of email address put in from header"
  ID                        id-at-zimbraPrefFromDisplay }

zimbraPrefGalAutoCompleteEnabled ATTRIBUTE ::= {
  WITH SYNTAX               BOOLEAN
  EQUALITY MATCHING RULE    booleanMatch
  SINGLE VALUE              TRUE
  LDAP-SYNTAX               boolean.&id
  LDAP-NAME                 {"zimbraPrefGalAutoCompleteEnabled"}
  LDAP-DESC                 "whether end-user wants auto-complete from GAL. Feature must also be enabled."
  ID                        id-at-zimbraPrefGalAutoCompleteEnabled }

zimbraPrefGalSearchEnabled ATTRIBUTE ::= {
  WITH SYNTAX               BOOLEAN
  EQUALITY MATCHING RULE    booleanMatch
  SINGLE VALUE              TRUE
  LDAP-SYNTAX               boolean.&id
  LDAP-NAME                 {"zimbraPrefGalSearchEnabled"}
  LDAP-DESC                 "whether end-user wants search from GAL. Feature must also be enabled"
  ID                        id-at-zimbraPrefGalSearchEnabled }

-- LDAP syntax length {32} rendered as DirectoryString{32}.
zimbraPrefGetMailAction ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraPrefGetMailAction"}
  LDAP-DESC                 "action to perform for the get mail button in UI"
  ID                        id-at-zimbraPrefGetMailAction }

-- LDAP syntax length {32} rendered as DirectoryString{32}.
zimbraPrefGroupMailBy ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraPrefGroupMailBy"}
  LDAP-DESC                 "how to group mail by default"
  ID                        id-at-zimbraPrefGroupMailBy }

zimbraPrefHtmlEditorDefaultFontColor ATTRIBUTE ::= {
  WITH SYNTAX               IA5String(SIZE (1..32))
  EQUALITY MATCHING RULE    caseIgnoreIA5Match
  SUBSTRINGS MATCHING RULE  caseIgnoreSubstringsMatch
  SINGLE VALUE              TRUE
  LDAP-SYNTAX               ia5String.&id
  LDAP-NAME                 {"zimbraPrefHtmlEditorDefaultFontColor"}
  LDAP-DESC                 "default font color"
  ID                        id-at-zimbraPrefHtmlEditorDefaultFontColor }

zimbraPrefHtmlEditorDefaultFontFamily ATTRIBUTE ::= {
  WITH SYNTAX               IA5String(SIZE (1..64))
  EQUALITY MATCHING RULE    caseIgnoreIA5Match
  SUBSTRINGS MATCHING RULE  caseIgnoreSubstringsMatch
  SINGLE VALUE              TRUE
  LDAP-SYNTAX               ia5String.&id
  LDAP-NAME                 {"zimbraPrefHtmlEditorDefaultFontFamily"}
  LDAP-DESC                 "default font family"
  ID                        id-at-zimbraPrefHtmlEditorDefaultFontFamily }

zimbraPrefHtmlEditorDefaultFontSize ATTRIBUTE ::= {
  WITH SYNTAX               IA5String(SIZE (1..32))
  EQUALITY MATCHING RULE    caseIgnoreIA5Match
  SUBSTRINGS MATCHING RULE  caseIgnoreSubstringsMatch
  SINGLE VALUE              TRUE
  LDAP-SYNTAX               ia5String.&id
  LDAP-NAME                 {"zimbraPrefHtmlEditorDefaultFontSize"}
  LDAP-DESC                 "default font size"
  ID                        id-at-zimbraPrefHtmlEditorDefaultFontSize }

zimbraPrefIMAutoLogin ATTRIBUTE ::= {
  WITH SYNTAX               BOOLEAN
  EQUALITY MATCHING RULE    booleanMatch
  SINGLE VALUE              TRUE
  LDAP-SYNTAX               boolean.&id
  LDAP-NAME                 {"zimbraPrefIMAutoLogin"}
  LDAP-DESC                 "whether to login to the IM client automatically"
  ID                        id-at-zimbraPrefIMAutoLogin }

zimbraPrefIMBuddyListSort ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraPrefIMBuddyListSort"}
  LDAP-DESC                 "IM buddy list sort order"
  ID                        id-at-zimbraPrefIMBuddyListSort }

zimbraPrefIMCustomStatusMessage ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraPrefIMCustomStatusMessage"}
  LDAP-DESC                 "Custom IM status messages"
  ID                        id-at-zimbraPrefIMCustomStatusMessage }

zimbraPrefIMFlashIcon ATTRIBUTE ::= {
  WITH SYNTAX               BOOLEAN
  EQUALITY MATCHING RULE    booleanMatch
  SINGLE VALUE              TRUE
  LDAP-SYNTAX               boolean.&id
  LDAP-NAME                 {"zimbraPrefIMFlashIcon"}
  LDAP-DESC                 "Flash IM icon on new messages"
  ID                        id-at-zimbraPrefIMFlashIcon }

zimbraPrefIMFlashTitle ATTRIBUTE ::= {
  WITH SYNTAX               BOOLEAN
  EQUALITY MATCHING RULE    booleanMatch
  SINGLE VALUE              TRUE
  LDAP-SYNTAX               boolean.&id
  LDAP-NAME                 {"zimbraPrefIMFlashTitle"}
  LDAP-DESC                 "Flash title bar when a new IM arrives"
  ID                        id-at-zimbraPrefIMFlashTitle }

zimbraPrefIMHideBlockedBuddies ATTRIBUTE ::= {
  WITH SYNTAX               BOOLEAN
  EQUALITY MATCHING RULE    booleanMatch
  SINGLE VALUE              TRUE
  LDAP-SYNTAX               boolean.&id
  LDAP-NAME                 {"zimbraPrefIMHideBlockedBuddies"}
  LDAP-DESC                 "whether to hide IM blocked buddies"
  ID                        id-at-zimbraPrefIMHideBlockedBuddies }

zimbraPrefIMHideOfflineBuddies ATTRIBUTE ::= {
  WITH SYNTAX               BOOLEAN
  EQUALITY MATCHING RULE    booleanMatch
  SINGLE VALUE              TRUE
  LDAP-SYNTAX               boolean.&id
  LDAP-NAME                 {"zimbraPrefIMHideOfflineBuddies"}
  LDAP-DESC                 "whether to hide IM offline buddies"
  ID                        id-at-zimbraPrefIMHideOfflineBuddies }

-- LDAP syntax length {32} rendered as DirectoryString{32}.
zimbraPrefIMIdleStatus ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraPrefIMIdleStatus"}
  LDAP-DESC                 "IM idle status"
  ID                        id-at-zimbraPrefIMIdleStatus }

zimbraPrefIMIdleTimeout ATTRIBUTE ::= {
  WITH SYNTAX               INTEGER
  EQUALITY MATCHING RULE    integerMatch
  SINGLE VALUE              TRUE
  LDAP-SYNTAX               integer.&id
  LDAP-NAME                 {"zimbraPrefIMIdleTimeout"}
  LDAP-DESC                 "IM session idle timeout in minutes"
  ID                        id-at-zimbraPrefIMIdleTimeout }

zimbraPrefIMInstantNotify ATTRIBUTE ::= {
  WITH SYNTAX               BOOLEAN
  EQUALITY MATCHING RULE    booleanMatch
  SINGLE VALUE              TRUE
  LDAP-SYNTAX               boolean.&id
  LDAP-NAME                 {"zimbraPrefIMInstantNotify"}
  LDAP-DESC                 "Enable instant notifications"
  ID                        id-at-zimbraPrefIMInstantNotify }

zimbraPrefIMLogChats ATTRIBUTE ::= {
  WITH SYNTAX               BOOLEAN
  EQUALITY MATCHING RULE    booleanMatch
  SINGLE VALUE              TRUE
  LDAP-SYNTAX               boolean.&id
  LDAP-NAME                 {"zimbraPrefIMLogChats"}
  LDAP-DESC                 "whether to log IM chats to the Chats folder"
  ID                        id-at-zimbraPrefIMLogChats }

zimbraPrefIMLogChatsEnabled ATTRIBUTE ::= {
  WITH SYNTAX               BOOLEAN
  EQUALITY MATCHING RULE    booleanMatch
  SINGLE VALUE              TRUE
  LDAP-SYNTAX               boolean.&id
  LDAP-NAME                 {"zimbraPrefIMLogChatsEnabled"}
  LDAP-DESC                 "whether IM log chats is enabled"
  ID                        id-at-zimbraPrefIMLogChatsEnabled }

zimbraPrefIMNotifyPresence ATTRIBUTE ::= {
  WITH SYNTAX               BOOLEAN
  EQUALITY MATCHING RULE    booleanMatch
  SINGLE VALUE              TRUE
  LDAP-SYNTAX               boolean.&id
  LDAP-NAME                 {"zimbraPrefIMNotifyPresence"}
  LDAP-DESC                 "Notify for presence modifications"
  ID                        id-at-zimbraPrefIMNotifyPresence }

zimbraPrefIMNotifyStatus ATTRIBUTE ::= {
  WITH SYNTAX               BOOLEAN
  EQUALITY MATCHING RULE    booleanMatch
  SINGLE VALUE              TRUE
  LDAP-SYNTAX               boolean.&id
  LDAP-NAME                 {"zimbraPrefIMNotifyStatus"}
  LDAP-DESC                 "Notify for status change"
  ID                        id-at-zimbraPrefIMNotifyStatus }

zimbraPrefIMReportIdle ATTRIBUTE ::= {
  WITH SYNTAX               BOOLEAN
  EQUALITY MATCHING RULE    booleanMatch
  SINGLE VALUE              TRUE
  LDAP-SYNTAX               boolean.&id
  LDAP-NAME                 {"zimbraPrefIMReportIdle"}
  LDAP-DESC                 "whether to report IM idle status"
  ID                        id-at-zimbraPrefIMReportIdle }

zimbraPrefIMSoundsEnabled ATTRIBUTE ::= {
  WITH SYNTAX               BOOLEAN
  EQUALITY MATCHING RULE    booleanMatch
  SINGLE VALUE              TRUE
  LDAP-SYNTAX               boolean.&id
  LDAP-NAME                 {"zimbraPrefIMSoundsEnabled"}
  LDAP-DESC                 "whether sounds is enabled in IM"
  ID                        id-at-zimbraPrefIMSoundsEnabled }

zimbraPrefIMToasterEnabled ATTRIBUTE ::= {
  WITH SYNTAX               BOOLEAN
  EQUALITY MATCHING RULE    booleanMatch
  SINGLE VALUE              TRUE
  LDAP-SYNTAX               boolean.&id
  LDAP-NAME                 {"zimbraPrefIMToasterEnabled"}
  LDAP-DESC                 "whether to enable toaster notification for IM"
  ID                        id-at-zimbraPrefIMToasterEnabled }

zimbraPrefIMYahooId ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraPrefIMYahooId"}
  LDAP-DESC                 "last used yahoo id"
  ID                        id-at-zimbraPrefIMYahooId }

-- LDAP syntax length {256} rendered as DirectoryString{256}.
zimbraPrefIdentityId ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraPrefIdentityId"}
  LDAP-DESC                 "Unique ID for an identity"
  ID                        id-at-zimbraPrefIdentityId }

-- LDAP syntax length {128} rendered as DirectoryString{128}.
zimbraPrefIdentityName ATTRIBUTE ::= {
  WITH SYNTAX               DirectoryString{128}
  EQUALITY MATCHING RULE    caseIgnoreMatch
  SUBSTRINGS MATCHING RULE  caseIgnoreSubstringsMatch
  SINGLE VALUE              TRUE
  LDAP-SYNTAX               directoryString.&id
  LDAP-NAME                 {"zimbraPrefIdentityName"}
  LDAP-DESC                 "name of the identity"
  ID                        id-at-zimbraPrefIdentityName }

zimbraPrefImapSearchFoldersEnabled ATTRIBUTE ::= {
  WITH SYNTAX               BOOLEAN
  EQUALITY MATCHING RULE    booleanMatch
  SINGLE VALUE              TRUE
  LDAP-SYNTAX               boolean.&id
  LDAP-NAME                 {"zimbraPrefImapSearchFoldersEnabled"}
  LDAP-DESC                 "whether or not the IMAP server exports search folders"
  ID                        id-at-zimbraPrefImapSearchFoldersEnabled }

zimbraPrefInboxReadLifetime ATTRIBUTE ::= {
  WITH SYNTAX               IA5String(SIZE (1..32))
  EQUALITY MATCHING RULE    caseIgnoreIA5Match
  SINGLE VALUE              TRUE
  LDAP-SYNTAX               ia5String.&id
  LDAP-NAME                 {"zimbraPrefInboxReadLifetime"}
  LDAP-DESC                 "Retention period of read messages in the Inbox folder. 0 means that all messages will be retained. . Must be in valid duration format: {digits}{time-unit}. digits: 0-9, time-unit: [hmsd]|ms. h - hours, m - minutes, s - seconds, d - days, ms - milliseconds. If time unit is not specified, the default is s(seconds)."
  ID                        id-at-zimbraPrefInboxReadLifetime }

zimbraPrefInboxUnreadLifetime ATTRIBUTE ::= {
  WITH SYNTAX               IA5String(SIZE (1..32))
  EQUALITY MATCHING RULE    caseIgnoreIA5Match
  SINGLE VALUE              TRUE
  LDAP-SYNTAX               ia5String.&id
  LDAP-NAME                 {"zimbraPrefInboxUnreadLifetime"}
  LDAP-DESC                 "Retention period of unread messages in the Inbox folder. 0 means that all messages will be retained. . Must be in valid duration format: {digits}{time-unit}. digits: 0-9, time-unit: [hmsd]|ms. h - hours, m - minutes, s - seconds, d - days, ms - milliseconds. If time unit is not specified, the default is s(seconds)."
  ID                        id-at-zimbraPrefInboxUnreadLifetime }

zimbraPrefIncludeSharedItemsInSearch ATTRIBUTE ::= {
  WITH SYNTAX               BOOLEAN
  EQUALITY MATCHING RULE    booleanMatch
  SINGLE VALUE              TRUE
  LDAP-SYNTAX               boolean.&id
  LDAP-NAME                 {"zimbraPrefIncludeSharedItemsInSearch"}
  LDAP-DESC                 "whether to include shared items in search"
  ID                        id-at-zimbraPrefIncludeSharedItemsInSearch }

zimbraPrefIncludeSpamInSearch ATTRIBUTE ::= {
  WITH SYNTAX               BOOLEAN
  EQUALITY MATCHING RULE    booleanMatch
  SINGLE VALUE              TRUE
  LDAP-SYNTAX               boolean.&id
  LDAP-NAME                 {"zimbraPrefIncludeSpamInSearch"}
  LDAP-DESC                 "whether or not to include spam in search by default"
  ID                        id-at-zimbraPrefIncludeSpamInSearch }

zimbraPrefIncludeTrashInSearch ATTRIBUTE ::= {
  WITH SYNTAX               BOOLEAN
  EQUALITY MATCHING RULE    booleanMatch
  SINGLE VALUE              TRUE
  LDAP-SYNTAX               boolean.&id
  LDAP-NAME                 {"zimbraPrefIncludeTrashInSearch"}
  LDAP-DESC                 "whether or not to include trash in search by default"
  ID                        id-at-zimbraPrefIncludeTrashInSearch }

zimbraPrefItemsPerVirtualPage ATTRIBUTE ::= {
  WITH SYNTAX               INTEGER
  EQUALITY MATCHING RULE    integerMatch
  SINGLE VALUE              TRUE
  LDAP-SYNTAX               integer.&id
  LDAP-NAME                 {"zimbraPrefItemsPerVirtualPage"}
  LDAP-DESC                 "number of messages/conversations per virtual page"
  ID                        id-at-zimbraPrefItemsPerVirtualPage }

zimbraPrefJunkLifetime ATTRIBUTE ::= {
  WITH SYNTAX               IA5String(SIZE (1..32))
  EQUALITY MATCHING RULE    caseIgnoreIA5Match
  SINGLE VALUE              TRUE
  LDAP-SYNTAX               ia5String.&id
  LDAP-NAME                 {"zimbraPrefJunkLifetime"}
  LDAP-DESC                 "Retention period of messages in the Junk folder. 0 means that all messages will be retained. This user-modifiable attribute works in conjunction with zimbraMailSpamLifetime, which is admin-modifiable. The shorter duration is used. . Must be in valid duration format: {digits}{time-unit}. digits: 0-9, time-unit: [hmsd]|ms. h - hours, m - minutes, s - seconds, d - days, ms - milliseconds. If time unit is not specified, the default is s(seconds)."
  ID                        id-at-zimbraPrefJunkLifetime }

-- LDAP syntax length {256} rendered as DirectoryString{256}.
zimbraPrefLabel ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraPrefLabel"}
  LDAP-DESC                 "optional account descriptive label"
  ID                        id-at-zimbraPrefLabel }

zimbraPrefListViewColumns ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraPrefListViewColumns"}
  LDAP-DESC                 "list view columns in web client"
  ID                        id-at-zimbraPrefListViewColumns }

-- LDAP syntax length {64} rendered as DirectoryString{64}.
zimbraPrefLocale ATTRIBUTE ::= {
  WITH SYNTAX               DirectoryString{64}
  EQUALITY MATCHING RULE    caseIgnoreMatch
  SUBSTRINGS MATCHING RULE  caseIgnoreSubstringsMatch
  SINGLE VALUE              TRUE
  LDAP-SYNTAX               directoryString.&id
  LDAP-NAME                 {"zimbraPrefLocale"}
  LDAP-DESC                 "user locale preference, e.g. en_US Whenever the server looks for the user locale, it will first look for zimbraPrefLocale, if it is not set then it will fallback to the current mechanism of looking for zimbraLocale in the various places for a user. zimbraLocale is the non end-user attribute that specifies which locale an object defaults to, it is not an end-user setting."
  ID                        id-at-zimbraPrefLocale }

-- LDAP syntax length {64} rendered as DirectoryString{64}.
zimbraPrefMailDefaultCharset ATTRIBUTE ::= {
  WITH SYNTAX               DirectoryString{64}
  EQUALITY MATCHING RULE    caseIgnoreMatch
  SUBSTRINGS MATCHING RULE  caseIgnoreSubstringsMatch
  SINGLE VALUE              TRUE
  LDAP-SYNTAX               directoryString.&id
  LDAP-NAME                 {"zimbraPrefMailDefaultCharset"}
  LDAP-DESC                 "Default Charset for mail composing and parsing text"
  ID                        id-at-zimbraPrefMailDefaultCharset }

zimbraPrefMailFlashIcon ATTRIBUTE ::= {
  WITH SYNTAX               BOOLEAN
  EQUALITY MATCHING RULE    booleanMatch
  SINGLE VALUE              TRUE
  LDAP-SYNTAX               boolean.&id
  LDAP-NAME                 {"zimbraPrefMailFlashIcon"}
  LDAP-DESC                 "Flash icon when a new email arrives"
  ID                        id-at-zimbraPrefMailFlashIcon }

zimbraPrefMailFlashTitle ATTRIBUTE ::= {
  WITH SYNTAX               BOOLEAN
  EQUALITY MATCHING RULE    booleanMatch
  SINGLE VALUE              TRUE
  LDAP-SYNTAX               boolean.&id
  LDAP-NAME                 {"zimbraPrefMailFlashTitle"}
  LDAP-DESC                 "Flash title bar when a new email arrives"
  ID                        id-at-zimbraPrefMailFlashTitle }

-- LDAP syntax length {1024} rendered as DirectoryString{1024}.
zimbraPrefMailFoldersCheckedForNewMsgIndicator ATTRIBUTE ::= {
  WITH SYNTAX               DirectoryString{1024}
  EQUALITY MATCHING RULE    caseIgnoreMatch
  SUBSTRINGS MATCHING RULE  caseIgnoreSubstringsMatch
  SINGLE VALUE              TRUE
  LDAP-SYNTAX               directoryString.&id
  LDAP-NAME                 {"zimbraPrefMailFoldersCheckedForNewMsgIndicator"}
  LDAP-DESC                 "a list of comma separated folder ids of all folders used to count for showing a new message indicator icon for the account, useful in UIs managing multiple accounts: desktop and family mailboxes."
  ID                        id-at-zimbraPrefMailFoldersCheckedForNewMsgIndicator }

zimbraPrefMailForwardingAddress ATTRIBUTE ::= {
  WITH SYNTAX               IA5String(SIZE (1..256))
  EQUALITY MATCHING RULE    caseIgnoreIA5Match
  SUBSTRINGS MATCHING RULE  caseIgnoreSubstringsMatch
  SINGLE VALUE              TRUE
  LDAP-SYNTAX               ia5String.&id
  LDAP-NAME                 {"zimbraPrefMailForwardingAddress"}
  LDAP-DESC                 "RFC822 forwarding address for an account"
  ID                        id-at-zimbraPrefMailForwardingAddress }

-- LDAP syntax length {512} rendered as DirectoryString{512}.
zimbraPrefMailInitialSearch ATTRIBUTE ::= {
  WITH SYNTAX               DirectoryString{512}
  EQUALITY MATCHING RULE    caseIgnoreMatch
  SUBSTRINGS MATCHING RULE  caseIgnoreSubstringsMatch
  SINGLE VALUE              TRUE
  LDAP-SYNTAX               directoryString.&id
  LDAP-NAME                 {"zimbraPrefMailInitialSearch"}
  LDAP-DESC                 "initial search done by dhtml client"
  ID                        id-at-zimbraPrefMailInitialSearch }

zimbraPrefMailItemsPerPage ATTRIBUTE ::= {
  WITH SYNTAX               INTEGER
  EQUALITY MATCHING RULE    integerMatch
  SINGLE VALUE              TRUE
  LDAP-SYNTAX               integer.&id
  LDAP-NAME                 {"zimbraPrefMailItemsPerPage"}
  LDAP-DESC                 "number of messages/conversations per page"
  ID                        id-at-zimbraPrefMailItemsPerPage }

zimbraPrefMailLocalDeliveryDisabled ATTRIBUTE ::= {
  WITH SYNTAX               BOOLEAN
  EQUALITY MATCHING RULE    booleanMatch
  SINGLE VALUE              TRUE
  LDAP-SYNTAX               boolean.&id
  LDAP-NAME                 {"zimbraPrefMailLocalDeliveryDisabled"}
  LDAP-DESC                 "whether or not to deliver mail locally"
  ID                        id-at-zimbraPrefMailLocalDeliveryDisabled }

zimbraPrefMailPollingInterval ATTRIBUTE ::= {
  WITH SYNTAX               IA5String(SIZE (1..32))
  EQUALITY MATCHING RULE    caseIgnoreIA5Match
  SINGLE VALUE              TRUE
  LDAP-SYNTAX               ia5String.&id
  LDAP-NAME                 {"zimbraPrefMailPollingInterval"}
  LDAP-DESC                 "interval at which the web client polls the server for new messages. Must be in valid duration format: {digits}{time-unit}. digits: 0-9, time-unit: [hmsd]|ms. h - hours, m - minutes, s - seconds, d - days, ms - milliseconds. If time unit is not specified, the default is s(seconds)."
  ID                        id-at-zimbraPrefMailPollingInterval }

zimbraPrefMailRequestReadReceipts ATTRIBUTE ::= {
  WITH SYNTAX               BOOLEAN
  EQUALITY MATCHING RULE    booleanMatch
  SINGLE VALUE              TRUE
  LDAP-SYNTAX               boolean.&id
  LDAP-NAME                 {"zimbraPrefMailRequestReadReceipts"}
  LDAP-DESC                 "whether web UI should always request read receipts for outgoing messages"
  ID                        id-at-zimbraPrefMailRequestReadReceipts }

zimbraPrefMailSMIMECertificate ATTRIBUTE ::= {
  WITH SYNTAX               OCTET STRING
  EQUALITY MATCHING RULE    octetStringMatch
  LDAP-SYNTAX               octetString.&id
  LDAP-NAME                 {"zimbraPrefMailSMIMECertificate"}
  LDAP-DESC                 "Deprecated since: 7.1.1. deprecated in favor of userCertificate and userSMIMECertificate. Orig desc: user's S/MIME public keys (certificates)"
  ID                        id-at-zimbraPrefMailSMIMECertificate }

-- LDAP syntax length {32} rendered as DirectoryString{32}.
zimbraPrefMailSelectAfterDelete ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraPrefMailSelectAfterDelete"}
  LDAP-DESC                 "After deleting a message in list, which message should be selected"
  ID                        id-at-zimbraPrefMailSelectAfterDelete }

-- LDAP syntax length {32} rendered as DirectoryString{32}.
zimbraPrefMailSendReadReceipts ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraPrefMailSendReadReceipts"}
  LDAP-DESC                 "whether to send read receipt"
  ID                        id-at-zimbraPrefMailSendReadReceipts }

zimbraPrefMailSignature ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraPrefMailSignature"}
  LDAP-DESC                 "mail text signature (deprecatedSince 5.0 in identity)"
  ID                        id-at-zimbraPrefMailSignature }

zimbraPrefMailSignatureContactId ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraPrefMailSignatureContactId"}
  LDAP-DESC                 "contact id associated with the signature"
  ID                        id-at-zimbraPrefMailSignatureContactId }

zimbraPrefMailSignatureEnabled ATTRIBUTE ::= {
  WITH SYNTAX               BOOLEAN
  EQUALITY MATCHING RULE    booleanMatch
  SINGLE VALUE              TRUE
  LDAP-SYNTAX               boolean.&id
  LDAP-NAME                 {"zimbraPrefMailSignatureEnabled"}
  LDAP-DESC                 "mail signature enabled (deprecatedSince 5.0 in identity)"
  ID                        id-at-zimbraPrefMailSignatureEnabled }

zimbraPrefMailSignatureHTML ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraPrefMailSignatureHTML"}
  LDAP-DESC                 "mail html signature"
  ID                        id-at-zimbraPrefMailSignatureHTML }

-- LDAP syntax length {32} rendered as DirectoryString{32}.
zimbraPrefMailSignatureStyle ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraPrefMailSignatureStyle"}
  LDAP-DESC                 "mail signature style outlook|internet (deprecatedSince 5.0 in identity)"
  ID                        id-at-zimbraPrefMailSignatureStyle }

zimbraPrefMailSoundsEnabled ATTRIBUTE ::= {
  WITH SYNTAX               BOOLEAN
  EQUALITY MATCHING RULE    booleanMatch
  SINGLE VALUE              TRUE
  LDAP-SYNTAX               boolean.&id
  LDAP-NAME                 {"zimbraPrefMailSoundsEnabled"}
  LDAP-DESC                 "whether audible alert is enabled when a new email arrives"
  ID                        id-at-zimbraPrefMailSoundsEnabled }

zimbraPrefMailToasterEnabled ATTRIBUTE ::= {
  WITH SYNTAX               BOOLEAN
  EQUALITY MATCHING RULE    booleanMatch
  SINGLE VALUE              TRUE
  LDAP-SYNTAX               boolean.&id
  LDAP-NAME                 {"zimbraPrefMailToasterEnabled"}
  LDAP-DESC                 "whether to enable toaster notification for new mail"
  ID                        id-at-zimbraPrefMailToasterEnabled }

zimbraPrefMailTrustedSenderList ATTRIBUTE ::= {
  WITH SYNTAX               IA5String(SIZE (1..256))
  EQUALITY MATCHING RULE    caseIgnoreIA5Match
  SUBSTRINGS MATCHING RULE  caseIgnoreSubstringsMatch
  LDAP-SYNTAX               ia5String.&id
  LDAP-NAME                 {"zimbraPrefMailTrustedSenderList"}
  LDAP-DESC                 "Trusted sender email addresses or domains. External images in emails sent by trusted senders are automatically loaded in the message view."
  ID                        id-at-zimbraPrefMailTrustedSenderList }

zimbraPrefMandatorySpellCheckEnabled ATTRIBUTE ::= {
  WITH SYNTAX               BOOLEAN
  EQUALITY MATCHING RULE    booleanMatch
  SINGLE VALUE              TRUE
  LDAP-SYNTAX               boolean.&id
  LDAP-NAME                 {"zimbraPrefMandatorySpellCheckEnabled"}
  LDAP-DESC                 "whether mandatory spell check is enabled"
  ID                        id-at-zimbraPrefMandatorySpellCheckEnabled }

zimbraPrefMarkMsgRead ATTRIBUTE ::= {
  WITH SYNTAX               INTEGER
  EQUALITY MATCHING RULE    integerMatch
  SINGLE VALUE              TRUE
  LDAP-SYNTAX               integer.&id
  LDAP-NAME                 {"zimbraPrefMarkMsgRead"}
  LDAP-DESC                 "whether and mark a message as read -1: Do not mark read 0: Mark read 1..n: Mark read after this many seconds"
  ID                        id-at-zimbraPrefMarkMsgRead }

zimbraPrefMessageIdDedupingEnabled ATTRIBUTE ::= {
  WITH SYNTAX               BOOLEAN
  EQUALITY MATCHING RULE    booleanMatch
  SINGLE VALUE              TRUE
  LDAP-SYNTAX               boolean.&id
  LDAP-NAME                 {"zimbraPrefMessageIdDedupingEnabled"}
  LDAP-DESC                 "Account-level switch that enables message deduping. See zimbraMessageIdDedupeCacheSize for more details."
  ID                        id-at-zimbraPrefMessageIdDedupingEnabled }

zimbraPrefMessageViewHtmlPreferred ATTRIBUTE ::= {
  WITH SYNTAX               BOOLEAN
  EQUALITY MATCHING RULE    booleanMatch
  SINGLE VALUE              TRUE
  LDAP-SYNTAX               boolean.&id
  LDAP-NAME                 {"zimbraPrefMessageViewHtmlPreferred"}
  LDAP-DESC                 "whether client prefers text/html or text/plain"
  ID                        id-at-zimbraPrefMessageViewHtmlPreferred }

zimbraPrefNewMailNotificationAddress ATTRIBUTE ::= {
  WITH SYNTAX               IA5String(SIZE (1..256))
  EQUALITY MATCHING RULE    caseIgnoreIA5Match
  SUBSTRINGS MATCHING RULE  caseIgnoreSubstringsMatch
  SINGLE VALUE              TRUE
  LDAP-SYNTAX               ia5String.&id
  LDAP-NAME                 {"zimbraPrefNewMailNotificationAddress"}
  LDAP-DESC                 "RFC822 email address for email notifications"
  ID                        id-at-zimbraPrefNewMailNotificationAddress }

zimbraPrefNewMailNotificationEnabled ATTRIBUTE ::= {
  WITH SYNTAX               BOOLEAN
  EQUALITY MATCHING RULE    booleanMatch
  SINGLE VALUE              TRUE
  LDAP-SYNTAX               boolean.&id
  LDAP-NAME                 {"zimbraPrefNewMailNotificationEnabled"}
  LDAP-DESC                 "whether or not new mail notification is enabled"
  ID                        id-at-zimbraPrefNewMailNotificationEnabled }

zimbraPrefOpenMailInNewWindow ATTRIBUTE ::= {
  WITH SYNTAX               BOOLEAN
  EQUALITY MATCHING RULE    booleanMatch
  SINGLE VALUE              TRUE
  LDAP-SYNTAX               boolean.&id
  LDAP-NAME                 {"zimbraPrefOpenMailInNewWindow"}
  LDAP-DESC                 "whether or not the client opens a new msg/conv in a new window (via dbl-click)"
  ID                        id-at-zimbraPrefOpenMailInNewWindow }

zimbraPrefOutOfOfficeCacheDuration ATTRIBUTE ::= {
  WITH SYNTAX               IA5String(SIZE (1..32))
  EQUALITY MATCHING RULE    caseIgnoreIA5Match
  SINGLE VALUE              TRUE
  LDAP-SYNTAX               ia5String.&id
  LDAP-NAME                 {"zimbraPrefOutOfOfficeCacheDuration"}
  LDAP-DESC                 "server remembers addresses to which notifications have been sent for this interval, and does not send duplicate notifications in this interval. Must be in valid duration format: {digits}{time-unit}. digits: 0-9, time-unit: [hmsd]|ms. h - hours, m - minutes, s - seconds, d - days, ms - milliseconds. If time unit is not specified, the default is s(seconds)."
  ID                        id-at-zimbraPrefOutOfOfficeCacheDuration }

zimbraPrefOutOfOfficeDirectAddress ATTRIBUTE ::= {
  WITH SYNTAX               IA5String(SIZE (1..256))
  EQUALITY MATCHING RULE    caseIgnoreIA5Match
  SUBSTRINGS MATCHING RULE  caseIgnoreSubstringsMatch
  LDAP-SYNTAX               ia5String.&id
  LDAP-NAME                 {"zimbraPrefOutOfOfficeDirectAddress"}
  LDAP-DESC                 "per RFC 3834 no out of office notifications are sent if recipients address is not directly specified in the To/CC headers - for this check, we check to see if To/CC contained accounts address, aliases, canonical address. But when external accounts are forwarded to Zimbra, and you want notifications sent to messages that contain their external address in To/Cc, add those address, then you can specify those external addresses here."
  ID                        id-at-zimbraPrefOutOfOfficeDirectAddress }

-- LDAP syntax length {8192} rendered as DirectoryString{8192}.
zimbraPrefOutOfOfficeExternalReply ATTRIBUTE ::= {
  WITH SYNTAX               DirectoryString{8192}
  EQUALITY MATCHING RULE    caseIgnoreMatch
  SUBSTRINGS MATCHING RULE  caseIgnoreSubstringsMatch
  SINGLE VALUE              TRUE
  LDAP-SYNTAX               directoryString.&id
  LDAP-NAME                 {"zimbraPrefOutOfOfficeExternalReply"}
  LDAP-DESC                 "out of office message to external senders"
  ID                        id-at-zimbraPrefOutOfOfficeExternalReply }

zimbraPrefOutOfOfficeExternalReplyEnabled ATTRIBUTE ::= {
  WITH SYNTAX               BOOLEAN
  EQUALITY MATCHING RULE    booleanMatch
  SINGLE VALUE              TRUE
  LDAP-SYNTAX               boolean.&id
  LDAP-NAME                 {"zimbraPrefOutOfOfficeExternalReplyEnabled"}
  LDAP-DESC                 "If TRUE, send zimbraPrefOutOfOfficeExternalReply to external senders. External senders are specified by zimbraInternalSendersDomain and zimbraPrefExternalSendersType."
  ID                        id-at-zimbraPrefOutOfOfficeExternalReplyEnabled }

-- LDAP syntax length {32} rendered as DirectoryString{32}.
zimbraPrefOutOfOfficeFreeBusyStatus ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraPrefOutOfOfficeFreeBusyStatus"}
  LDAP-DESC                 "free/busy status while out of office"
  ID                        id-at-zimbraPrefOutOfOfficeFreeBusyStatus }

zimbraPrefOutOfOfficeFromDate ATTRIBUTE ::= {
  WITH SYNTAX               GeneralizedTime
  EQUALITY MATCHING RULE    generalizedTimeMatch
  ORDERING MATCHING RULE    generalizedTimeOrderingMatch
  SINGLE VALUE              TRUE
  LDAP-SYNTAX               generalizedTime.&id
  LDAP-NAME                 {"zimbraPrefOutOfOfficeFromDate"}
  LDAP-DESC                 "out of office notifications (if enabled) are sent only if current date is after this date"
  ID                        id-at-zimbraPrefOutOfOfficeFromDate }

-- LDAP syntax length {8192} rendered as DirectoryString{8192}.
zimbraPrefOutOfOfficeReply ATTRIBUTE ::= {
  WITH SYNTAX               DirectoryString{8192}
  EQUALITY MATCHING RULE    caseIgnoreMatch
  SUBSTRINGS MATCHING RULE  caseIgnoreSubstringsMatch
  SINGLE VALUE              TRUE
  LDAP-SYNTAX               directoryString.&id
  LDAP-NAME                 {"zimbraPrefOutOfOfficeReply"}
  LDAP-DESC                 "out of office message"
  ID                        id-at-zimbraPrefOutOfOfficeReply }

zimbraPrefOutOfOfficeReplyEnabled ATTRIBUTE ::= {
  WITH SYNTAX               BOOLEAN
  EQUALITY MATCHING RULE    booleanMatch
  SINGLE VALUE              TRUE
  LDAP-SYNTAX               boolean.&id
  LDAP-NAME                 {"zimbraPrefOutOfOfficeReplyEnabled"}
  LDAP-DESC                 "whether or not out of office reply is enabled"
  ID                        id-at-zimbraPrefOutOfOfficeReplyEnabled }

zimbraPrefOutOfOfficeStatusAlertOnLogin ATTRIBUTE ::= {
  WITH SYNTAX               BOOLEAN
  EQUALITY MATCHING RULE    booleanMatch
  SINGLE VALUE              TRUE
  LDAP-SYNTAX               boolean.&id
  LDAP-NAME                 {"zimbraPrefOutOfOfficeStatusAlertOnLogin"}
  LDAP-DESC                 "when user has OOO message enabled, when they login into web client, whether to alert the user that the OOO message is turned on and provide the ability to turn it off"
  ID                        id-at-zimbraPrefOutOfOfficeStatusAlertOnLogin }

zimbraPrefOutOfOfficeSuppressExternalReply ATTRIBUTE ::= {
  WITH SYNTAX               BOOLEAN
  EQUALITY MATCHING RULE    booleanMatch
  SINGLE VALUE              TRUE
  LDAP-SYNTAX               boolean.&id
  LDAP-NAME                 {"zimbraPrefOutOfOfficeSuppressExternalReply"}
  LDAP-DESC                 "If TRUE, OOO reply is not sent to external senders, when the user enables OOO for the account"
  ID                        id-at-zimbraPrefOutOfOfficeSuppressExternalReply }

zimbraPrefOutOfOfficeUntilDate ATTRIBUTE ::= {
  WITH SYNTAX               GeneralizedTime
  EQUALITY MATCHING RULE    generalizedTimeMatch
  ORDERING MATCHING RULE    generalizedTimeOrderingMatch
  SINGLE VALUE              TRUE
  LDAP-SYNTAX               generalizedTime.&id
  LDAP-NAME                 {"zimbraPrefOutOfOfficeUntilDate"}
  LDAP-DESC                 "out of office notifications (if enabled) are sent only if current date is before this date"
  ID                        id-at-zimbraPrefOutOfOfficeUntilDate }

-- LDAP syntax length {32} rendered as DirectoryString{32}.
zimbraPrefPop3DeleteOption ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraPrefPop3DeleteOption"}
  LDAP-DESC                 "When messages are accessed via POP3: - keep: Leave DELE'ed messages in Inbox. - read: Mark RETR'ed messages as read, and leave DELE'ed messages in Inbox. - trash: Move DELE'ed messages to Trash, and mark them as read. - delete: Hard-delete DELE'ed messages. This is the straightforward POP3 implementation."
  ID                        id-at-zimbraPrefPop3DeleteOption }

zimbraPrefPop3DownloadSince ATTRIBUTE ::= {
  WITH SYNTAX               GeneralizedTime
  EQUALITY MATCHING RULE    generalizedTimeMatch
  ORDERING MATCHING RULE    generalizedTimeOrderingMatch
  SINGLE VALUE              TRUE
  LDAP-SYNTAX               generalizedTime.&id
  LDAP-NAME                 {"zimbraPrefPop3DownloadSince"}
  LDAP-DESC                 "download pop3 messages since"
  ID                        id-at-zimbraPrefPop3DownloadSince }

zimbraPrefPop3IncludeSpam ATTRIBUTE ::= {
  WITH SYNTAX               BOOLEAN
  EQUALITY MATCHING RULE    booleanMatch
  SINGLE VALUE              TRUE
  LDAP-SYNTAX               boolean.&id
  LDAP-NAME                 {"zimbraPrefPop3IncludeSpam"}
  LDAP-DESC                 "whether or not to include spam messages in POP3 access"
  ID                        id-at-zimbraPrefPop3IncludeSpam }

zimbraPrefQuickCommand ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraPrefQuickCommand"}
  LDAP-DESC                 "quick command encoded by the client"
  ID                        id-at-zimbraPrefQuickCommand }

-- LDAP syntax length {256} rendered as DirectoryString{256}.
zimbraPrefReadReceiptsToAddress ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraPrefReadReceiptsToAddress"}
  LDAP-DESC                 "Deprecated since: 6.0.8. Deprecated per bug 46988. This feature was never fully implemented.. Orig desc: address to put in reply-to header of read receipt messages, if it is not set, then the compose identities primary email address is used."
  ID                        id-at-zimbraPrefReadReceiptsToAddress }

zimbraPrefReadingPaneEnabled ATTRIBUTE ::= {
  WITH SYNTAX               BOOLEAN
  EQUALITY MATCHING RULE    booleanMatch
  SINGLE VALUE              TRUE
  LDAP-SYNTAX               boolean.&id
  LDAP-NAME                 {"zimbraPrefReadingPaneEnabled"}
  LDAP-DESC                 "Deprecated since: 6.0.0_BETA2. deprecated in favor of zimbraPrefReadingPaneLocation and zimbraPrefConvReadingPaneLocation. Orig desc: whether reading pane is shown by default"
  ID                        id-at-zimbraPrefReadingPaneEnabled }

-- LDAP syntax length {32} rendered as DirectoryString{32}.
zimbraPrefReadingPaneLocation ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraPrefReadingPaneLocation"}
  LDAP-DESC                 "where the message reading pane is displayed in list views"
  ID                        id-at-zimbraPrefReadingPaneLocation }

-- LDAP syntax length {32} rendered as DirectoryString{32}.
zimbraPrefReplyIncludeOriginalText ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraPrefReplyIncludeOriginalText"}
  LDAP-DESC                 "what part of the original message to include during replies (deprecatedSince 5.0 in identity). The value includeBody has been deprecated since 6.0.6, use includeBodyAndHeaders instead."
  ID                        id-at-zimbraPrefReplyIncludeOriginalText }

-- LDAP syntax length {256} rendered as DirectoryString{256}.
zimbraPrefReplyToAddress ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraPrefReplyToAddress"}
  LDAP-DESC                 "address to put in reply-to header"
  ID                        id-at-zimbraPrefReplyToAddress }

-- LDAP syntax length {256} rendered as DirectoryString{256}.
zimbraPrefReplyToDisplay ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraPrefReplyToDisplay"}
  LDAP-DESC                 "personal part of email address put in reply-to header"
  ID                        id-at-zimbraPrefReplyToDisplay }

zimbraPrefReplyToEnabled ATTRIBUTE ::= {
  WITH SYNTAX               BOOLEAN
  EQUALITY MATCHING RULE    booleanMatch
  SINGLE VALUE              TRUE
  LDAP-SYNTAX               boolean.&id
  LDAP-NAME                 {"zimbraPrefReplyToEnabled"}
  LDAP-DESC                 "TRUE if we should set a reply-to header"
  ID                        id-at-zimbraPrefReplyToEnabled }

zimbraPrefSaveToSent ATTRIBUTE ::= {
  WITH SYNTAX               BOOLEAN
  EQUALITY MATCHING RULE    booleanMatch
  SINGLE VALUE              TRUE
  LDAP-SYNTAX               boolean.&id
  LDAP-NAME                 {"zimbraPrefSaveToSent"}
  LDAP-DESC                 "whether or not to save outgoing mail (deprecatedSince 5.0 in identity)"
  ID                        id-at-zimbraPrefSaveToSent }

zimbraPrefSearchTreeOpen ATTRIBUTE ::= {
  WITH SYNTAX               BOOLEAN
  EQUALITY MATCHING RULE    booleanMatch
  SINGLE VALUE              TRUE
  LDAP-SYNTAX               boolean.&id
  LDAP-NAME                 {"zimbraPrefSearchTreeOpen"}
  LDAP-DESC                 "whether or not search tree is expanded"
  ID                        id-at-zimbraPrefSearchTreeOpen }

zimbraPrefSentLifetime ATTRIBUTE ::= {
  WITH SYNTAX               IA5String(SIZE (1..32))
  EQUALITY MATCHING RULE    caseIgnoreIA5Match
  SINGLE VALUE              TRUE
  LDAP-SYNTAX               ia5String.&id
  LDAP-NAME                 {"zimbraPrefSentLifetime"}
  LDAP-DESC                 "Retention period of messages in the Sent folder. 0 means that all messages will be retained. . Must be in valid duration format: {digits}{time-unit}. digits: 0-9, time-unit: [hmsd]|ms. h - hours, m - minutes, s - seconds, d - days, ms - milliseconds. If time unit is not specified, the default is s(seconds)."
  ID                        id-at-zimbraPrefSentLifetime }

-- LDAP syntax length {256} rendered as DirectoryString{256}.
zimbraPrefSentMailFolder ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraPrefSentMailFolder"}
  LDAP-DESC                 "name of folder to save sent mail in (deprecatedSince 5.0 in identity)"
  ID                        id-at-zimbraPrefSentMailFolder }

zimbraPrefSharedAddrBookAutoCompleteEnabled ATTRIBUTE ::= {
  WITH SYNTAX               BOOLEAN
  EQUALITY MATCHING RULE    booleanMatch
  SINGLE VALUE              TRUE
  LDAP-SYNTAX               boolean.&id
  LDAP-NAME                 {"zimbraPrefSharedAddrBookAutoCompleteEnabled"}
  LDAP-DESC                 "whether end-user wants auto-complete from shared address books."
  ID                        id-at-zimbraPrefSharedAddrBookAutoCompleteEnabled }

zimbraPrefShortEmailAddress ATTRIBUTE ::= {
  WITH SYNTAX               BOOLEAN
  EQUALITY MATCHING RULE    booleanMatch
  SINGLE VALUE              TRUE
  LDAP-SYNTAX               boolean.&id
  LDAP-NAME                 {"zimbraPrefShortEmailAddress"}
  LDAP-DESC                 "show just the display name of email addresses in the message header area and compose pane"
  ID                        id-at-zimbraPrefShortEmailAddress }

-- LDAP syntax length {2048} rendered as DirectoryString{2048}.
zimbraPrefShortcuts ATTRIBUTE ::= {
  WITH SYNTAX               DirectoryString{2048}
  EQUALITY MATCHING RULE    caseIgnoreMatch
  SUBSTRINGS MATCHING RULE  caseIgnoreSubstringsMatch
  SINGLE VALUE              TRUE
  LDAP-SYNTAX               directoryString.&id
  LDAP-NAME                 {"zimbraPrefShortcuts"}
  LDAP-DESC                 "keyboard shortcuts"
  ID                        id-at-zimbraPrefShortcuts }

zimbraPrefShowCalendarWeek ATTRIBUTE ::= {
  WITH SYNTAX               BOOLEAN
  EQUALITY MATCHING RULE    booleanMatch
  SINGLE VALUE              TRUE
  LDAP-SYNTAX               boolean.&id
  LDAP-NAME                 {"zimbraPrefShowCalendarWeek"}
  LDAP-DESC                 "show calendar week in calendar views"
  ID                        id-at-zimbraPrefShowCalendarWeek }

zimbraPrefShowComposeDirection ATTRIBUTE ::= {
  WITH SYNTAX               BOOLEAN
  EQUALITY MATCHING RULE    booleanMatch
  SINGLE VALUE              TRUE
  LDAP-SYNTAX               boolean.&id
  LDAP-NAME                 {"zimbraPrefShowComposeDirection"}
  LDAP-DESC                 "whether or not to show direction buttons in compose toolbar"
  ID                        id-at-zimbraPrefShowComposeDirection }

zimbraPrefShowFragments ATTRIBUTE ::= {
  WITH SYNTAX               BOOLEAN
  EQUALITY MATCHING RULE    booleanMatch
  SINGLE VALUE              TRUE
  LDAP-SYNTAX               boolean.&id
  LDAP-NAME                 {"zimbraPrefShowFragments"}
  LDAP-DESC                 "show fragments in conversation and message lists"
  ID                        id-at-zimbraPrefShowFragments }

zimbraPrefShowSearchString ATTRIBUTE ::= {
  WITH SYNTAX               BOOLEAN
  EQUALITY MATCHING RULE    booleanMatch
  SINGLE VALUE              TRUE
  LDAP-SYNTAX               boolean.&id
  LDAP-NAME                 {"zimbraPrefShowSearchString"}
  LDAP-DESC                 "whether to show search box or not"
  ID                        id-at-zimbraPrefShowSearchString }

zimbraPrefShowSelectionCheckbox ATTRIBUTE ::= {
  WITH SYNTAX               BOOLEAN
  EQUALITY MATCHING RULE    booleanMatch
  SINGLE VALUE              TRUE
  LDAP-SYNTAX               boolean.&id
  LDAP-NAME                 {"zimbraPrefShowSelectionCheckbox"}
  LDAP-DESC                 "show selection checkbox for selecting email, contact, voicemail items in a list view for batch operations"
  ID                        id-at-zimbraPrefShowSelectionCheckbox }

-- LDAP syntax length {80} rendered as DirectoryString{80}.
zimbraPrefSkin ATTRIBUTE ::= {
  WITH SYNTAX               DirectoryString{80}
  EQUALITY MATCHING RULE    caseIgnoreMatch
  SUBSTRINGS MATCHING RULE  caseIgnoreSubstringsMatch
  SINGLE VALUE              TRUE
  LDAP-SYNTAX               directoryString.&id
  LDAP-NAME                 {"zimbraPrefSkin"}
  LDAP-DESC                 "Skin to use for this account"
  ID                        id-at-zimbraPrefSkin }

zimbraPrefSortOrder ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraPrefSortOrder"}
  LDAP-DESC                 "sort order for list view in the WEB UI"
  ID                        id-at-zimbraPrefSortOrder }

-- LDAP syntax length {64} rendered as DirectoryString{64}.
zimbraPrefSpellDictionary ATTRIBUTE ::= {
  WITH SYNTAX               DirectoryString{64}
  EQUALITY MATCHING RULE    caseIgnoreMatch
  SUBSTRINGS MATCHING RULE  caseIgnoreSubstringsMatch
  SINGLE VALUE              TRUE
  LDAP-SYNTAX               directoryString.&id
  LDAP-NAME                 {"zimbraPrefSpellDictionary"}
  LDAP-DESC                 "The name of the dictionary used for spell checking. If not set, the locale is used."
  ID                        id-at-zimbraPrefSpellDictionary }

zimbraPrefSpellIgnoreAllCaps ATTRIBUTE ::= {
  WITH SYNTAX               BOOLEAN
  EQUALITY MATCHING RULE    booleanMatch
  SINGLE VALUE              TRUE
  LDAP-SYNTAX               boolean.&id
  LDAP-NAME                 {"zimbraPrefSpellIgnoreAllCaps"}
  LDAP-DESC                 "If TRUE, the spell checker ignores words that contain only upper-case letters."
  ID                        id-at-zimbraPrefSpellIgnoreAllCaps }

zimbraPrefSpellIgnorePattern ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraPrefSpellIgnorePattern"}
  LDAP-DESC                 "Regular Expression for words to ignore during spell check."
  ID                        id-at-zimbraPrefSpellIgnorePattern }

-- LDAP syntax length {256} rendered as DirectoryString{256}.
zimbraPrefSpellIgnoreWord ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraPrefSpellIgnoreWord"}
  LDAP-DESC                 "List of words to ignore when checking spelling. The word list of an account includes the words specified for its cos and domain."
  ID                        id-at-zimbraPrefSpellIgnoreWord }

zimbraPrefStandardClientAccessibilityMode ATTRIBUTE ::= {
  WITH SYNTAX               BOOLEAN
  EQUALITY MATCHING RULE    booleanMatch
  SINGLE VALUE              TRUE
  LDAP-SYNTAX               boolean.&id
  LDAP-NAME                 {"zimbraPrefStandardClientAccessibilityMode"}
  LDAP-DESC                 "whether standard client should operate in accessibility Mode"
  ID                        id-at-zimbraPrefStandardClientAccessibilityMode }

zimbraPrefTagTreeOpen ATTRIBUTE ::= {
  WITH SYNTAX               BOOLEAN
  EQUALITY MATCHING RULE    booleanMatch
  SINGLE VALUE              TRUE
  LDAP-SYNTAX               boolean.&id
  LDAP-NAME                 {"zimbraPrefTagTreeOpen"}
  LDAP-DESC                 "whether or not tag tree is expanded"
  ID                        id-at-zimbraPrefTagTreeOpen }

-- LDAP syntax length {32} rendered as DirectoryString{32}.
zimbraPrefTasksFilterBy ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraPrefTasksFilterBy"}
  LDAP-DESC                 "preferred task filtering option in UI"
  ID                        id-at-zimbraPrefTasksFilterBy }

-- LDAP syntax length {32} rendered as DirectoryString{32}.
zimbraPrefTasksReadingPaneLocation ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraPrefTasksReadingPaneLocation"}
  LDAP-DESC                 "where the reading pane is displayed for tasks"
  ID                        id-at-zimbraPrefTasksReadingPaneLocation }

-- LDAP syntax length {256} rendered as DirectoryString{256}.
zimbraPrefTimeZoneId ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraPrefTimeZoneId"}
  LDAP-DESC                 "time zone of user or COS"
  ID                        id-at-zimbraPrefTimeZoneId }

zimbraPrefTrashLifetime ATTRIBUTE ::= {
  WITH SYNTAX               IA5String(SIZE (1..32))
  EQUALITY MATCHING RULE    caseIgnoreIA5Match
  SINGLE VALUE              TRUE
  LDAP-SYNTAX               ia5String.&id
  LDAP-NAME                 {"zimbraPrefTrashLifetime"}
  LDAP-DESC                 "Retention period of messages in the Trash folder. 0 means that all messages will be retained. This user-modifiable attribute works in conjunction with zimbraMailTrashLifetime, which is admin-modifiable. The shorter duration is used. . Must be in valid duration format: {digits}{time-unit}. digits: 0-9, time-unit: [hmsd]|ms. h - hours, m - minutes, s - seconds, d - days, ms - milliseconds. If time unit is not specified, the default is s(seconds)."
  ID                        id-at-zimbraPrefTrashLifetime }

zimbraPrefUseDefaultIdentitySettings ATTRIBUTE ::= {
  WITH SYNTAX               BOOLEAN
  EQUALITY MATCHING RULE    booleanMatch
  SINGLE VALUE              TRUE
  LDAP-SYNTAX               boolean.&id
  LDAP-NAME                 {"zimbraPrefUseDefaultIdentitySettings"}
  LDAP-DESC                 "Deprecated since: 5.0. no longer used in account or identity. Orig desc: TRUE if we this identity should get settings from the default identity"
  ID                        id-at-zimbraPrefUseDefaultIdentitySettings }

zimbraPrefUseKeyboardShortcuts ATTRIBUTE ::= {
  WITH SYNTAX               BOOLEAN
  EQUALITY MATCHING RULE    booleanMatch
  SINGLE VALUE              TRUE
  LDAP-SYNTAX               boolean.&id
  LDAP-NAME                 {"zimbraPrefUseKeyboardShortcuts"}
  LDAP-DESC                 "whether or not keyboard shortcuts are enabled"
  ID                        id-at-zimbraPrefUseKeyboardShortcuts }

zimbraPrefUseRfc2231 ATTRIBUTE ::= {
  WITH SYNTAX               BOOLEAN
  EQUALITY MATCHING RULE    booleanMatch
  SINGLE VALUE              TRUE
  LDAP-SYNTAX               boolean.&id
  LDAP-NAME                 {"zimbraPrefUseRfc2231"}
  LDAP-DESC                 "When composing and sending mail, whether to use RFC 2231 MIME parameter value encoding. If set to FALSE, then RFC 2047 style encoding is used."
  ID                        id-at-zimbraPrefUseRfc2231 }

zimbraPrefUseSendMsgShortcut ATTRIBUTE ::= {
  WITH SYNTAX               BOOLEAN
  EQUALITY MATCHING RULE    booleanMatch
  SINGLE VALUE              TRUE
  LDAP-SYNTAX               boolean.&id
  LDAP-NAME                 {"zimbraPrefUseSendMsgShortcut"}
  LDAP-DESC                 "Whether to allow the send message Control-Enter shortcut in the web client UI"
  ID                        id-at-zimbraPrefUseSendMsgShortcut }

zimbraPrefUseTimeZoneListInCalendar ATTRIBUTE ::= {
  WITH SYNTAX               BOOLEAN
  EQUALITY MATCHING RULE    booleanMatch
  SINGLE VALUE              TRUE
  LDAP-SYNTAX               boolean.&id
  LDAP-NAME                 {"zimbraPrefUseTimeZoneListInCalendar"}
  LDAP-DESC                 "whether list of well known time zones is displayed in calendar UI"
  ID                        id-at-zimbraPrefUseTimeZoneListInCalendar }

zimbraPrefVoiceItemsPerPage ATTRIBUTE ::= {
  WITH SYNTAX               INTEGER
  EQUALITY MATCHING RULE    integerMatch
  SINGLE VALUE              TRUE
  LDAP-SYNTAX               integer.&id
  LDAP-NAME                 {"zimbraPrefVoiceItemsPerPage"}
  LDAP-DESC                 "number of voice messages/call logs per page"
  ID                        id-at-zimbraPrefVoiceItemsPerPage }

zimbraPrefWarnOnExit ATTRIBUTE ::= {
  WITH SYNTAX               BOOLEAN
  EQUALITY MATCHING RULE    booleanMatch
  SINGLE VALUE              TRUE
  LDAP-SYNTAX               boolean.&id
  LDAP-NAME                 {"zimbraPrefWarnOnExit"}
  LDAP-DESC                 "whether to display a warning when users try to navigate away from ZCS"
  ID                        id-at-zimbraPrefWarnOnExit }

zimbraPrefWebClientOfflineBrowserKey ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraPrefWebClientOfflineBrowserKey"}
  LDAP-DESC                 "set of known keys corresponding to browsers used by the user for web client offline access"
  ID                        id-at-zimbraPrefWebClientOfflineBrowserKey }

-- LDAP syntax length {512} rendered as DirectoryString{512}.
zimbraPrefWhenInFolderIds ATTRIBUTE ::= {
  WITH SYNTAX               DirectoryString{512}
  EQUALITY MATCHING RULE    caseIgnoreMatch
  SUBSTRINGS MATCHING RULE  caseIgnoreSubstringsMatch
  LDAP-SYNTAX               directoryString.&id
  LDAP-NAME                 {"zimbraPrefWhenInFolderIds"}
  LDAP-DESC                 "if replying/forwarding a message in this folder, use this identity (deprecatedSince 5.0 in account)"
  ID                        id-at-zimbraPrefWhenInFolderIds }

zimbraPrefWhenInFoldersEnabled ATTRIBUTE ::= {
  WITH SYNTAX               BOOLEAN
  EQUALITY MATCHING RULE    booleanMatch
  SINGLE VALUE              TRUE
  LDAP-SYNTAX               boolean.&id
  LDAP-NAME                 {"zimbraPrefWhenInFoldersEnabled"}
  LDAP-DESC                 "TRUE if we should look at zimbraPrefWhenInFolderIds (deprecatedSince 5.0 in account)"
  ID                        id-at-zimbraPrefWhenInFoldersEnabled }

-- LDAP syntax length {2048} rendered as DirectoryString{2048}.
zimbraPrefWhenSentToAddresses ATTRIBUTE ::= {
  WITH SYNTAX               DirectoryString{2048}
  EQUALITY MATCHING RULE    caseIgnoreMatch
  SUBSTRINGS MATCHING RULE  caseIgnoreSubstringsMatch
  LDAP-SYNTAX               directoryString.&id
  LDAP-NAME                 {"zimbraPrefWhenSentToAddresses"}
  LDAP-DESC                 "addresses that we will look at to see if we should use an identity (deprecatedSince 5.0 in account)"
  ID                        id-at-zimbraPrefWhenSentToAddresses }

zimbraPrefWhenSentToEnabled ATTRIBUTE ::= {
  WITH SYNTAX               BOOLEAN
  EQUALITY MATCHING RULE    booleanMatch
  SINGLE VALUE              TRUE
  LDAP-SYNTAX               boolean.&id
  LDAP-NAME                 {"zimbraPrefWhenSentToEnabled"}
  LDAP-DESC                 "TRUE if we should look at zimbraPrefWhenSentToAddresses (deprecatedSince 5.0 in account)"
  ID                        id-at-zimbraPrefWhenSentToEnabled }

zimbraPrefZimletTreeOpen ATTRIBUTE ::= {
  WITH SYNTAX               BOOLEAN
  EQUALITY MATCHING RULE    booleanMatch
  SINGLE VALUE              TRUE
  LDAP-SYNTAX               boolean.&id
  LDAP-NAME                 {"zimbraPrefZimletTreeOpen"}
  LDAP-DESC                 "whether or not zimlet tree is expanded"
  ID                        id-at-zimbraPrefZimletTreeOpen }

zimbraPrefZimlets ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraPrefZimlets"}
  LDAP-DESC                 "zimlets user wants to see in the UI"
  ID                        id-at-zimbraPrefZimlets }

zimbraPrevFoldersToTrackMax ATTRIBUTE ::= {
  WITH SYNTAX               INTEGER
  EQUALITY MATCHING RULE    integerMatch
  SINGLE VALUE              TRUE
  LDAP-SYNTAX               integer.&id
  LDAP-NAME                 {"zimbraPrevFoldersToTrackMax"}
  LDAP-DESC                 "Max number of previous residing folders server tracks for a mail item"
  ID                        id-at-zimbraPrevFoldersToTrackMax }

-- LDAP syntax length {32} rendered as DirectoryString{32}.
zimbraProduct ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraProduct"}
  LDAP-DESC                 "whether this instance of Zimbra is running ZCS or some other derivative product"
  ID                        id-at-zimbraProduct }

-- LDAP syntax length {256} rendered as DirectoryString{256}.
zimbraProxyAllowedDomains ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraProxyAllowedDomains"}
  LDAP-DESC                 "Allowed domains for Proxy servlet"
  ID                        id-at-zimbraProxyAllowedDomains }

-- LDAP syntax length {256} rendered as DirectoryString{256}.
zimbraProxyCacheableContentTypes ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraProxyCacheableContentTypes"}
  LDAP-DESC                 "Deprecated since: 7.2.1. Deprecated per bug 74769. Orig desc: Content types that can be cached by proxy servlet"
  ID                        id-at-zimbraProxyCacheableContentTypes }

-- LDAP syntax length {256} rendered as DirectoryString{256}.
zimbraPublicServiceHostname ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraPublicServiceHostname"}
  LDAP-DESC                 "Name to be used in public API such as REST or SOAP proxy."
  ID                        id-at-zimbraPublicServiceHostname }

zimbraPublicServicePort ATTRIBUTE ::= {
  WITH SYNTAX               INTEGER
  EQUALITY MATCHING RULE    integerMatch
  SINGLE VALUE              TRUE
  LDAP-SYNTAX               integer.&id
  LDAP-NAME                 {"zimbraPublicServicePort"}
  LDAP-DESC                 "Port to be used in public API such as REST or SOAP proxy."
  ID                        id-at-zimbraPublicServicePort }

-- LDAP syntax length {256} rendered as DirectoryString{256}.
zimbraPublicServiceProtocol ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraPublicServiceProtocol"}
  LDAP-DESC                 "Protocol to be used in public API such as REST or SOAP proxy."
  ID                        id-at-zimbraPublicServiceProtocol }

zimbraPublicShareLifetime ATTRIBUTE ::= {
  WITH SYNTAX               IA5String(SIZE (1..32))
  EQUALITY MATCHING RULE    caseIgnoreIA5Match
  SINGLE VALUE              TRUE
  LDAP-SYNTAX               ia5String.&id
  LDAP-NAME                 {"zimbraPublicShareLifetime"}
  LDAP-DESC                 "Maximum allowed lifetime of public shares. A value of 0 indicates that there's no limit on a public share's lifetime. . Must be in valid duration format: {digits}{time-unit}. digits: 0-9, time-unit: [hmsd]|ms. h - hours, m - minutes, s - seconds, d - days, ms - milliseconds. If time unit is not specified, the default is s(seconds)."
  ID                        id-at-zimbraPublicShareLifetime }

zimbraPublicSharingEnabled ATTRIBUTE ::= {
  WITH SYNTAX               BOOLEAN
  EQUALITY MATCHING RULE    booleanMatch
  SINGLE VALUE              TRUE
  LDAP-SYNTAX               boolean.&id
  LDAP-NAME                 {"zimbraPublicSharingEnabled"}
  LDAP-DESC                 "switch for turning public sharing on/off"
  ID                        id-at-zimbraPublicSharingEnabled }

zimbraQuotaLastWarnTime ATTRIBUTE ::= {
  WITH SYNTAX               GeneralizedTime
  EQUALITY MATCHING RULE    generalizedTimeMatch
  ORDERING MATCHING RULE    generalizedTimeOrderingMatch
  SINGLE VALUE              TRUE
  LDAP-SYNTAX               generalizedTime.&id
  LDAP-NAME                 {"zimbraQuotaLastWarnTime"}
  LDAP-DESC                 "Last time a quota warning was sent."
  ID                        id-at-zimbraQuotaLastWarnTime }

zimbraQuotaWarnInterval ATTRIBUTE ::= {
  WITH SYNTAX               IA5String(SIZE (1..32))
  EQUALITY MATCHING RULE    caseIgnoreIA5Match
  SINGLE VALUE              TRUE
  LDAP-SYNTAX               ia5String.&id
  LDAP-NAME                 {"zimbraQuotaWarnInterval"}
  LDAP-DESC                 "Minimum duration of time between quota warnings.. Must be in valid duration format: {digits}{time-unit}. digits: 0-9, time-unit: [hmsd]|ms. h - hours, m - minutes, s - seconds, d - days, ms - milliseconds. If time unit is not specified, the default is s(seconds)."
  ID                        id-at-zimbraQuotaWarnInterval }

-- LDAP syntax length {10000} rendered as DirectoryString{10000}.
zimbraQuotaWarnMessage ATTRIBUTE ::= {
  WITH SYNTAX               DirectoryString{10000}
  EQUALITY MATCHING RULE    caseIgnoreMatch
  SUBSTRINGS MATCHING RULE  caseIgnoreSubstringsMatch
  SINGLE VALUE              TRUE
  LDAP-SYNTAX               directoryString.&id
  LDAP-NAME                 {"zimbraQuotaWarnMessage"}
  LDAP-DESC                 "Quota warning message template."
  ID                        id-at-zimbraQuotaWarnMessage }

zimbraQuotaWarnPercent ATTRIBUTE ::= {
  WITH SYNTAX               INTEGER
  EQUALITY MATCHING RULE    integerMatch
  SINGLE VALUE              TRUE
  LDAP-SYNTAX               integer.&id
  LDAP-NAME                 {"zimbraQuotaWarnPercent"}
  LDAP-DESC                 "Threshold for quota warning messages."
  ID                        id-at-zimbraQuotaWarnPercent }

-- LDAP syntax length {256} rendered as DirectoryString{256}.
zimbraRedoLogArchiveDir ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraRedoLogArchiveDir"}
  LDAP-DESC                 "redolog rollover destination"
  ID                        id-at-zimbraRedoLogArchiveDir }

zimbraRedoLogCrashRecoveryLookbackSec ATTRIBUTE ::= {
  WITH SYNTAX               INTEGER
  EQUALITY MATCHING RULE    integerMatch
  SINGLE VALUE              TRUE
  LDAP-SYNTAX               integer.&id
  LDAP-NAME                 {"zimbraRedoLogCrashRecoveryLookbackSec"}
  LDAP-DESC                 "how many seconds worth of committed redo ops to re-execute during crash recovery; related to mysql parameter innodb_flush_log_at_trx_commit=0"
  ID                        id-at-zimbraRedoLogCrashRecoveryLookbackSec }

zimbraRedoLogDeleteOnRollover ATTRIBUTE ::= {
  WITH SYNTAX               BOOLEAN
  EQUALITY MATCHING RULE    booleanMatch
  SINGLE VALUE              TRUE
  LDAP-SYNTAX               boolean.&id
  LDAP-NAME                 {"zimbraRedoLogDeleteOnRollover"}
  LDAP-DESC                 "whether logs are delete on rollover or archived"
  ID                        id-at-zimbraRedoLogDeleteOnRollover }

zimbraRedoLogEnabled ATTRIBUTE ::= {
  WITH SYNTAX               BOOLEAN
  EQUALITY MATCHING RULE    booleanMatch
  SINGLE VALUE              TRUE
  LDAP-SYNTAX               boolean.&id
  LDAP-NAME                 {"zimbraRedoLogEnabled"}
  LDAP-DESC                 "whether redo logging is enabled"
  ID                        id-at-zimbraRedoLogEnabled }

zimbraRedoLogFsyncIntervalMS ATTRIBUTE ::= {
  WITH SYNTAX               INTEGER
  EQUALITY MATCHING RULE    integerMatch
  SINGLE VALUE              TRUE
  LDAP-SYNTAX               integer.&id
  LDAP-NAME                 {"zimbraRedoLogFsyncIntervalMS"}
  LDAP-DESC                 "how frequently writes to redo log get fsynced to disk"
  ID                        id-at-zimbraRedoLogFsyncIntervalMS }

-- LDAP syntax length {256} rendered as DirectoryString{256}.
zimbraRedoLogLogPath ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraRedoLogLogPath"}
  LDAP-DESC                 "name and location of the redolog file"
  ID                        id-at-zimbraRedoLogLogPath }

-- LDAP syntax length {256} rendered as DirectoryString{256}.
zimbraRedoLogProvider ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraRedoLogProvider"}
  LDAP-DESC                 "provider class name for redo logging"
  ID                        id-at-zimbraRedoLogProvider }

zimbraRedoLogRolloverFileSizeKB ATTRIBUTE ::= {
  WITH SYNTAX               INTEGER
  EQUALITY MATCHING RULE    integerMatch
  SINGLE VALUE              TRUE
  LDAP-SYNTAX               integer.&id
  LDAP-NAME                 {"zimbraRedoLogRolloverFileSizeKB"}
  LDAP-DESC                 "redo.log file becomes eligible for rollover over when it goes over this size"
  ID                        id-at-zimbraRedoLogRolloverFileSizeKB }

zimbraRedoLogRolloverHardMaxFileSizeKB ATTRIBUTE ::= {
  WITH SYNTAX               INTEGER
  EQUALITY MATCHING RULE    integerMatch
  SINGLE VALUE              TRUE
  LDAP-SYNTAX               integer.&id
  LDAP-NAME                 {"zimbraRedoLogRolloverHardMaxFileSizeKB"}
  LDAP-DESC                 "redo.log file rolls over when it goes over this size, even if it does not meet the minimum file age requirement"
  ID                        id-at-zimbraRedoLogRolloverHardMaxFileSizeKB }

zimbraRedoLogRolloverMinFileAge ATTRIBUTE ::= {
  WITH SYNTAX               INTEGER
  EQUALITY MATCHING RULE    integerMatch
  SINGLE VALUE              TRUE
  LDAP-SYNTAX               integer.&id
  LDAP-NAME                 {"zimbraRedoLogRolloverMinFileAge"}
  LDAP-DESC                 "minimum age in minutes for redo.log file before it becomes eligible for rollover based on size"
  ID                        id-at-zimbraRedoLogRolloverMinFileAge }

zimbraRegexMaxAccessesWhenMatching ATTRIBUTE ::= {
  WITH SYNTAX               INTEGER
  EQUALITY MATCHING RULE    integerMatch
  SINGLE VALUE              TRUE
  LDAP-SYNTAX               integer.&id
  LDAP-NAME                 {"zimbraRegexMaxAccessesWhenMatching"}
  LDAP-DESC                 "This attribute is used to limit the amount of computation allowed when matching regex expressions. For example as part of the IMAP LIST command. Set to a higher value if legitimate IMAP list commands fail throwing TooManyAccessesToMatchTargetException."
  ID                        id-at-zimbraRegexMaxAccessesWhenMatching }

zimbraRemoteManagementCommand ATTRIBUTE ::= {
  WITH SYNTAX               IA5String(SIZE (1..1024))
  EQUALITY MATCHING RULE    caseIgnoreIA5Match
  SUBSTRINGS MATCHING RULE  caseIgnoreSubstringsMatch
  SINGLE VALUE              TRUE
  LDAP-SYNTAX               ia5String.&id
  LDAP-NAME                 {"zimbraRemoteManagementCommand"}
  LDAP-DESC                 "Path to remote management command to execute on this server"
  ID                        id-at-zimbraRemoteManagementCommand }

zimbraRemoteManagementPort ATTRIBUTE ::= {
  WITH SYNTAX               INTEGER
  EQUALITY MATCHING RULE    integerMatch
  SINGLE VALUE              TRUE
  LDAP-SYNTAX               integer.&id
  LDAP-NAME                 {"zimbraRemoteManagementPort"}
  LDAP-DESC                 "Port on which remote management sshd listening on this server."
  ID                        id-at-zimbraRemoteManagementPort }

zimbraRemoteManagementPrivateKeyPath ATTRIBUTE ::= {
  WITH SYNTAX               IA5String(SIZE (1..1024))
  EQUALITY MATCHING RULE    caseIgnoreIA5Match
  SUBSTRINGS MATCHING RULE  caseIgnoreSubstringsMatch
  SINGLE VALUE              TRUE
  LDAP-SYNTAX               ia5String.&id
  LDAP-NAME                 {"zimbraRemoteManagementPrivateKeyPath"}
  LDAP-DESC                 "Private key this server should use to access another server"
  ID                        id-at-zimbraRemoteManagementPrivateKeyPath }

zimbraRemoteManagementUser ATTRIBUTE ::= {
  WITH SYNTAX               IA5String(SIZE (1..256))
  EQUALITY MATCHING RULE    caseIgnoreIA5Match
  SUBSTRINGS MATCHING RULE  caseIgnoreSubstringsMatch
  SINGLE VALUE              TRUE
  LDAP-SYNTAX               ia5String.&id
  LDAP-NAME                 {"zimbraRemoteManagementUser"}
  LDAP-DESC                 "Login name of user allowed to execute remote management command"
  ID                        id-at-zimbraRemoteManagementUser }

zimbraResponseHeader ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraResponseHeader"}
  LDAP-DESC                 "Custom response headers. For example, can be used to add a P3P header for user agents to understand the sites privacy policy. Note: the value MUST be the entire header line (e.g. X-Foo: Bar)."
  ID                        id-at-zimbraResponseHeader }

-- LDAP syntax length {32} rendered as DirectoryString{32}.
zimbraReverseProxyAcceptMutex ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraReverseProxyAcceptMutex"}
  LDAP-DESC                 "on - accept_mutex flag 'on' for the reverse proxy. This is default. off - accept_mutex flag 'off' for the reverse proxy. Turning it off will get much better distribution of client connections between workers."
  ID                        id-at-zimbraReverseProxyAcceptMutex }

zimbraReverseProxyAdminEnabled ATTRIBUTE ::= {
  WITH SYNTAX               BOOLEAN
  EQUALITY MATCHING RULE    booleanMatch
  SINGLE VALUE              TRUE
  LDAP-SYNTAX               boolean.&id
  LDAP-NAME                 {"zimbraReverseProxyAdminEnabled"}
  LDAP-DESC                 "indicate whether to turn on admin console proxy"
  ID                        id-at-zimbraReverseProxyAdminEnabled }

zimbraReverseProxyAdminIPAddress ATTRIBUTE ::= {
  WITH SYNTAX               IA5String(SIZE (1..256))
  EQUALITY MATCHING RULE    caseIgnoreIA5Match
  SUBSTRINGS MATCHING RULE  caseIgnoreSubstringsMatch
  LDAP-SYNTAX               ia5String.&id
  LDAP-NAME                 {"zimbraReverseProxyAdminIPAddress"}
  LDAP-DESC                 "Allowed reverse proxy IP addresses. Lookup servlet will only generate authtokens if request was made from one of these IP addresses"
  ID                        id-at-zimbraReverseProxyAdminIPAddress }

zimbraReverseProxyAdminPortAttribute ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraReverseProxyAdminPortAttribute"}
  LDAP-DESC                 "the attribute that identifies the zimbra admin bind port"
  ID                        id-at-zimbraReverseProxyAdminPortAttribute }

zimbraReverseProxyAuthWaitInterval ATTRIBUTE ::= {
  WITH SYNTAX               IA5String(SIZE (1..32))
  EQUALITY MATCHING RULE    caseIgnoreIA5Match
  SINGLE VALUE              TRUE
  LDAP-SYNTAX               ia5String.&id
  LDAP-NAME                 {"zimbraReverseProxyAuthWaitInterval"}
  LDAP-DESC                 "wait duration before nginx sending back the NO response for failed imap/pop3 reverse proxy lookups. Must be in valid duration format: {digits}{time-unit}. digits: 0-9, time-unit: [hmsd]|ms. h - hours, m - minutes, s - seconds, d - days, ms - milliseconds. If time unit is not specified, the default is s(seconds)."
  ID                        id-at-zimbraReverseProxyAuthWaitInterval }

zimbraReverseProxyAvailableLookupTargets ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraReverseProxyAvailableLookupTargets"}
  LDAP-DESC                 "The servers to be included in the proxy lookup handlers list. Proxy will only use the servers specified here to do the lookup. Leaving empty means using all the servers whose zimbraReverseProxyLookupTarget is TRUE."
  ID                        id-at-zimbraReverseProxyAvailableLookupTargets }

zimbraReverseProxyCacheEntryTTL ATTRIBUTE ::= {
  WITH SYNTAX               IA5String(SIZE (1..32))
  EQUALITY MATCHING RULE    caseIgnoreIA5Match
  SINGLE VALUE              TRUE
  LDAP-SYNTAX               ia5String.&id
  LDAP-NAME                 {"zimbraReverseProxyCacheEntryTTL"}
  LDAP-DESC                 "time interval that an entry cached by NGINX will remain in the cache. Must be in valid duration format: {digits}{time-unit}. digits: 0-9, time-unit: [hmsd]|ms. h - hours, m - minutes, s - seconds, d - days, ms - milliseconds. If time unit is not specified, the default is s(seconds)."
  ID                        id-at-zimbraReverseProxyCacheEntryTTL }

zimbraReverseProxyCacheFetchTimeout ATTRIBUTE ::= {
  WITH SYNTAX               IA5String(SIZE (1..32))
  EQUALITY MATCHING RULE    caseIgnoreIA5Match
  SINGLE VALUE              TRUE
  LDAP-SYNTAX               ia5String.&id
  LDAP-NAME                 {"zimbraReverseProxyCacheFetchTimeout"}
  LDAP-DESC                 "time interval that NGINX proxy will wait for a cache result, before considering the result as a cache miss. Must be in valid duration format: {digits}{time-unit}. digits: 0-9, time-unit: [hmsd]|ms. h - hours, m - minutes, s - seconds, d - days, ms - milliseconds. If time unit is not specified, the default is s(seconds)."
  ID                        id-at-zimbraReverseProxyCacheFetchTimeout }

zimbraReverseProxyCacheReconnectInterval ATTRIBUTE ::= {
  WITH SYNTAX               IA5String(SIZE (1..32))
  EQUALITY MATCHING RULE    caseIgnoreIA5Match
  SINGLE VALUE              TRUE
  LDAP-SYNTAX               ia5String.&id
  LDAP-NAME                 {"zimbraReverseProxyCacheReconnectInterval"}
  LDAP-DESC                 "time interval that NGINX proxy will wait before attempting to re-establish a connection to a memcache server that disconnected. Must be in valid duration format: {digits}{time-unit}. digits: 0-9, time-unit: [hmsd]|ms. h - hours, m - minutes, s - seconds, d - days, ms - milliseconds. If time unit is not specified, the default is s(seconds)."
  ID                        id-at-zimbraReverseProxyCacheReconnectInterval }

zimbraReverseProxyClientCertCA ATTRIBUTE ::= {
  WITH SYNTAX               IA5String
  EQUALITY MATCHING RULE    caseIgnoreIA5Match
  SUBSTRINGS MATCHING RULE  caseIgnoreSubstringsMatch
  SINGLE VALUE              TRUE
  LDAP-SYNTAX               ia5String.&id
  LDAP-NAME                 {"zimbraReverseProxyClientCertCA"}
  LDAP-DESC                 "CA certificate for authenticating client certificates in nginx proxy (https only)"
  ID                        id-at-zimbraReverseProxyClientCertCA }

-- LDAP syntax length {32} rendered as DirectoryString{32}.
zimbraReverseProxyClientCertMode ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraReverseProxyClientCertMode"}
  LDAP-DESC                 "enable authentication via X.509 Client Certificate in nginx proxy (https only)"
  ID                        id-at-zimbraReverseProxyClientCertMode }

zimbraReverseProxyConnectTimeout ATTRIBUTE ::= {
  WITH SYNTAX               IA5String(SIZE (1..32))
  EQUALITY MATCHING RULE    caseIgnoreIA5Match
  SINGLE VALUE              TRUE
  LDAP-SYNTAX               ia5String.&id
  LDAP-NAME                 {"zimbraReverseProxyConnectTimeout"}
  LDAP-DESC                 "Time interval after which NGINX mail proxy will disconnect while establishing an upstream IMAP/POP connection. Must be in valid duration format: {digits}{time-unit}. digits: 0-9, time-unit: [hmsd]|ms. h - hours, m - minutes, s - seconds, d - days, ms - milliseconds. If time unit is not specified, the default is s(seconds)."
  ID                        id-at-zimbraReverseProxyConnectTimeout }

zimbraReverseProxyDefaultRealm ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraReverseProxyDefaultRealm"}
  LDAP-DESC                 "The default realm that will be used by NGINX mail proxy, when the realm is not specified in GSSAPI Authentication"
  ID                        id-at-zimbraReverseProxyDefaultRealm }

zimbraReverseProxyDnsLookupInServerEnabled ATTRIBUTE ::= {
  WITH SYNTAX               BOOLEAN
  EQUALITY MATCHING RULE    booleanMatch
  SINGLE VALUE              TRUE
  LDAP-SYNTAX               boolean.&id
  LDAP-NAME                 {"zimbraReverseProxyDnsLookupInServerEnabled"}
  LDAP-DESC                 "Control whether force the server side do the DNS lookup and send the result IP back to proxy. If set false, the raw address configured (e.g. zimbraMailHost) is directly sent to proxy."
  ID                        id-at-zimbraReverseProxyDnsLookupInServerEnabled }

zimbraReverseProxyDomainNameAttribute ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraReverseProxyDomainNameAttribute"}
  LDAP-DESC                 "LDAP attribute that contains domain name for the domain"
  ID                        id-at-zimbraReverseProxyDomainNameAttribute }

zimbraReverseProxyDomainNameQuery ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraReverseProxyDomainNameQuery"}
  LDAP-DESC                 "LDAP query to find a domain"
  ID                        id-at-zimbraReverseProxyDomainNameQuery }

zimbraReverseProxyDomainNameSearchBase ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraReverseProxyDomainNameSearchBase"}
  LDAP-DESC                 "search base for zimbraReverseProxyDomainNameQuery"
  ID                        id-at-zimbraReverseProxyDomainNameSearchBase }

zimbraReverseProxyErrorHandlerURL ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraReverseProxyErrorHandlerURL"}
  LDAP-DESC                 "the URL of customized proxy error handler. If set, when errors happen in proxy, proxy will redirect to this URL with two paras - err: error code; up: the addr of upstream server connecting to which the error happens"
  ID                        id-at-zimbraReverseProxyErrorHandlerURL }

-- LDAP syntax length {32} rendered as DirectoryString{32}.
zimbraReverseProxyExactServerVersionCheck ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraReverseProxyExactServerVersionCheck"}
  LDAP-DESC                 "Whether nginx will match exact server version against the version received in the client request (in ZM_AUTH_TOKEN). Defaults to on. Setting this to off will make nginx compare only the major and minor server versions (eg. all 8.5.x will be treated same by nginx)"
  ID                        id-at-zimbraReverseProxyExactServerVersionCheck }

zimbraReverseProxyExternalRouteIncludeOriginalAuthusername ATTRIBUTE ::= {
  WITH SYNTAX               BOOLEAN
  EQUALITY MATCHING RULE    booleanMatch
  SINGLE VALUE              TRUE
  LDAP-SYNTAX               boolean.&id
  LDAP-NAME                 {"zimbraReverseProxyExternalRouteIncludeOriginalAuthusername"}
  LDAP-DESC                 "During migrations Nginx lookup handler rewrites non-qualified username to fully qualified breaking proxy to external legacy mail platform. When zimbraReverseProxyUseExternalRoute is set to TRUE and zimbraReverseProxyExternalRouteIncludeOriginalAuthusername is set to FALSE nginx lookup handler drops the domain name from the userAccount and returns just the username."
  ID                        id-at-zimbraReverseProxyExternalRouteIncludeOriginalAuthusername }

zimbraReverseProxyGenConfigPerVirtualHostname ATTRIBUTE ::= {
  WITH SYNTAX               BOOLEAN
  EQUALITY MATCHING RULE    booleanMatch
  SINGLE VALUE              TRUE
  LDAP-SYNTAX               boolean.&id
  LDAP-NAME                 {"zimbraReverseProxyGenConfigPerVirtualHostname"}
  LDAP-DESC                 "Control whether to generate per virtual hostname nginx configuration. This would be helpful when multiple virtual host names are defined, but they are actually share the same configuration (like ssl cert, client CA, ...). This attr has to be set as ""TRUE"" to enable the features like cert per domain."
  ID                        id-at-zimbraReverseProxyGenConfigPerVirtualHostname }

zimbraReverseProxyHttpEnabled ATTRIBUTE ::= {
  WITH SYNTAX               BOOLEAN
  EQUALITY MATCHING RULE    booleanMatch
  SINGLE VALUE              TRUE
  LDAP-SYNTAX               boolean.&id
  LDAP-NAME                 {"zimbraReverseProxyHttpEnabled"}
  LDAP-DESC                 "Whether to enable HTTP proxy"
  ID                        id-at-zimbraReverseProxyHttpEnabled }

zimbraReverseProxyHttpPortAttribute ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraReverseProxyHttpPortAttribute"}
  LDAP-DESC                 "attribute that contains http bind port"
  ID                        id-at-zimbraReverseProxyHttpPortAttribute }

zimbraReverseProxyHttpSSLPortAttribute ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraReverseProxyHttpSSLPortAttribute"}
  LDAP-DESC                 "attribute that contains http ssl bind port"
  ID                        id-at-zimbraReverseProxyHttpSSLPortAttribute }

zimbraReverseProxyIPLoginLimit ATTRIBUTE ::= {
  WITH SYNTAX               INTEGER
  EQUALITY MATCHING RULE    integerMatch
  SINGLE VALUE              TRUE
  LDAP-SYNTAX               integer.&id
  LDAP-NAME                 {"zimbraReverseProxyIPLoginLimit"}
  LDAP-DESC                 "Sets the upper limit on logins from a remote IP via POP or IMAP to this proxy server after which login is rejected with an appropriate protocol specific bye response. This counter is cumulative for all users that appear to the proxy to be logging in from the same IP address. If multiple users appear to the proxy to be logging in from the same IP address (usual with NATing), then each of the different users login will contribute to increasing the hit counter for that IP address, and when the counter eventually exceeds the limit, then the connections from that IP address will be throttled. Therefore, all users from the same IP will contribute to (and be affected by) this counter. Logins using all protocols (POP3/POP3S/IMAP/IMAPS) will affect this counter (the counter is aggregate for all protocols, *not* separate). If this value is set to 0, then no limiting will take place for any IP."
  ID                        id-at-zimbraReverseProxyIPLoginLimit }

zimbraReverseProxyIPLoginLimitTime ATTRIBUTE ::= {
  WITH SYNTAX               INTEGER
  EQUALITY MATCHING RULE    integerMatch
  SINGLE VALUE              TRUE
  LDAP-SYNTAX               integer.&id
  LDAP-NAME                 {"zimbraReverseProxyIPLoginLimitTime"}
  LDAP-DESC                 "Sets the time-to-live for the hit counter for IP based login throttling. If time is set to 3600 and limit is set to 1000, then it means that NGINX should not allow more than 1000 users to log in via the proxy from the same IP, within the time interval of an hour. The semantics for such a configuration would then be: allow maximum 1000 users per hour from any given IP address."
  ID                        id-at-zimbraReverseProxyIPLoginLimitTime }

-- LDAP syntax length {256} rendered as DirectoryString{256}.
zimbraReverseProxyImapEnabledCapability ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraReverseProxyImapEnabledCapability"}
  LDAP-DESC                 "NGINX reverse proxy imap capabilities"
  ID                        id-at-zimbraReverseProxyImapEnabledCapability }

zimbraReverseProxyImapExposeVersionOnBanner ATTRIBUTE ::= {
  WITH SYNTAX               BOOLEAN
  EQUALITY MATCHING RULE    booleanMatch
  SINGLE VALUE              TRUE
  LDAP-SYNTAX               boolean.&id
  LDAP-NAME                 {"zimbraReverseProxyImapExposeVersionOnBanner"}
  LDAP-DESC                 "Whether to expose version on Proxy IMAP banner"
  ID                        id-at-zimbraReverseProxyImapExposeVersionOnBanner }

zimbraReverseProxyImapPortAttribute ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraReverseProxyImapPortAttribute"}
  LDAP-DESC                 "attribute that contains imap bind port"
  ID                        id-at-zimbraReverseProxyImapPortAttribute }

zimbraReverseProxyImapSSLPortAttribute ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraReverseProxyImapSSLPortAttribute"}
  LDAP-DESC                 "attribute that contains imap bind port for SSL"
  ID                        id-at-zimbraReverseProxyImapSSLPortAttribute }

zimbraReverseProxyImapSaslGssapiEnabled ATTRIBUTE ::= {
  WITH SYNTAX               BOOLEAN
  EQUALITY MATCHING RULE    booleanMatch
  SINGLE VALUE              TRUE
  LDAP-SYNTAX               boolean.&id
  LDAP-NAME                 {"zimbraReverseProxyImapSaslGssapiEnabled"}
  LDAP-DESC                 "whether IMAP SASL GSSAPI is enabled for reverse proxy"
  ID                        id-at-zimbraReverseProxyImapSaslGssapiEnabled }

zimbraReverseProxyImapSaslPlainEnabled ATTRIBUTE ::= {
  WITH SYNTAX               BOOLEAN
  EQUALITY MATCHING RULE    booleanMatch
  SINGLE VALUE              TRUE
  LDAP-SYNTAX               boolean.&id
  LDAP-NAME                 {"zimbraReverseProxyImapSaslPlainEnabled"}
  LDAP-DESC                 "whether IMAP SASL PLAIN is enabled for reverse proxy"
  ID                        id-at-zimbraReverseProxyImapSaslPlainEnabled }

-- LDAP syntax length {32} rendered as DirectoryString{32}.
zimbraReverseProxyImapStartTlsMode ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraReverseProxyImapStartTlsMode"}
  LDAP-DESC                 "on - on the plain POP/IMAP port, starttls is allowed off - no starttls is offered on plain port only - you have to use starttls before clear text login"
  ID                        id-at-zimbraReverseProxyImapStartTlsMode }

zimbraReverseProxyInactivityTimeout ATTRIBUTE ::= {
  WITH SYNTAX               IA5String(SIZE (1..32))
  EQUALITY MATCHING RULE    caseIgnoreIA5Match
  SINGLE VALUE              TRUE
  LDAP-SYNTAX               ia5String.&id
  LDAP-NAME                 {"zimbraReverseProxyInactivityTimeout"}
  LDAP-DESC                 "Deprecated since: 8.0.0. deprecated in favor of local config ""imap_max_idle_time"", ""pop3_max_idle_time"", ""imap_authenticated_max_idle_time"" in bug 59685. Orig desc: Time interval after which NGINX mail proxy will disconnect an inactive IMAP/POP connection. Must be in valid duration format: {digits}{time-unit}. digits: 0-9, time-unit: [hmsd]|ms. h - hours, m - minutes, s - seconds, d - days, ms - milliseconds. If time unit is not specified, the default is s(seconds)."
  ID                        id-at-zimbraReverseProxyInactivityTimeout }

zimbraReverseProxyIpThrottleMsg ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraReverseProxyIpThrottleMsg"}
  LDAP-DESC                 "The error message with which a connection attempt from an IP address will be throttled, if the connection count exceeds the configured limit"
  ID                        id-at-zimbraReverseProxyIpThrottleMsg }

-- LDAP syntax length {32} rendered as DirectoryString{32}.
zimbraReverseProxyLogLevel ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraReverseProxyLogLevel"}
  LDAP-DESC                 "Log level for NGINX Proxy error log"
  ID                        id-at-zimbraReverseProxyLogLevel }

zimbraReverseProxyLookupTarget ATTRIBUTE ::= {
  WITH SYNTAX               BOOLEAN
  EQUALITY MATCHING RULE    booleanMatch
  SINGLE VALUE              TRUE
  LDAP-SYNTAX               boolean.&id
  LDAP-NAME                 {"zimbraReverseProxyLookupTarget"}
  LDAP-DESC                 "whether this server is a reverse proxy lookup target"
  ID                        id-at-zimbraReverseProxyLookupTarget }

zimbraReverseProxyMailEnabled ATTRIBUTE ::= {
  WITH SYNTAX               BOOLEAN
  EQUALITY MATCHING RULE    booleanMatch
  SINGLE VALUE              TRUE
  LDAP-SYNTAX               boolean.&id
  LDAP-NAME                 {"zimbraReverseProxyMailEnabled"}
  LDAP-DESC                 "Whether to enable IMAP/POP proxy"
  ID                        id-at-zimbraReverseProxyMailEnabled }

zimbraReverseProxyMailHostAttribute ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraReverseProxyMailHostAttribute"}
  LDAP-DESC                 "LDAP attribute that contains mailhost for the user"
  ID                        id-at-zimbraReverseProxyMailHostAttribute }

zimbraReverseProxyMailHostQuery ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraReverseProxyMailHostQuery"}
  LDAP-DESC                 "LDAP query to find a user"
  ID                        id-at-zimbraReverseProxyMailHostQuery }

zimbraReverseProxyMailHostSearchBase ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraReverseProxyMailHostSearchBase"}
  LDAP-DESC                 "search base for zimbraReverseProxyMailHostQuery"
  ID                        id-at-zimbraReverseProxyMailHostSearchBase }

zimbraReverseProxyMailImapEnabled ATTRIBUTE ::= {
  WITH SYNTAX               BOOLEAN
  EQUALITY MATCHING RULE    booleanMatch
  SINGLE VALUE              TRUE
  LDAP-SYNTAX               boolean.&id
  LDAP-NAME                 {"zimbraReverseProxyMailImapEnabled"}
  LDAP-DESC                 "Whether to enable IMAP proxy"
  ID                        id-at-zimbraReverseProxyMailImapEnabled }

zimbraReverseProxyMailImapsEnabled ATTRIBUTE ::= {
  WITH SYNTAX               BOOLEAN
  EQUALITY MATCHING RULE    booleanMatch
  SINGLE VALUE              TRUE
  LDAP-SYNTAX               boolean.&id
  LDAP-NAME                 {"zimbraReverseProxyMailImapsEnabled"}
  LDAP-DESC                 "Whether to enable IMAPs proxy"
  ID                        id-at-zimbraReverseProxyMailImapsEnabled }

-- LDAP syntax length {32} rendered as DirectoryString{32}.
zimbraReverseProxyMailMode ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraReverseProxyMailMode"}
  LDAP-DESC                 "whether to run proxy in HTTP, HTTPS, both, mixed, or redirect mode. See also related attributes zimbraMailProxyPort and zimbraMailSSLProxyPort"
  ID                        id-at-zimbraReverseProxyMailMode }

zimbraReverseProxyMailPop3Enabled ATTRIBUTE ::= {
  WITH SYNTAX               BOOLEAN
  EQUALITY MATCHING RULE    booleanMatch
  SINGLE VALUE              TRUE
  LDAP-SYNTAX               boolean.&id
  LDAP-NAME                 {"zimbraReverseProxyMailPop3Enabled"}
  LDAP-DESC                 "Whether to enable Pop3 proxy"
  ID                        id-at-zimbraReverseProxyMailPop3Enabled }

zimbraReverseProxyMailPop3sEnabled ATTRIBUTE ::= {
  WITH SYNTAX               BOOLEAN
  EQUALITY MATCHING RULE    booleanMatch
  SINGLE VALUE              TRUE
  LDAP-SYNTAX               boolean.&id
  LDAP-NAME                 {"zimbraReverseProxyMailPop3sEnabled"}
  LDAP-DESC                 "Whether to enable Pop3s proxy"
  ID                        id-at-zimbraReverseProxyMailPop3sEnabled }

zimbraReverseProxyPassErrors ATTRIBUTE ::= {
  WITH SYNTAX               BOOLEAN
  EQUALITY MATCHING RULE    booleanMatch
  SINGLE VALUE              TRUE
  LDAP-SYNTAX               boolean.&id
  LDAP-NAME                 {"zimbraReverseProxyPassErrors"}
  LDAP-DESC                 "whether NGINX mail proxy will pass upstream server errors back to the downstream email clients"
  ID                        id-at-zimbraReverseProxyPassErrors }

-- LDAP syntax length {256} rendered as DirectoryString{256}.
zimbraReverseProxyPop3EnabledCapability ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraReverseProxyPop3EnabledCapability"}
  LDAP-DESC                 "NGINX reverse proxy pop3 capabilities"
  ID                        id-at-zimbraReverseProxyPop3EnabledCapability }

zimbraReverseProxyPop3ExposeVersionOnBanner ATTRIBUTE ::= {
  WITH SYNTAX               BOOLEAN
  EQUALITY MATCHING RULE    booleanMatch
  SINGLE VALUE              TRUE
  LDAP-SYNTAX               boolean.&id
  LDAP-NAME                 {"zimbraReverseProxyPop3ExposeVersionOnBanner"}
  LDAP-DESC                 "Whether to expose version on Proxy POP3 banner"
  ID                        id-at-zimbraReverseProxyPop3ExposeVersionOnBanner }

zimbraReverseProxyPop3PortAttribute ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraReverseProxyPop3PortAttribute"}
  LDAP-DESC                 "attribute that contains pop3 bind port"
  ID                        id-at-zimbraReverseProxyPop3PortAttribute }

zimbraReverseProxyPop3SSLPortAttribute ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraReverseProxyPop3SSLPortAttribute"}
  LDAP-DESC                 "attribute that contains pop3 bind port for SSL"
  ID                        id-at-zimbraReverseProxyPop3SSLPortAttribute }

zimbraReverseProxyPop3SaslGssapiEnabled ATTRIBUTE ::= {
  WITH SYNTAX               BOOLEAN
  EQUALITY MATCHING RULE    booleanMatch
  SINGLE VALUE              TRUE
  LDAP-SYNTAX               boolean.&id
  LDAP-NAME                 {"zimbraReverseProxyPop3SaslGssapiEnabled"}
  LDAP-DESC                 "whether POP3 SASL GSSAPI is enabled for reverse proxy"
  ID                        id-at-zimbraReverseProxyPop3SaslGssapiEnabled }

zimbraReverseProxyPop3SaslPlainEnabled ATTRIBUTE ::= {
  WITH SYNTAX               BOOLEAN
  EQUALITY MATCHING RULE    booleanMatch
  SINGLE VALUE              TRUE
  LDAP-SYNTAX               boolean.&id
  LDAP-NAME                 {"zimbraReverseProxyPop3SaslPlainEnabled"}
  LDAP-DESC                 "whether POP3 SASL PLAIN is enabled for reverse proxy"
  ID                        id-at-zimbraReverseProxyPop3SaslPlainEnabled }

-- LDAP syntax length {32} rendered as DirectoryString{32}.
zimbraReverseProxyPop3StartTlsMode ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraReverseProxyPop3StartTlsMode"}
  LDAP-DESC                 "on - on the plain POP/IMAP port, starttls is allowed off - no starttls is offered on plain port only - you have to use starttls before clear text login"
  ID                        id-at-zimbraReverseProxyPop3StartTlsMode }

zimbraReverseProxyPortQuery ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraReverseProxyPortQuery"}
  LDAP-DESC                 "LDAP query to find server object"
  ID                        id-at-zimbraReverseProxyPortQuery }

zimbraReverseProxyPortSearchBase ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraReverseProxyPortSearchBase"}
  LDAP-DESC                 "search base for zimbraReverseProxyPortQuery"
  ID                        id-at-zimbraReverseProxyPortSearchBase }

zimbraReverseProxyRouteLookupTimeout ATTRIBUTE ::= {
  WITH SYNTAX               IA5String(SIZE (1..32))
  EQUALITY MATCHING RULE    caseIgnoreIA5Match
  SINGLE VALUE              TRUE
  LDAP-SYNTAX               ia5String.&id
  LDAP-NAME                 {"zimbraReverseProxyRouteLookupTimeout"}
  LDAP-DESC                 "Time interval after which NGINX will fail over to the next route lookup handler, if a handler does not respond to the route lookup request within this time. Must be in valid duration format: {digits}{time-unit}. digits: 0-9, time-unit: [hmsd]|ms. h - hours, m - minutes, s - seconds, d - days, ms - milliseconds. If time unit is not specified, the default is s(seconds)."
  ID                        id-at-zimbraReverseProxyRouteLookupTimeout }

zimbraReverseProxyRouteLookupTimeoutCache ATTRIBUTE ::= {
  WITH SYNTAX               IA5String(SIZE (1..32))
  EQUALITY MATCHING RULE    caseIgnoreIA5Match
  SINGLE VALUE              TRUE
  LDAP-SYNTAX               ia5String.&id
  LDAP-NAME                 {"zimbraReverseProxyRouteLookupTimeoutCache"}
  LDAP-DESC                 "Time interval (ms) given to mail route lookup handler to cache a failed response to route a previous lookup request (after this time elapses, Proxy retries this host). Must be in valid duration format: {digits}{time-unit}. digits: 0-9, time-unit: [hmsd]|ms. h - hours, m - minutes, s - seconds, d - days, ms - milliseconds. If time unit is not specified, the default is s(seconds)."
  ID                        id-at-zimbraReverseProxyRouteLookupTimeoutCache }

zimbraReverseProxySSLCiphers ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraReverseProxySSLCiphers"}
  LDAP-DESC                 "permitted ciphers for reverse proxy. Ciphers are in the formats supported by OpenSSL e.g. ALL:!ADH:!EXPORT56:RC4+RSA:+HIGH:+MEDIUM:+LOW:+SSLv2:+EXP; if not set, default ciphers permitted by nginx will apply"
  ID                        id-at-zimbraReverseProxySSLCiphers }

zimbraReverseProxySSLECDHCurve ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraReverseProxySSLECDHCurve"}
  LDAP-DESC                 "SSL ECDH cipher curve for web proxy"
  ID                        id-at-zimbraReverseProxySSLECDHCurve }

zimbraReverseProxySSLProtocols ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraReverseProxySSLProtocols"}
  LDAP-DESC                 "SSL protocols enabled for the proxy"
  ID                        id-at-zimbraReverseProxySSLProtocols }

zimbraReverseProxySSLToUpstreamEnabled ATTRIBUTE ::= {
  WITH SYNTAX               BOOLEAN
  EQUALITY MATCHING RULE    booleanMatch
  SINGLE VALUE              TRUE
  LDAP-SYNTAX               boolean.&id
  LDAP-NAME                 {"zimbraReverseProxySSLToUpstreamEnabled"}
  LDAP-DESC                 "If set as TRUE, proxy will use SSL to connect to the upstream mail servers for web and mail proxy. Note admin console proxy always use https no matter how this attr is set."
  ID                        id-at-zimbraReverseProxySSLToUpstreamEnabled }

zimbraReverseProxySendImapId ATTRIBUTE ::= {
  WITH SYNTAX               BOOLEAN
  EQUALITY MATCHING RULE    booleanMatch
  SINGLE VALUE              TRUE
  LDAP-SYNTAX               boolean.&id
  LDAP-NAME                 {"zimbraReverseProxySendImapId"}
  LDAP-DESC                 "whether nginx should send ID command for imap"
  ID                        id-at-zimbraReverseProxySendImapId }

zimbraReverseProxySendPop3Xoip ATTRIBUTE ::= {
  WITH SYNTAX               BOOLEAN
  EQUALITY MATCHING RULE    booleanMatch
  SINGLE VALUE              TRUE
  LDAP-SYNTAX               boolean.&id
  LDAP-NAME                 {"zimbraReverseProxySendPop3Xoip"}
  LDAP-DESC                 "whether nginx should send XOIP command for pop3"
  ID                        id-at-zimbraReverseProxySendPop3Xoip }

zimbraReverseProxyUpstreamConnectTimeout ATTRIBUTE ::= {
  WITH SYNTAX               INTEGER
  EQUALITY MATCHING RULE    integerMatch
  SINGLE VALUE              TRUE
  LDAP-SYNTAX               integer.&id
  LDAP-NAME                 {"zimbraReverseProxyUpstreamConnectTimeout"}
  LDAP-DESC                 "The connect timeout is the time interval after which NGINX will disconnect while establishing an upstream HTTP connection. Measured in seconds, should not be more than 75 seconds."
  ID                        id-at-zimbraReverseProxyUpstreamConnectTimeout }

zimbraReverseProxyUpstreamEwsServers ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraReverseProxyUpstreamEwsServers"}
  LDAP-DESC                 "The servers running mailbox with EWS functionality to be included in the ""ews"" block in the nginx web proxy config file"
  ID                        id-at-zimbraReverseProxyUpstreamEwsServers }

zimbraReverseProxyUpstreamLoginServers ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraReverseProxyUpstreamLoginServers"}
  LDAP-DESC                 "The servers to be included in the login block in the nginx web proxy config file. The servers configured here will only affect the proxy of login URL requests."
  ID                        id-at-zimbraReverseProxyUpstreamLoginServers }

zimbraReverseProxyUpstreamPollingTimeout ATTRIBUTE ::= {
  WITH SYNTAX               IA5String(SIZE (1..32))
  EQUALITY MATCHING RULE    caseIgnoreIA5Match
  SINGLE VALUE              TRUE
  LDAP-SYNTAX               ia5String.&id
  LDAP-NAME                 {"zimbraReverseProxyUpstreamPollingTimeout"}
  LDAP-DESC                 "The read timeout for long polling support by proxy, e.g. ActiveSync for mobile devices. . Must be in valid duration format: {digits}{time-unit}. digits: 0-9, time-unit: [hmsd]|ms. h - hours, m - minutes, s - seconds, d - days, ms - milliseconds. If time unit is not specified, the default is s(seconds)."
  ID                        id-at-zimbraReverseProxyUpstreamPollingTimeout }

zimbraReverseProxyUpstreamReadTimeout ATTRIBUTE ::= {
  WITH SYNTAX               IA5String(SIZE (1..32))
  EQUALITY MATCHING RULE    caseIgnoreIA5Match
  SINGLE VALUE              TRUE
  LDAP-SYNTAX               ia5String.&id
  LDAP-NAME                 {"zimbraReverseProxyUpstreamReadTimeout"}
  LDAP-DESC                 "The read timeout for the response of upstream server, which determines how long nginx will wait to get the response to a request. . Must be in valid duration format: {digits}{time-unit}. digits: 0-9, time-unit: [hmsd]|ms. h - hours, m - minutes, s - seconds, d - days, ms - milliseconds. If time unit is not specified, the default is s(seconds)."
  ID                        id-at-zimbraReverseProxyUpstreamReadTimeout }

zimbraReverseProxyUpstreamSendTimeout ATTRIBUTE ::= {
  WITH SYNTAX               IA5String(SIZE (1..32))
  EQUALITY MATCHING RULE    caseIgnoreIA5Match
  SINGLE VALUE              TRUE
  LDAP-SYNTAX               ia5String.&id
  LDAP-NAME                 {"zimbraReverseProxyUpstreamSendTimeout"}
  LDAP-DESC                 "The send timeout of transfering a request to the upstream server. If after this time the upstream server doesn't take new data, proxy will close the connection. . Must be in valid duration format: {digits}{time-unit}. digits: 0-9, time-unit: [hmsd]|ms. h - hours, m - minutes, s - seconds, d - days, ms - milliseconds. If time unit is not specified, the default is s(seconds)."
  ID                        id-at-zimbraReverseProxyUpstreamSendTimeout }

zimbraReverseProxyUpstreamServers ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraReverseProxyUpstreamServers"}
  LDAP-DESC                 "The servers to be included in the ""upstream"" block in the nginx web proxy config file. The servers configured here will only affect the proxy of pre-login requests. Leaving empty means using all the servers whose zimbraReverseProxyLookupTarget is TRUE."
  ID                        id-at-zimbraReverseProxyUpstreamServers }

zimbraReverseProxyUseExternalRoute ATTRIBUTE ::= {
  WITH SYNTAX               BOOLEAN
  EQUALITY MATCHING RULE    booleanMatch
  SINGLE VALUE              TRUE
  LDAP-SYNTAX               boolean.&id
  LDAP-NAME                 {"zimbraReverseProxyUseExternalRoute"}
  LDAP-DESC                 "There is a deployment scenario for migrations where all of the customers users are pointed at the zimbra POP IMAP reverse proxy. We then want their connections proxied back to the legacy system for not-yet-non-migrated users. If this attribute is TRUE, reverse proxy lookup servlet should check to see if zimbraExternal* is set on the domain. If so it is used. If not, lookup proceeds as usual."
  ID                        id-at-zimbraReverseProxyUseExternalRoute }

zimbraReverseProxyUseExternalRouteIfAccountNotExist ATTRIBUTE ::= {
  WITH SYNTAX               BOOLEAN
  EQUALITY MATCHING RULE    booleanMatch
  SINGLE VALUE              TRUE
  LDAP-SYNTAX               boolean.&id
  LDAP-NAME                 {"zimbraReverseProxyUseExternalRouteIfAccountNotExist"}
  LDAP-DESC                 "Use external route configured on domain if account cannot be found. Also see zimbraReverseProxyUseExternalRoute."
  ID                        id-at-zimbraReverseProxyUseExternalRouteIfAccountNotExist }

zimbraReverseProxyUserLoginLimit ATTRIBUTE ::= {
  WITH SYNTAX               INTEGER
  EQUALITY MATCHING RULE    integerMatch
  SINGLE VALUE              TRUE
  LDAP-SYNTAX               integer.&id
  LDAP-NAME                 {"zimbraReverseProxyUserLoginLimit"}
  LDAP-DESC                 "Limit how many times a user can login via the proxy. Setting limit to 100 and time to 3600 means: allow maximum 100 logins per hour for any user. As with the ip counterparts, the user hit counter and timeout are cumulative for all protocols. Also, for a given users login, both counters are checked in succession, with the IP counter being checked first. A login may be rejected (throttled) because the IP is over-usage, or because the login name itself is over-usage. A value of 0 indicates that no throttling will take place for any user."
  ID                        id-at-zimbraReverseProxyUserLoginLimit }

zimbraReverseProxyUserLoginLimitTime ATTRIBUTE ::= {
  WITH SYNTAX               INTEGER
  EQUALITY MATCHING RULE    integerMatch
  SINGLE VALUE              TRUE
  LDAP-SYNTAX               integer.&id
  LDAP-NAME                 {"zimbraReverseProxyUserLoginLimitTime"}
  LDAP-DESC                 "Sets the time-to-live for the hit counter for per user login throttling."
  ID                        id-at-zimbraReverseProxyUserLoginLimitTime }

zimbraReverseProxyUserNameAttribute ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraReverseProxyUserNameAttribute"}
  LDAP-DESC                 "LDAP attribute that contains user name for the principal"
  ID                        id-at-zimbraReverseProxyUserNameAttribute }

zimbraReverseProxyUserThrottleMsg ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraReverseProxyUserThrottleMsg"}
  LDAP-DESC                 "The error message with which a login attempt by a user will be throttled, if the attempt count exceeds the configured limit"
  ID                        id-at-zimbraReverseProxyUserThrottleMsg }

zimbraReverseProxyWorkerConnections ATTRIBUTE ::= {
  WITH SYNTAX               INTEGER
  EQUALITY MATCHING RULE    integerMatch
  SINGLE VALUE              TRUE
  LDAP-SYNTAX               integer.&id
  LDAP-NAME                 {"zimbraReverseProxyWorkerConnections"}
  LDAP-DESC                 "Maximum number of connections that an NGINX Proxy worker process is allowed to handle"
  ID                        id-at-zimbraReverseProxyWorkerConnections }

zimbraReverseProxyWorkerProcesses ATTRIBUTE ::= {
  WITH SYNTAX               INTEGER
  EQUALITY MATCHING RULE    integerMatch
  SINGLE VALUE              TRUE
  LDAP-SYNTAX               integer.&id
  LDAP-NAME                 {"zimbraReverseProxyWorkerProcesses"}
  LDAP-DESC                 "Number of worker processes of NGINX Proxy"
  ID                        id-at-zimbraReverseProxyWorkerProcesses }

-- LDAP syntax length {256} rendered as DirectoryString{256}.
zimbraSMIMELdapAttribute ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraSMIMELdapAttribute"}
  LDAP-DESC                 "LDAP attribute(s) for public key lookup for S/MIME via external LDAP. Multiple attributes can be separated by comma. All SMIME attributes are in the format of {config-name}:{value}. A 'SMIME config' is a set of SMIME attribute values with the same {config-name}. Multiple SMIME configs can be configured on a domain or on globalconfig. Note: SMIME attributes on domains do not inherited values from globalconfig, they are not domain-inherited attributes. During SMIME public key lookup, if there are any SMIME config on the domain of the account, they are used. SMIME configs on globalconfig will be used only when there is no SMIME config on the domain. SMIME attributes cannot be modified directly with zmprov md/mcf commands. Use zmprov gcsc/gdsc/mcsc/mdsc/rcsc/rdsc command instead."
  ID                        id-at-zimbraSMIMELdapAttribute }

-- LDAP syntax length {256} rendered as DirectoryString{256}.
zimbraSMIMELdapBindDn ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraSMIMELdapBindDn"}
  LDAP-DESC                 "LDAP bind DN for public key lookup for S/MIME via external LDAP. Can be empty for anonymous bind. All SMIME attributes are in the format of {config-name}:{value}. A 'SMIME config' is a set of SMIME attribute values with the same {config-name}. Multiple SMIME configs can be configured on a domain or on globalconfig. Note: SMIME attributes on domains do not inherited values from globalconfig, they are not domain-inherited attributes. During SMIME public key lookup, if there are any SMIME config on the domain of the account, they are used. SMIME configs on globalconfig will be used only when there is no SMIME config on the domain. SMIME attributes cannot be modified directly with zmprov md/mcf commands. Use zmprov gcsc/gdsc/mcsc/mdsc/rcsc/rdsc command instead."
  ID                        id-at-zimbraSMIMELdapBindDn }

-- LDAP syntax length {256} rendered as DirectoryString{256}.
zimbraSMIMELdapBindPassword ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraSMIMELdapBindPassword"}
  LDAP-DESC                 "LDAP bind password for public key lookup for S/MIME via external LDAP. Can be empty for anonymous bind. All SMIME attributes are in the format of {config-name}:{value}. A 'SMIME config' is a set of SMIME attribute values with the same {config-name}. Multiple SMIME configs can be configured on a domain or on globalconfig. Note: SMIME attributes on domains do not inherited values from globalconfig, they are not domain-inherited attributes. During SMIME public key lookup, if there are any SMIME config on the domain of the account, they are used. SMIME configs on globalconfig will be used only when there is no SMIME config on the domain. SMIME attributes cannot be modified directly with zmprov md/mcf commands. Use zmprov gcsc/gdsc/mcsc/mdsc/rcsc/rdsc command instead."
  ID                        id-at-zimbraSMIMELdapBindPassword }

-- LDAP syntax length {32} rendered as DirectoryString{32}.
zimbraSMIMELdapDiscoverSearchBaseEnabled ATTRIBUTE ::= {
  WITH SYNTAX               DirectoryString{32}
  EQUALITY MATCHING RULE    caseIgnoreMatch
  SUBSTRINGS MATCHING RULE  caseIgnoreSubstringsMatch
  LDAP-SYNTAX               directoryString.&id
  LDAP-NAME                 {"zimbraSMIMELdapDiscoverSearchBaseEnabled"}
  LDAP-DESC                 "Whether or not to discover search base DNs if zimbraSMIMELdapSearchBase is not set. Allowed values are TRUE or FALSE. If zimbraSMIMELdapSearchBase is set for a config, this attribute is ignored for the config. If not set, default for the config is FALSE. In that case, if zimbraSMIMELdapSearchBase is not set, the search will default to the rootDSE. If multiple DNs are discovered, the ldap search will use them one by one until a hit is returned. All SMIME attributes are in the format of {config-name}:{value}. A 'SMIME config' is a set of SMIME attribute values with the same {config-name}. Multiple SMIME configs can be configured on a domain or on globalconfig. Note: SMIME attributes on domains do not inherited values from globalconfig, they are not domain-inherited attributes. During SMIME public key lookup, if there are any SMIME config on the domain of the account, they are used. SMIME configs on globalconfig will be used only when there is no SMIME config on the domain. SMIME attributes cannot be modified directly with zmprov md/mcf commands. Use zmprov gcsc/gdsc/mcsc/mdsc/rcsc/rdsc command instead."
  ID                        id-at-zimbraSMIMELdapDiscoverSearchBaseEnabled }

-- LDAP syntax length {1024} rendered as DirectoryString{1024}.
zimbraSMIMELdapFilter ATTRIBUTE ::= {
  WITH SYNTAX               DirectoryString{1024}
  EQUALITY MATCHING RULE    caseIgnoreMatch
  SUBSTRINGS MATCHING RULE  caseIgnoreSubstringsMatch
  LDAP-SYNTAX               directoryString.&id
  LDAP-NAME                 {"zimbraSMIMELdapFilter"}
  LDAP-DESC                 "LDAP search filter for public key lookup for S/MIME via external LDAP. Can contain the following conversion variables for expansion: %n - search key with @ (or without, if no @ was specified) %u - with @ removed e.g. (mail=%n) All SMIME attributes are in the format of {config-name}:{value}. A 'SMIME config' is a set of SMIME attribute values with the same {config-name}. Multiple SMIME configs can be configured on a domain or on globalconfig. Note: SMIME attributes on domains do not inherited values from globalconfig, they are not domain-inherited attributes. During SMIME public key lookup, if there are any SMIME config on the domain of the account, they are used. SMIME configs on globalconfig will be used only when there is no SMIME config on the domain. SMIME attributes cannot be modified directly with zmprov md/mcf commands. Use zmprov gcsc/gdsc/mcsc/mdsc/rcsc/rdsc command instead."
  ID                        id-at-zimbraSMIMELdapFilter }

-- LDAP syntax length {256} rendered as DirectoryString{256}.
zimbraSMIMELdapSearchBase ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraSMIMELdapSearchBase"}
  LDAP-DESC                 "LDAP search base for public key lookup for S/MIME via external LDAP. All SMIME attributes are in the format of {config-name}:{value}. A 'SMIME config' is a set of SMIME attribute values with the same {config-name}. Multiple SMIME configs can be configured on a domain or on globalconfig. Note: SMIME attributes on domains do not inherited values from globalconfig, they are not domain-inherited attributes. During SMIME public key lookup, if there are any SMIME config on the domain of the account, they are used. SMIME configs on globalconfig will be used only when there is no SMIME config on the domain. SMIME attributes cannot be modified directly with zmprov md/mcf commands. Use zmprov gcsc/gdsc/mcsc/mdsc/rcsc/rdsc command instead."
  ID                        id-at-zimbraSMIMELdapSearchBase }

zimbraSMIMELdapStartTlsEnabled ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraSMIMELdapStartTlsEnabled"}
  LDAP-DESC                 "Whether to use startTLS for public key lookup for S/MIME via external LDAP. All SMIME attributes are in the format of {config-name}:{value}. A 'SMIME config' is a set of SMIME attribute values with the same {config-name}. Multiple SMIME configs can be configured on a domain or on globalconfig. Note: SMIME attributes on domains do not inherited values from globalconfig, they are not domain-inherited attributes. During SMIME public key lookup, if there are any SMIME config on the domain of the account, they are used. SMIME configs on globalconfig will be used only when there is no SMIME config on the domain. SMIME attributes cannot be modified directly with zmprov md/mcf commands. Use zmprov gcsc/gdsc/mcsc/mdsc/rcsc/rdsc command instead."
  ID                        id-at-zimbraSMIMELdapStartTlsEnabled }

-- LDAP syntax length {256} rendered as DirectoryString{256}.
zimbraSMIMELdapURL ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraSMIMELdapURL"}
  LDAP-DESC                 "LDAP URL(s) for public key lookup for S/MIME via external LDAP. Multiple URLs for error fallback purpose can be separated by space. All SMIME attributes are in the format of {config-name}:{value}. A 'SMIME config' is a set of SMIME attribute values with the same {config-name}. Multiple SMIME configs can be configured on a domain or on globalconfig. Note: SMIME attributes on domains do not inherited values from globalconfig, they are not domain-inherited attributes. During SMIME public key lookup, if there are any SMIME config on the domain of the account, they are used. SMIME configs on globalconfig will be used only when there is no SMIME config on the domain. SMIME attributes cannot be modified directly with zmprov md/mcf commands. Use zmprov gcsc/gdsc/mcsc/mdsc/rcsc/rdsc command instead."
  ID                        id-at-zimbraSMIMELdapURL }

zimbraSSLCertificate ATTRIBUTE ::= {
  WITH SYNTAX               IA5String
  EQUALITY MATCHING RULE    caseIgnoreIA5Match
  SUBSTRINGS MATCHING RULE  caseIgnoreSubstringsMatch
  SINGLE VALUE              TRUE
  LDAP-SYNTAX               ia5String.&id
  LDAP-NAME                 {"zimbraSSLCertificate"}
  LDAP-DESC                 "SSL certificate"
  ID                        id-at-zimbraSSLCertificate }

zimbraSSLExcludeCipherSuites ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraSSLExcludeCipherSuites"}
  LDAP-DESC                 "excluded cipher suites"
  ID                        id-at-zimbraSSLExcludeCipherSuites }

zimbraSSLIncludeCipherSuites ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraSSLIncludeCipherSuites"}
  LDAP-DESC                 "List of included cipher suites for Jetty. If any value is set only these ciphers will be used, in effect superseding zimbraSSLExcludeCipherSuites. Order of selection is based on client preference and default Java order since Java SSLEngine does not allow changing the preference order."
  ID                        id-at-zimbraSSLIncludeCipherSuites }

zimbraSSLPrivateKey ATTRIBUTE ::= {
  WITH SYNTAX               IA5String
  EQUALITY MATCHING RULE    caseIgnoreIA5Match
  SUBSTRINGS MATCHING RULE  caseIgnoreSubstringsMatch
  SINGLE VALUE              TRUE
  LDAP-SYNTAX               ia5String.&id
  LDAP-NAME                 {"zimbraSSLPrivateKey"}
  LDAP-DESC                 "SSL private key"
  ID                        id-at-zimbraSSLPrivateKey }

zimbraSaslGssapiRequiresTls ATTRIBUTE ::= {
  WITH SYNTAX               BOOLEAN
  EQUALITY MATCHING RULE    booleanMatch
  SINGLE VALUE              TRUE
  LDAP-SYNTAX               boolean.&id
  LDAP-NAME                 {"zimbraSaslGssapiRequiresTls"}
  LDAP-DESC                 "whether TLS is required for IMAP/POP GSSAPI auth"
  ID                        id-at-zimbraSaslGssapiRequiresTls }

zimbraScheduledTaskNumThreads ATTRIBUTE ::= {
  WITH SYNTAX               INTEGER
  EQUALITY MATCHING RULE    integerMatch
  SINGLE VALUE              TRUE
  LDAP-SYNTAX               integer.&id
  LDAP-NAME                 {"zimbraScheduledTaskNumThreads"}
  LDAP-DESC                 "Maximum number of scheduled tasks that can run simultaneously."
  ID                        id-at-zimbraScheduledTaskNumThreads }

-- LDAP syntax length {256} rendered as DirectoryString{256}.
zimbraServerExtraObjectClass ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraServerExtraObjectClass"}
  LDAP-DESC                 "Object classes to add when creating a zimbra server object."
  ID                        id-at-zimbraServerExtraObjectClass }

-- LDAP syntax length {256} rendered as DirectoryString{256}.
zimbraServerId ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraServerId"}
  LDAP-DESC                 "ZimbraID of the server that this component is running on"
  ID                        id-at-zimbraServerId }

-- LDAP syntax length {1024} rendered as DirectoryString{1024}.
zimbraServerInheritedAttr ATTRIBUTE ::= {
  WITH SYNTAX               DirectoryString{1024}
  EQUALITY MATCHING RULE    caseIgnoreMatch
  SUBSTRINGS MATCHING RULE  caseIgnoreSubstringsMatch
  LDAP-SYNTAX               directoryString.&id
  LDAP-NAME                 {"zimbraServerInheritedAttr"}
  LDAP-DESC                 "Deprecated since: 5.0. deprecated in favor of the serverInherited flag. Orig desc: zimbraServer attrs that get inherited from global config"
  ID                        id-at-zimbraServerInheritedAttr }

zimbraServerVersion ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraServerVersion"}
  LDAP-DESC                 "Current version of ZCS installed on this server"
  ID                        id-at-zimbraServerVersion }

zimbraServerVersionBuild ATTRIBUTE ::= {
  WITH SYNTAX               INTEGER
  EQUALITY MATCHING RULE    integerMatch
  SINGLE VALUE              TRUE
  LDAP-SYNTAX               integer.&id
  LDAP-NAME                 {"zimbraServerVersionBuild"}
  LDAP-DESC                 "Current build number of ZCS installed on this server for this version"
  ID                        id-at-zimbraServerVersionBuild }

zimbraServerVersionMajor ATTRIBUTE ::= {
  WITH SYNTAX               INTEGER
  EQUALITY MATCHING RULE    integerMatch
  SINGLE VALUE              TRUE
  LDAP-SYNTAX               integer.&id
  LDAP-NAME                 {"zimbraServerVersionMajor"}
  LDAP-DESC                 "Current major version of ZCS installed on this server"
  ID                        id-at-zimbraServerVersionMajor }

zimbraServerVersionMicro ATTRIBUTE ::= {
  WITH SYNTAX               INTEGER
  EQUALITY MATCHING RULE    integerMatch
  SINGLE VALUE              TRUE
  LDAP-SYNTAX               integer.&id
  LDAP-NAME                 {"zimbraServerVersionMicro"}
  LDAP-DESC                 "Current micro level version of ZCS installed on this server"
  ID                        id-at-zimbraServerVersionMicro }

zimbraServerVersionMinor ATTRIBUTE ::= {
  WITH SYNTAX               INTEGER
  EQUALITY MATCHING RULE    integerMatch
  SINGLE VALUE              TRUE
  LDAP-SYNTAX               integer.&id
  LDAP-NAME                 {"zimbraServerVersionMinor"}
  LDAP-DESC                 "Current minor version of ZCS installed on this server"
  ID                        id-at-zimbraServerVersionMinor }

zimbraServerVersionType ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraServerVersionType"}
  LDAP-DESC                 "Current version type of ZCS installed on this server"
  ID                        id-at-zimbraServerVersionType }

-- LDAP syntax length {256} rendered as DirectoryString{256}.
zimbraServiceEnabled ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraServiceEnabled"}
  LDAP-DESC                 "services that are enabled on this server"
  ID                        id-at-zimbraServiceEnabled }

-- LDAP syntax length {256} rendered as DirectoryString{256}.
zimbraServiceHostname ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraServiceHostname"}
  LDAP-DESC                 "public hostname of the host"
  ID                        id-at-zimbraServiceHostname }

-- LDAP syntax length {256} rendered as DirectoryString{256}.
zimbraServiceInstalled ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraServiceInstalled"}
  LDAP-DESC                 "services that are installed on this server"
  ID                        id-at-zimbraServiceInstalled }

-- LDAP syntax length {1024} rendered as DirectoryString{1024}.
zimbraShareInfo ATTRIBUTE ::= {
  WITH SYNTAX               DirectoryString{1024}
  EQUALITY MATCHING RULE    caseIgnoreMatch
  SUBSTRINGS MATCHING RULE  caseIgnoreSubstringsMatch
  LDAP-SYNTAX               directoryString.&id
  LDAP-NAME                 {"zimbraShareInfo"}
  LDAP-DESC                 "Deprecated since: 8.0.0. Manual publishing of shares by admin is no longer required since now automated publishing of sharing info updates to LDAP is supported. Orig desc: items an account or group has shared"
  ID                        id-at-zimbraShareInfo }

zimbraShareLifetime ATTRIBUTE ::= {
  WITH SYNTAX               IA5String(SIZE (1..32))
  EQUALITY MATCHING RULE    caseIgnoreIA5Match
  SINGLE VALUE              TRUE
  LDAP-SYNTAX               ia5String.&id
  LDAP-NAME                 {"zimbraShareLifetime"}
  LDAP-DESC                 "Maximum allowed lifetime of shares to internal users or groups. A value of 0 indicates that there's no limit on an internal share's lifetime. . Must be in valid duration format: {digits}{time-unit}. digits: 0-9, time-unit: [hmsd]|ms. h - hours, m - minutes, s - seconds, d - days, ms - milliseconds. If time unit is not specified, the default is s(seconds)."
  ID                        id-at-zimbraShareLifetime }

-- LDAP syntax length {128} rendered as DirectoryString{128}.
zimbraShareNotificationMtaAuthAccount ATTRIBUTE ::= {
  WITH SYNTAX               DirectoryString{128}
  EQUALITY MATCHING RULE    caseIgnoreMatch
  SUBSTRINGS MATCHING RULE  caseIgnoreSubstringsMatch
  SINGLE VALUE              TRUE
  LDAP-SYNTAX               directoryString.&id
  LDAP-NAME                 {"zimbraShareNotificationMtaAuthAccount"}
  LDAP-DESC                 "Account name for authenticating to share notification MTA."
  ID                        id-at-zimbraShareNotificationMtaAuthAccount }

-- LDAP syntax length {64} rendered as DirectoryString{64}.
zimbraShareNotificationMtaAuthPassword ATTRIBUTE ::= {
  WITH SYNTAX               DirectoryString{64}
  EQUALITY MATCHING RULE    caseIgnoreMatch
  SUBSTRINGS MATCHING RULE  caseIgnoreSubstringsMatch
  SINGLE VALUE              TRUE
  LDAP-SYNTAX               directoryString.&id
  LDAP-NAME                 {"zimbraShareNotificationMtaAuthPassword"}
  LDAP-DESC                 "Password for authenticating to share notification MTA."
  ID                        id-at-zimbraShareNotificationMtaAuthPassword }

zimbraShareNotificationMtaAuthRequired ATTRIBUTE ::= {
  WITH SYNTAX               BOOLEAN
  EQUALITY MATCHING RULE    booleanMatch
  SINGLE VALUE              TRUE
  LDAP-SYNTAX               boolean.&id
  LDAP-NAME                 {"zimbraShareNotificationMtaAuthRequired"}
  LDAP-DESC                 "Whether to use credential to authenticate to share notification MTA."
  ID                        id-at-zimbraShareNotificationMtaAuthRequired }

-- LDAP syntax length {32} rendered as DirectoryString{32}.
zimbraShareNotificationMtaConnectionType ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraShareNotificationMtaConnectionType"}
  LDAP-DESC                 "Connection mode when connecting to share notification MTA."
  ID                        id-at-zimbraShareNotificationMtaConnectionType }

zimbraShareNotificationMtaEnabled ATTRIBUTE ::= {
  WITH SYNTAX               BOOLEAN
  EQUALITY MATCHING RULE    booleanMatch
  SINGLE VALUE              TRUE
  LDAP-SYNTAX               boolean.&id
  LDAP-NAME                 {"zimbraShareNotificationMtaEnabled"}
  LDAP-DESC                 "Whether share notification MTA is enabled."
  ID                        id-at-zimbraShareNotificationMtaEnabled }

-- LDAP syntax length {128} rendered as DirectoryString{128}.
zimbraShareNotificationMtaHostname ATTRIBUTE ::= {
  WITH SYNTAX               DirectoryString{128}
  EQUALITY MATCHING RULE    caseIgnoreMatch
  SUBSTRINGS MATCHING RULE  caseIgnoreSubstringsMatch
  SINGLE VALUE              TRUE
  LDAP-SYNTAX               directoryString.&id
  LDAP-NAME                 {"zimbraShareNotificationMtaHostname"}
  LDAP-DESC                 "SMTP hostname for share notification MTA used for sending email notifications."
  ID                        id-at-zimbraShareNotificationMtaHostname }

zimbraShareNotificationMtaPort ATTRIBUTE ::= {
  WITH SYNTAX               INTEGER
  EQUALITY MATCHING RULE    integerMatch
  SINGLE VALUE              TRUE
  LDAP-SYNTAX               integer.&id
  LDAP-NAME                 {"zimbraShareNotificationMtaPort"}
  LDAP-DESC                 "SMTP port for share notification MTA used for sending email notifications."
  ID                        id-at-zimbraShareNotificationMtaPort }

-- LDAP syntax length {256} rendered as DirectoryString{256}.
zimbraShareOwnerAccountId ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraShareOwnerAccountId"}
  LDAP-DESC                 "account ID of the owner of the shared folder"
  ID                        id-at-zimbraShareOwnerAccountId }

-- LDAP syntax length {1024} rendered as DirectoryString{1024}.
zimbraSharedItem ATTRIBUTE ::= {
  WITH SYNTAX               DirectoryString{1024}
  EQUALITY MATCHING RULE    caseIgnoreMatch
  SUBSTRINGS MATCHING RULE  caseIgnoreSubstringsMatch
  LDAP-SYNTAX               directoryString.&id
  LDAP-NAME                 {"zimbraSharedItem"}
  LDAP-DESC                 "All items an account has shared"
  ID                        id-at-zimbraSharedItem }

zimbraSharingUpdatePublishInterval ATTRIBUTE ::= {
  WITH SYNTAX               IA5String(SIZE (1..32))
  EQUALITY MATCHING RULE    caseIgnoreIA5Match
  SINGLE VALUE              TRUE
  LDAP-SYNTAX               ia5String.&id
  LDAP-NAME                 {"zimbraSharingUpdatePublishInterval"}
  LDAP-DESC                 "Interval between successive executions of the task that publishes shared item updates to LDAP. Must be in valid duration format: {digits}{time-unit}. digits: 0-9, time-unit: [hmsd]|ms. h - hours, m - minutes, s - seconds, d - days, ms - milliseconds. If time unit is not specified, the default is s(seconds)."
  ID                        id-at-zimbraSharingUpdatePublishInterval }

-- LDAP syntax length {256} rendered as DirectoryString{256}.
zimbraSignatureId ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraSignatureId"}
  LDAP-DESC                 "Unique ID for an signature"
  ID                        id-at-zimbraSignatureId }

zimbraSignatureMaxNumEntries ATTRIBUTE ::= {
  WITH SYNTAX               INTEGER
  EQUALITY MATCHING RULE    integerMatch
  SINGLE VALUE              TRUE
  LDAP-SYNTAX               integer.&id
  LDAP-NAME                 {"zimbraSignatureMaxNumEntries"}
  LDAP-DESC                 "maximum number of signatures allowed on an account"
  ID                        id-at-zimbraSignatureMaxNumEntries }

zimbraSignatureMinNumEntries ATTRIBUTE ::= {
  WITH SYNTAX               INTEGER
  EQUALITY MATCHING RULE    integerMatch
  SINGLE VALUE              TRUE
  LDAP-SYNTAX               integer.&id
  LDAP-NAME                 {"zimbraSignatureMinNumEntries"}
  LDAP-DESC                 "minimum number of signatures allowed on an account, this is only used in the client"
  ID                        id-at-zimbraSignatureMinNumEntries }

-- LDAP syntax length {128} rendered as DirectoryString{128}.
zimbraSignatureName ATTRIBUTE ::= {
  WITH SYNTAX               DirectoryString{128}
  EQUALITY MATCHING RULE    caseIgnoreMatch
  SUBSTRINGS MATCHING RULE  caseIgnoreSubstringsMatch
  SINGLE VALUE              TRUE
  LDAP-SYNTAX               directoryString.&id
  LDAP-NAME                 {"zimbraSignatureName"}
  LDAP-DESC                 "name of the signature"
  ID                        id-at-zimbraSignatureName }

-- LDAP syntax length {256} rendered as DirectoryString{256}.
zimbraSkinBackgroundColor ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraSkinBackgroundColor"}
  LDAP-DESC                 "background color for chameleon skin for the domain"
  ID                        id-at-zimbraSkinBackgroundColor }

-- LDAP syntax length {256} rendered as DirectoryString{256}.
zimbraSkinFavicon ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraSkinFavicon"}
  LDAP-DESC                 "favicon for chameleon skin for the domain"
  ID                        id-at-zimbraSkinFavicon }

-- LDAP syntax length {256} rendered as DirectoryString{256}.
zimbraSkinForegroundColor ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraSkinForegroundColor"}
  LDAP-DESC                 "foreground color for chameleon skin for the domain"
  ID                        id-at-zimbraSkinForegroundColor }

-- LDAP syntax length {256} rendered as DirectoryString{256}.
zimbraSkinLogoAppBanner ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraSkinLogoAppBanner"}
  LDAP-DESC                 "logo app banner for chameleon skin for the domain"
  ID                        id-at-zimbraSkinLogoAppBanner }

-- LDAP syntax length {256} rendered as DirectoryString{256}.
zimbraSkinLogoLoginBanner ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraSkinLogoLoginBanner"}
  LDAP-DESC                 "logo login banner for chameleon skin for the domain"
  ID                        id-at-zimbraSkinLogoLoginBanner }

-- LDAP syntax length {256} rendered as DirectoryString{256}.
zimbraSkinLogoURL ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraSkinLogoURL"}
  LDAP-DESC                 "Logo URL for chameleon skin for the domain"
  ID                        id-at-zimbraSkinLogoURL }

-- LDAP syntax length {256} rendered as DirectoryString{256}.
zimbraSkinSecondaryColor ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraSkinSecondaryColor"}
  LDAP-DESC                 "secondary color for chameleon skin for the domain"
  ID                        id-at-zimbraSkinSecondaryColor }

-- LDAP syntax length {256} rendered as DirectoryString{256}.
zimbraSkinSelectionColor ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraSkinSelectionColor"}
  LDAP-DESC                 "selection color for chameleon skin for the domain"
  ID                        id-at-zimbraSkinSelectionColor }

zimbraSmtpEnableTrace ATTRIBUTE ::= {
  WITH SYNTAX               BOOLEAN
  EQUALITY MATCHING RULE    booleanMatch
  SINGLE VALUE              TRUE
  LDAP-SYNTAX               boolean.&id
  LDAP-NAME                 {"zimbraSmtpEnableTrace"}
  LDAP-DESC                 "Whether to enable smtp debug trace"
  ID                        id-at-zimbraSmtpEnableTrace }

zimbraSmtpHostname ATTRIBUTE ::= {
  WITH SYNTAX               IA5String(SIZE (1..256))
  EQUALITY MATCHING RULE    caseIgnoreIA5Match
  SUBSTRINGS MATCHING RULE  caseIgnoreSubstringsMatch
  LDAP-SYNTAX               ia5String.&id
  LDAP-NAME                 {"zimbraSmtpHostname"}
  LDAP-DESC                 "the SMTP server to connect to when sending mail"
  ID                        id-at-zimbraSmtpHostname }

zimbraSmtpPort ATTRIBUTE ::= {
  WITH SYNTAX               INTEGER
  EQUALITY MATCHING RULE    integerMatch
  SINGLE VALUE              TRUE
  LDAP-SYNTAX               integer.&id
  LDAP-NAME                 {"zimbraSmtpPort"}
  LDAP-DESC                 "the SMTP server port to connect to when sending mail"
  ID                        id-at-zimbraSmtpPort }

zimbraSmtpRestrictEnvelopeFrom ATTRIBUTE ::= {
  WITH SYNTAX               BOOLEAN
  EQUALITY MATCHING RULE    booleanMatch
  SINGLE VALUE              TRUE
  LDAP-SYNTAX               boolean.&id
  LDAP-NAME                 {"zimbraSmtpRestrictEnvelopeFrom"}
  LDAP-DESC                 "If TRUE, the address for MAIL FROM in the SMTP session will always be set to the email address of the account. If FALSE, the address will be the value of the Sender or From header in the outgoing message, in that order."
  ID                        id-at-zimbraSmtpRestrictEnvelopeFrom }

zimbraSmtpSendAddAuthenticatedUser ATTRIBUTE ::= {
  WITH SYNTAX               BOOLEAN
  EQUALITY MATCHING RULE    booleanMatch
  SINGLE VALUE              TRUE
  LDAP-SYNTAX               boolean.&id
  LDAP-NAME                 {"zimbraSmtpSendAddAuthenticatedUser"}
  LDAP-DESC                 "If true, an X-Authenticated-User header will be added to messages sent via SendMsgRequest."
  ID                        id-at-zimbraSmtpSendAddAuthenticatedUser }

zimbraSmtpSendAddMailer ATTRIBUTE ::= {
  WITH SYNTAX               BOOLEAN
  EQUALITY MATCHING RULE    booleanMatch
  SINGLE VALUE              TRUE
  LDAP-SYNTAX               boolean.&id
  LDAP-NAME                 {"zimbraSmtpSendAddMailer"}
  LDAP-DESC                 "Whether X-Mailer will be added to messages sent by Zimbra"
  ID                        id-at-zimbraSmtpSendAddMailer }

zimbraSmtpSendAddOriginatingIP ATTRIBUTE ::= {
  WITH SYNTAX               BOOLEAN
  EQUALITY MATCHING RULE    booleanMatch
  SINGLE VALUE              TRUE
  LDAP-SYNTAX               boolean.&id
  LDAP-NAME                 {"zimbraSmtpSendAddOriginatingIP"}
  LDAP-DESC                 "Whether X-Originating-IP will be added to messages sent via SendMsgRequest."
  ID                        id-at-zimbraSmtpSendAddOriginatingIP }

zimbraSmtpSendPartial ATTRIBUTE ::= {
  WITH SYNTAX               BOOLEAN
  EQUALITY MATCHING RULE    booleanMatch
  SINGLE VALUE              TRUE
  LDAP-SYNTAX               boolean.&id
  LDAP-NAME                 {"zimbraSmtpSendPartial"}
  LDAP-DESC                 "Value of the mail.smtp.sendpartial property"
  ID                        id-at-zimbraSmtpSendPartial }

zimbraSmtpTimeout ATTRIBUTE ::= {
  WITH SYNTAX               INTEGER
  EQUALITY MATCHING RULE    integerMatch
  SINGLE VALUE              TRUE
  LDAP-SYNTAX               integer.&id
  LDAP-NAME                 {"zimbraSmtpTimeout"}
  LDAP-DESC                 "timeout value in seconds"
  ID                        id-at-zimbraSmtpTimeout }

zimbraSoapExposeVersion ATTRIBUTE ::= {
  WITH SYNTAX               BOOLEAN
  EQUALITY MATCHING RULE    booleanMatch
  SINGLE VALUE              TRUE
  LDAP-SYNTAX               boolean.&id
  LDAP-NAME                 {"zimbraSoapExposeVersion"}
  LDAP-DESC                 "If TRUE, enables support for GetVersionInfo for account SOAP requests. If FALSE, GetVersionInfoRequest returns a SOAP fault."
  ID                        id-at-zimbraSoapExposeVersion }

zimbraSoapRequestMaxSize ATTRIBUTE ::= {
  WITH SYNTAX               INTEGER
  EQUALITY MATCHING RULE    integerMatch
  SINGLE VALUE              TRUE
  LDAP-SYNTAX               integer.&id
  LDAP-NAME                 {"zimbraSoapRequestMaxSize"}
  LDAP-DESC                 "Maximum size in bytes for incoming SOAP requests. 0 means no limit."
  ID                        id-at-zimbraSoapRequestMaxSize }

-- LDAP syntax length {256} rendered as DirectoryString{256}.
zimbraSocialcastURL ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraSocialcastURL"}
  LDAP-DESC                 "URL for Socialcast integration"
  ID                        id-at-zimbraSocialcastURL }

zimbraSpamApplyUserFilters ATTRIBUTE ::= {
  WITH SYNTAX               BOOLEAN
  EQUALITY MATCHING RULE    booleanMatch
  SINGLE VALUE              TRUE
  LDAP-SYNTAX               boolean.&id
  LDAP-NAME                 {"zimbraSpamApplyUserFilters"}
  LDAP-DESC                 "If TRUE, spam messages will be affected by user mail filters instead of being automatically filed into the Junk folder."
  ID                        id-at-zimbraSpamApplyUserFilters }

zimbraSpamCheckEnabled ATTRIBUTE ::= {
  WITH SYNTAX               BOOLEAN
  EQUALITY MATCHING RULE    booleanMatch
  SINGLE VALUE              TRUE
  LDAP-SYNTAX               boolean.&id
  LDAP-NAME                 {"zimbraSpamCheckEnabled"}
  LDAP-DESC                 "Deprecated since: 4.5. Deprecated in favor of zimbraServiceEnabled. Orig desc: Whether to enable spam checking"
  ID                        id-at-zimbraSpamCheckEnabled }

zimbraSpamHeader ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraSpamHeader"}
  LDAP-DESC                 "mail header name for flagging spam"
  ID                        id-at-zimbraSpamHeader }

zimbraSpamHeaderValue ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraSpamHeaderValue"}
  LDAP-DESC                 "regular expression for matching the spam header"
  ID                        id-at-zimbraSpamHeaderValue }

zimbraSpamIsNotSpamAccount ATTRIBUTE ::= {
  WITH SYNTAX               IA5String(SIZE (1..256))
  EQUALITY MATCHING RULE    caseIgnoreIA5Match
  SUBSTRINGS MATCHING RULE  caseIgnoreSubstringsMatch
  SINGLE VALUE              TRUE
  LDAP-SYNTAX               ia5String.&id
  LDAP-NAME                 {"zimbraSpamIsNotSpamAccount"}
  LDAP-DESC                 "When user classifies a message as not spam forward message via SMTP to this account"
  ID                        id-at-zimbraSpamIsNotSpamAccount }

zimbraSpamIsSpamAccount ATTRIBUTE ::= {
  WITH SYNTAX               IA5String(SIZE (1..256))
  EQUALITY MATCHING RULE    caseIgnoreIA5Match
  SUBSTRINGS MATCHING RULE  caseIgnoreSubstringsMatch
  SINGLE VALUE              TRUE
  LDAP-SYNTAX               ia5String.&id
  LDAP-NAME                 {"zimbraSpamIsSpamAccount"}
  LDAP-DESC                 "When user classifies a message as spam forward message via SMTP to this account"
  ID                        id-at-zimbraSpamIsSpamAccount }

zimbraSpamKillPercent ATTRIBUTE ::= {
  WITH SYNTAX               INTEGER
  EQUALITY MATCHING RULE    integerMatch
  SINGLE VALUE              TRUE
  LDAP-SYNTAX               integer.&id
  LDAP-NAME                 {"zimbraSpamKillPercent"}
  LDAP-DESC                 "Spaminess percentage beyond which a message is dropped"
  ID                        id-at-zimbraSpamKillPercent }

zimbraSpamReportEnvelopeFrom ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraSpamReportEnvelopeFrom"}
  LDAP-DESC                 "value for envelope from (MAIL FROM) in spam report"
  ID                        id-at-zimbraSpamReportEnvelopeFrom }

zimbraSpamReportSenderHeader ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraSpamReportSenderHeader"}
  LDAP-DESC                 "mail header name for sender in spam report"
  ID                        id-at-zimbraSpamReportSenderHeader }

zimbraSpamReportTypeHam ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraSpamReportTypeHam"}
  LDAP-DESC                 "spam report type value for ham"
  ID                        id-at-zimbraSpamReportTypeHam }

zimbraSpamReportTypeHeader ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraSpamReportTypeHeader"}
  LDAP-DESC                 "mail header name for report type in spam report"
  ID                        id-at-zimbraSpamReportTypeHeader }

zimbraSpamReportTypeSpam ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraSpamReportTypeSpam"}
  LDAP-DESC                 "spam report type value for spam"
  ID                        id-at-zimbraSpamReportTypeSpam }

zimbraSpamSubjectTag ATTRIBUTE ::= {
  WITH SYNTAX               IA5String(SIZE (1..32))
  EQUALITY MATCHING RULE    caseIgnoreIA5Match
  SUBSTRINGS MATCHING RULE  caseIgnoreSubstringsMatch
  SINGLE VALUE              TRUE
  LDAP-SYNTAX               ia5String.&id
  LDAP-NAME                 {"zimbraSpamSubjectTag"}
  LDAP-DESC                 "Subject prefix for spam messages"
  ID                        id-at-zimbraSpamSubjectTag }

zimbraSpamTagPercent ATTRIBUTE ::= {
  WITH SYNTAX               INTEGER
  EQUALITY MATCHING RULE    integerMatch
  SINGLE VALUE              TRUE
  LDAP-SYNTAX               integer.&id
  LDAP-NAME                 {"zimbraSpamTagPercent"}
  LDAP-DESC                 "Spaminess percentage beyond which a message is marked as spam"
  ID                        id-at-zimbraSpamTagPercent }

-- LDAP syntax length {128} rendered as DirectoryString{128}.
zimbraSpamTrashAlias ATTRIBUTE ::= {
  WITH SYNTAX               DirectoryString{128}
  EQUALITY MATCHING RULE    caseIgnoreMatch
  SUBSTRINGS MATCHING RULE  caseIgnoreSubstringsMatch
  LDAP-SYNTAX               directoryString.&id
  LDAP-NAME                 {"zimbraSpamTrashAlias"}
  LDAP-DESC                 "Aliases of Trash folder. In case some IMAP clients use different folder names other than Trash, the spam filter still special-cases those folders as if they are Trash."
  ID                        id-at-zimbraSpamTrashAlias }

zimbraSpamWhitelistHeader ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraSpamWhitelistHeader"}
  LDAP-DESC                 "Mail header name for flagging a message as not spam. If set, this takes precedence over zimbraSpamHeader."
  ID                        id-at-zimbraSpamWhitelistHeader }

zimbraSpamWhitelistHeaderValue ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraSpamWhitelistHeaderValue"}
  LDAP-DESC                 "regular expression for matching the value of zimbraSpamWhitelistHeader for flagging a message as not spam"
  ID                        id-at-zimbraSpamWhitelistHeaderValue }

zimbraSpellAvailableDictionary ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraSpellAvailableDictionary"}
  LDAP-DESC                 "The list of available dictionaries that can be used for spell checking."
  ID                        id-at-zimbraSpellAvailableDictionary }

zimbraSpellCheckURL ATTRIBUTE ::= {
  WITH SYNTAX               IA5String(SIZE (1..256))
  EQUALITY MATCHING RULE    caseIgnoreIA5Match
  SUBSTRINGS MATCHING RULE  caseIgnoreSubstringsMatch
  LDAP-SYNTAX               ia5String.&id
  LDAP-NAME                 {"zimbraSpellCheckURL"}
  LDAP-DESC                 "URL of the server running the spell checking service. Multi-valued attribute that allows multiple spell check servers to be specified. If the request to the first server fails, a request to the second server is sent and so on."
  ID                        id-at-zimbraSpellCheckURL }

zimbraSpnegoAuthEnabled ATTRIBUTE ::= {
  WITH SYNTAX               BOOLEAN
  EQUALITY MATCHING RULE    booleanMatch
  SINGLE VALUE              TRUE
  LDAP-SYNTAX               boolean.&id
  LDAP-NAME                 {"zimbraSpnegoAuthEnabled"}
  LDAP-DESC                 "whether spnego SSO is enabled"
  ID                        id-at-zimbraSpnegoAuthEnabled }

zimbraSpnegoAuthErrorURL ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraSpnegoAuthErrorURL"}
  LDAP-DESC                 "spnego auth error URL"
  ID                        id-at-zimbraSpnegoAuthErrorURL }

zimbraSpnegoAuthPrincipal ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraSpnegoAuthPrincipal"}
  LDAP-DESC                 "spnego auth principal"
  ID                        id-at-zimbraSpnegoAuthPrincipal }

zimbraSpnegoAuthRealm ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraSpnegoAuthRealm"}
  LDAP-DESC                 "spnego auth realm"
  ID                        id-at-zimbraSpnegoAuthRealm }

zimbraSpnegoAuthTargetName ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraSpnegoAuthTargetName"}
  LDAP-DESC                 "spnego auth target name"
  ID                        id-at-zimbraSpnegoAuthTargetName }

zimbraSshPublicKey ATTRIBUTE ::= {
  WITH SYNTAX               IA5String(SIZE (1..1024))
  EQUALITY MATCHING RULE    caseIgnoreIA5Match
  SUBSTRINGS MATCHING RULE  caseIgnoreSubstringsMatch
  SINGLE VALUE              TRUE
  LDAP-SYNTAX               ia5String.&id
  LDAP-NAME                 {"zimbraSshPublicKey"}
  LDAP-DESC                 "Public key of this server, used by other hosts to authorize this server to login."
  ID                        id-at-zimbraSshPublicKey }

zimbraSslCaCert ATTRIBUTE ::= {
  WITH SYNTAX               IA5String(SIZE (1..2048))
  EQUALITY MATCHING RULE    caseIgnoreIA5Match
  SUBSTRINGS MATCHING RULE  caseIgnoreSubstringsMatch
  SINGLE VALUE              TRUE
  LDAP-SYNTAX               ia5String.&id
  LDAP-NAME                 {"zimbraSslCaCert"}
  LDAP-DESC                 "CA Cert used to sign all self signed certs"
  ID                        id-at-zimbraSslCaCert }

zimbraSslCaKey ATTRIBUTE ::= {
  WITH SYNTAX               IA5String(SIZE (1..2048))
  EQUALITY MATCHING RULE    caseIgnoreIA5Match
  SUBSTRINGS MATCHING RULE  caseIgnoreSubstringsMatch
  SINGLE VALUE              TRUE
  LDAP-SYNTAX               ia5String.&id
  LDAP-NAME                 {"zimbraSslCaKey"}
  LDAP-DESC                 "CA Key used to sign all self signed certs"
  ID                        id-at-zimbraSslCaKey }

-- LDAP syntax length {256} rendered as DirectoryString{256}.
zimbraStandardClientCustomPrefTab ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraStandardClientCustomPrefTab"}
  LDAP-DESC                 "description of the custom tab in the Preferences page in HTML client in the format {tab-name},{associated-URL}"
  ID                        id-at-zimbraStandardClientCustomPrefTab }

zimbraStandardClientCustomPrefTabsEnabled ATTRIBUTE ::= {
  WITH SYNTAX               BOOLEAN
  EQUALITY MATCHING RULE    booleanMatch
  SINGLE VALUE              TRUE
  LDAP-SYNTAX               boolean.&id
  LDAP-NAME                 {"zimbraStandardClientCustomPrefTabsEnabled"}
  LDAP-DESC                 "whether extra custom tabs in the Preferences page in HTML client are enabled"
  ID                        id-at-zimbraStandardClientCustomPrefTabsEnabled }

zimbraStatThreadNamePrefix ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraStatThreadNamePrefix"}
  LDAP-DESC                 "Prefixes of thread names. Each value is a column in threads.csv that tracks the number of threads whose name starts with the given prefix."
  ID                        id-at-zimbraStatThreadNamePrefix }

zimbraSyncWindowSize ATTRIBUTE ::= {
  WITH SYNTAX               INTEGER
  EQUALITY MATCHING RULE    integerMatch
  SINGLE VALUE              TRUE
  LDAP-SYNTAX               integer.&id
  LDAP-NAME                 {"zimbraSyncWindowSize"}
  LDAP-DESC                 "The maximum batch size for each ZimbraSync transaction. Default value of 0 means to follow client requested size. If set to any positive integer, the value will be the maximum number of items to sync even if client requests more. This setting affects all sync categories including email, contacts, calendar and tasks."
  ID                        id-at-zimbraSyncWindowSize }

zimbraTableMaintenanceGrowthFactor ATTRIBUTE ::= {
  WITH SYNTAX               INTEGER
  EQUALITY MATCHING RULE    integerMatch
  SINGLE VALUE              TRUE
  LDAP-SYNTAX               integer.&id
  LDAP-NAME                 {"zimbraTableMaintenanceGrowthFactor"}
  LDAP-DESC                 "Deprecated since: 4.5.7. We now maintain all tables unconditionally. See bug 19145. Orig desc: table maintenance will be performed if the number of rows grows by this factor"
  ID                        id-at-zimbraTableMaintenanceGrowthFactor }

zimbraTableMaintenanceMaxRows ATTRIBUTE ::= {
  WITH SYNTAX               INTEGER
  EQUALITY MATCHING RULE    integerMatch
  SINGLE VALUE              TRUE
  LDAP-SYNTAX               integer.&id
  LDAP-NAME                 {"zimbraTableMaintenanceMaxRows"}
  LDAP-DESC                 "Deprecated since: 4.5.7. We now maintain all tables unconditionally. See bug 19145. Orig desc: maximum number of rows required for database table maintenance"
  ID                        id-at-zimbraTableMaintenanceMaxRows }

zimbraTableMaintenanceMinRows ATTRIBUTE ::= {
  WITH SYNTAX               INTEGER
  EQUALITY MATCHING RULE    integerMatch
  SINGLE VALUE              TRUE
  LDAP-SYNTAX               integer.&id
  LDAP-NAME                 {"zimbraTableMaintenanceMinRows"}
  LDAP-DESC                 "Deprecated since: 4.5.7. We now maintain all tables unconditionally. See bug 19145. Orig desc: minimum number of rows required for database table maintenance"
  ID                        id-at-zimbraTableMaintenanceMinRows }

-- LDAP syntax length {32} rendered as DirectoryString{32}.
zimbraTableMaintenanceOperation ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraTableMaintenanceOperation"}
  LDAP-DESC                 "Deprecated since: 4.5.7. We now maintain all tables unconditionally. See bug 19145. Orig desc: table maintenance operation that will be performed. Valid options: ""ANALYZE"", ""OPTIMIZE"""
  ID                        id-at-zimbraTableMaintenanceOperation }

zimbraTextAnalyzer ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraTextAnalyzer"}
  LDAP-DESC                 "The registered name of the Zimbra Analyzer Extension for this account to use"
  ID                        id-at-zimbraTextAnalyzer }

zimbraThreadMonitorEnabled ATTRIBUTE ::= {
  WITH SYNTAX               BOOLEAN
  EQUALITY MATCHING RULE    booleanMatch
  SINGLE VALUE              TRUE
  LDAP-SYNTAX               boolean.&id
  LDAP-NAME                 {"zimbraThreadMonitorEnabled"}
  LDAP-DESC                 "Whether or not Jetty thread monitor is enabled. Used for debugging Jetty, not recommended for extended use in production environment. Defaults to FALSE"
  ID                        id-at-zimbraThreadMonitorEnabled }

zimbraThrottleSafeHosts ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraThrottleSafeHosts"}
  LDAP-DESC                 "Hosts to ignore during IP based throttling. Account and command rate limits will still be applied. Typically should list nginx hostname and any other mailbox servers which can proxy to this server"
  ID                        id-at-zimbraThrottleSafeHosts }

zimbraThrottleWhitelist ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraThrottleWhitelist"}
  LDAP-DESC                 "Hosts to whitelist during IP based throttling. Account and command rate limits will not be applied. This should only be used for internal servers which cannot service end user traffic; e.g. migration or monitoring hosts"
  ID                        id-at-zimbraThrottleWhitelist }

-- LDAP syntax length {256} rendered as DirectoryString{256}.
zimbraTimeZoneDaylightDtStart ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraTimeZoneDaylightDtStart"}
  LDAP-DESC                 "Deprecated since: 5.0. Deprecated as of bug 12416. Orig desc: Start date for daylight time"
  ID                        id-at-zimbraTimeZoneDaylightDtStart }

-- LDAP syntax length {5} rendered as DirectoryString{5}.
zimbraTimeZoneDaylightOffset ATTRIBUTE ::= {
  WITH SYNTAX               DirectoryString{5}
  EQUALITY MATCHING RULE    caseIgnoreMatch
  SUBSTRINGS MATCHING RULE  caseIgnoreSubstringsMatch
  LDAP-SYNTAX               directoryString.&id
  LDAP-NAME                 {"zimbraTimeZoneDaylightOffset"}
  LDAP-DESC                 "Deprecated since: 5.0. Deprecated as of bug 12416. Orig desc: Offset in daylight time"
  ID                        id-at-zimbraTimeZoneDaylightOffset }

-- LDAP syntax length {256} rendered as DirectoryString{256}.
zimbraTimeZoneDaylightRRule ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraTimeZoneDaylightRRule"}
  LDAP-DESC                 "Deprecated since: 5.0. Deprecated as of bug 12416. Orig desc: iCalendar recurrence rule for onset of daylight time"
  ID                        id-at-zimbraTimeZoneDaylightRRule }

-- LDAP syntax length {256} rendered as DirectoryString{256}.
zimbraTimeZoneStandardDtStart ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraTimeZoneStandardDtStart"}
  LDAP-DESC                 "Deprecated since: 5.0. Deprecated as of bug 12416. Orig desc: Start date for standard time"
  ID                        id-at-zimbraTimeZoneStandardDtStart }

-- LDAP syntax length {5} rendered as DirectoryString{5}.
zimbraTimeZoneStandardOffset ATTRIBUTE ::= {
  WITH SYNTAX               DirectoryString{5}
  EQUALITY MATCHING RULE    caseIgnoreMatch
  SUBSTRINGS MATCHING RULE  caseIgnoreSubstringsMatch
  LDAP-SYNTAX               directoryString.&id
  LDAP-NAME                 {"zimbraTimeZoneStandardOffset"}
  LDAP-DESC                 "Deprecated since: 5.0. Deprecated as of bug 12416. Orig desc: Offset in standard time"
  ID                        id-at-zimbraTimeZoneStandardOffset }

-- LDAP syntax length {256} rendered as DirectoryString{256}.
zimbraTimeZoneStandardRRule ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraTimeZoneStandardRRule"}
  LDAP-DESC                 "Deprecated since: 5.0. Deprecated as of bug 12416. Orig desc: iCalendar recurrence rule for onset of standard time"
  ID                        id-at-zimbraTimeZoneStandardRRule }

zimbraTouchJSErrorTrackingEnabled ATTRIBUTE ::= {
  WITH SYNTAX               BOOLEAN
  EQUALITY MATCHING RULE    booleanMatch
  SINGLE VALUE              TRUE
  LDAP-SYNTAX               boolean.&id
  LDAP-NAME                 {"zimbraTouchJSErrorTrackingEnabled"}
  LDAP-DESC                 "whether JavaScript error tracking via third party service is enabled"
  ID                        id-at-zimbraTouchJSErrorTrackingEnabled }

zimbraTouchJSErrorTrackingKey ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraTouchJSErrorTrackingKey"}
  LDAP-DESC                 "Key to be used for JavaScript error tracking via third party service"
  ID                        id-at-zimbraTouchJSErrorTrackingKey }

-- LDAP syntax length {256} rendered as DirectoryString{256}.
zimbraUCCallControlURL ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraUCCallControlURL"}
  LDAP-DESC                 "call control service URL for the UC service"
  ID                        id-at-zimbraUCCallControlURL }

-- LDAP syntax length {256} rendered as DirectoryString{256}.
zimbraUCPassword ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraUCPassword"}
  LDAP-DESC                 "password for the user's UC service"
  ID                        id-at-zimbraUCPassword }

-- LDAP syntax length {256} rendered as DirectoryString{256}.
zimbraUCPresenceSessionId ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraUCPresenceSessionId"}
  LDAP-DESC                 "presence session id for Cisco presence service"
  ID                        id-at-zimbraUCPresenceSessionId }

-- LDAP syntax length {256} rendered as DirectoryString{256}.
zimbraUCPresenceURL ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraUCPresenceURL"}
  LDAP-DESC                 "presence service URL for the UC service"
  ID                        id-at-zimbraUCPresenceURL }

-- LDAP syntax length {256} rendered as DirectoryString{256}.
zimbraUCProvider ATTRIBUTE ::= {
  WITH SYNTAX               DirectoryString{256}
  EQUALITY MATCHING RULE    caseExactMatch
  SUBSTRINGS MATCHING RULE  caseExactSubstringsMatch
  SINGLE VALUE              TRUE
  LDAP-SYNTAX               directoryString.&id
  LDAP-NAME                 {"zimbraUCProvider"}
  LDAP-DESC                 "provider for the UC service"
  ID                        id-at-zimbraUCProvider }

-- LDAP syntax length {256} rendered as DirectoryString{256}.
zimbraUCProviderEnabled ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraUCProviderEnabled"}
  LDAP-DESC                 "Designated UC provider of the system"
  ID                        id-at-zimbraUCProviderEnabled }

-- LDAP syntax length {256} rendered as DirectoryString{256}.
zimbraUCServiceId ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraUCServiceId"}
  LDAP-DESC                 "UC service zimbraId"
  ID                        id-at-zimbraUCServiceId }

-- LDAP syntax length {256} rendered as DirectoryString{256}.
zimbraUCUserURL ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraUCUserURL"}
  LDAP-DESC                 "user info service URL for the UC service"
  ID                        id-at-zimbraUCUserURL }

-- LDAP syntax length {256} rendered as DirectoryString{256}.
zimbraUCUsername ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraUCUsername"}
  LDAP-DESC                 "username for the user's UC service"
  ID                        id-at-zimbraUCUsername }

-- LDAP syntax length {256} rendered as DirectoryString{256}.
zimbraUCVoicemailURL ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraUCVoicemailURL"}
  LDAP-DESC                 "voicemail service URL for the UC service"
  ID                        id-at-zimbraUCVoicemailURL }

zimbraUserServicesEnabled ATTRIBUTE ::= {
  WITH SYNTAX               BOOLEAN
  EQUALITY MATCHING RULE    booleanMatch
  SINGLE VALUE              TRUE
  LDAP-SYNTAX               boolean.&id
  LDAP-NAME                 {"zimbraUserServicesEnabled"}
  LDAP-DESC                 "whether end-user services on SOAP and LMTP interfaces are enabled"
  ID                        id-at-zimbraUserServicesEnabled }

zimbraVersion ATTRIBUTE ::= {
  WITH SYNTAX               INTEGER
  EQUALITY MATCHING RULE    integerMatch
  SINGLE VALUE              TRUE
  LDAP-SYNTAX               integer.&id
  LDAP-NAME                 {"zimbraVersion"}
  LDAP-DESC                 "account version information"
  ID                        id-at-zimbraVersion }

zimbraVersionCheckInterval ATTRIBUTE ::= {
  WITH SYNTAX               IA5String(SIZE (1..32))
  EQUALITY MATCHING RULE    caseIgnoreIA5Match
  SINGLE VALUE              TRUE
  LDAP-SYNTAX               ia5String.&id
  LDAP-NAME                 {"zimbraVersionCheckInterval"}
  LDAP-DESC                 "Time interval after which Zimbra version check detects a new version. Must be in valid duration format: {digits}{time-unit}. digits: 0-9, time-unit: [hmsd]|ms. h - hours, m - minutes, s - seconds, d - days, ms - milliseconds. If time unit is not specified, the default is s(seconds)."
  ID                        id-at-zimbraVersionCheckInterval }

zimbraVersionCheckLastAttempt ATTRIBUTE ::= {
  WITH SYNTAX               GeneralizedTime
  EQUALITY MATCHING RULE    generalizedTimeMatch
  ORDERING MATCHING RULE    generalizedTimeOrderingMatch
  SINGLE VALUE              TRUE
  LDAP-SYNTAX               generalizedTime.&id
  LDAP-NAME                 {"zimbraVersionCheckLastAttempt"}
  LDAP-DESC                 "time Zimbra version was last checked"
  ID                        id-at-zimbraVersionCheckLastAttempt }

zimbraVersionCheckLastResponse ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraVersionCheckLastResponse"}
  LDAP-DESC                 "last response of last Zimbra version check. This will be a short XML that will contain information about available updates."
  ID                        id-at-zimbraVersionCheckLastResponse }

zimbraVersionCheckLastSuccess ATTRIBUTE ::= {
  WITH SYNTAX               GeneralizedTime
  EQUALITY MATCHING RULE    generalizedTimeMatch
  ORDERING MATCHING RULE    generalizedTimeOrderingMatch
  SINGLE VALUE              TRUE
  LDAP-SYNTAX               generalizedTime.&id
  LDAP-NAME                 {"zimbraVersionCheckLastSuccess"}
  LDAP-DESC                 "time Zimbra version was last checked successfully"
  ID                        id-at-zimbraVersionCheckLastSuccess }

-- LDAP syntax length {10000} rendered as DirectoryString{10000}.
zimbraVersionCheckNotificationBody ATTRIBUTE ::= {
  WITH SYNTAX               DirectoryString{10000}
  EQUALITY MATCHING RULE    caseIgnoreMatch
  SUBSTRINGS MATCHING RULE  caseIgnoreSubstringsMatch
  SINGLE VALUE              TRUE
  LDAP-SYNTAX               directoryString.&id
  LDAP-NAME                 {"zimbraVersionCheckNotificationBody"}
  LDAP-DESC                 "template used to construct the body of an Zimbra version check notification message"
  ID                        id-at-zimbraVersionCheckNotificationBody }

zimbraVersionCheckNotificationEmail ATTRIBUTE ::= {
  WITH SYNTAX               IA5String(SIZE (1..256))
  EQUALITY MATCHING RULE    caseIgnoreIA5Match
  SUBSTRINGS MATCHING RULE  caseIgnoreSubstringsMatch
  SINGLE VALUE              TRUE
  LDAP-SYNTAX               ia5String.&id
  LDAP-NAME                 {"zimbraVersionCheckNotificationEmail"}
  LDAP-DESC                 "email address to send mail to for the Zimbra version check notification message"
  ID                        id-at-zimbraVersionCheckNotificationEmail }

-- LDAP syntax length {1000} rendered as DirectoryString{1000}.
zimbraVersionCheckNotificationEmailFrom ATTRIBUTE ::= {
  WITH SYNTAX               DirectoryString{1000}
  EQUALITY MATCHING RULE    caseIgnoreMatch
  SUBSTRINGS MATCHING RULE  caseIgnoreSubstringsMatch
  SINGLE VALUE              TRUE
  LDAP-SYNTAX               directoryString.&id
  LDAP-NAME                 {"zimbraVersionCheckNotificationEmailFrom"}
  LDAP-DESC                 "from address for the Zimbra version check notification message"
  ID                        id-at-zimbraVersionCheckNotificationEmailFrom }

-- LDAP syntax length {1000} rendered as DirectoryString{1000}.
zimbraVersionCheckNotificationSubject ATTRIBUTE ::= {
  WITH SYNTAX               DirectoryString{1000}
  EQUALITY MATCHING RULE    caseIgnoreMatch
  SUBSTRINGS MATCHING RULE  caseIgnoreSubstringsMatch
  SINGLE VALUE              TRUE
  LDAP-SYNTAX               directoryString.&id
  LDAP-NAME                 {"zimbraVersionCheckNotificationSubject"}
  LDAP-DESC                 "template used to construct the subject of an Zimbra version check notification message"
  ID                        id-at-zimbraVersionCheckNotificationSubject }

zimbraVersionCheckSendNotifications ATTRIBUTE ::= {
  WITH SYNTAX               BOOLEAN
  EQUALITY MATCHING RULE    booleanMatch
  SINGLE VALUE              TRUE
  LDAP-SYNTAX               boolean.&id
  LDAP-NAME                 {"zimbraVersionCheckSendNotifications"}
  LDAP-DESC                 "whether to send a notification message if Zimbra version check detects a new version"
  ID                        id-at-zimbraVersionCheckSendNotifications }

-- LDAP syntax length {256} rendered as DirectoryString{256}.
zimbraVersionCheckServer ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraVersionCheckServer"}
  LDAP-DESC                 "zimbraId of the server that should perform the Zimbra version checks"
  ID                        id-at-zimbraVersionCheckServer }

-- LDAP syntax length {256} rendered as DirectoryString{256}.
zimbraVersionCheckURL ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraVersionCheckURL"}
  LDAP-DESC                 "URL of the Zimbra version check script"
  ID                        id-at-zimbraVersionCheckURL }

zimbraVirtualAccountInitialPasswordSet ATTRIBUTE ::= {
  WITH SYNTAX               BOOLEAN
  EQUALITY MATCHING RULE    booleanMatch
  SINGLE VALUE              TRUE
  LDAP-SYNTAX               boolean.&id
  LDAP-NAME                 {"zimbraVirtualAccountInitialPasswordSet"}
  LDAP-DESC                 "Whether virtual user set/changed his password after an external virtual account for him is provisioned. This attribute is applicable for accounts having zimbraIsExternalVirtualAccount set to TRUE."
  ID                        id-at-zimbraVirtualAccountInitialPasswordSet }

-- LDAP syntax length {256} rendered as DirectoryString{256}.
zimbraVirtualHostname ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraVirtualHostname"}
  LDAP-DESC                 "An alias for this domain, used to determine default login domain based on URL client is visiting"
  ID                        id-at-zimbraVirtualHostname }

-- LDAP syntax length {256} rendered as DirectoryString{256}.
zimbraVirtualIPAddress ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraVirtualIPAddress"}
  LDAP-DESC                 "An virtual IP address for this domain, used to determine domain based on an IP address"
  ID                        id-at-zimbraVirtualIPAddress }

zimbraVirusBlockEncryptedArchive ATTRIBUTE ::= {
  WITH SYNTAX               BOOLEAN
  EQUALITY MATCHING RULE    booleanMatch
  SINGLE VALUE              TRUE
  LDAP-SYNTAX               boolean.&id
  LDAP-NAME                 {"zimbraVirusBlockEncryptedArchive"}
  LDAP-DESC                 "Whether to block archive files that are password protected or encrypted"
  ID                        id-at-zimbraVirusBlockEncryptedArchive }

zimbraVirusCheckEnabled ATTRIBUTE ::= {
  WITH SYNTAX               BOOLEAN
  EQUALITY MATCHING RULE    booleanMatch
  SINGLE VALUE              TRUE
  LDAP-SYNTAX               boolean.&id
  LDAP-NAME                 {"zimbraVirusCheckEnabled"}
  LDAP-DESC                 "Deprecated since: 4.5. Deprecated in favor of zimbraServiceEnabled. Orig desc: Whether to enable virus checking"
  ID                        id-at-zimbraVirusCheckEnabled }

zimbraVirusDefinitionsUpdateFrequency ATTRIBUTE ::= {
  WITH SYNTAX               IA5String(SIZE (1..32))
  EQUALITY MATCHING RULE    caseIgnoreIA5Match
  SINGLE VALUE              TRUE
  LDAP-SYNTAX               ia5String.&id
  LDAP-NAME                 {"zimbraVirusDefinitionsUpdateFrequency"}
  LDAP-DESC                 "how often the virus definitions are updated. Must be in valid duration format: {digits}{time-unit}. digits: 0-9, time-unit: [hmsd]|ms. h - hours, m - minutes, s - seconds, d - days, ms - milliseconds. If time unit is not specified, the default is s(seconds)."
  ID                        id-at-zimbraVirusDefinitionsUpdateFrequency }

zimbraVirusWarnAdmin ATTRIBUTE ::= {
  WITH SYNTAX               BOOLEAN
  EQUALITY MATCHING RULE    booleanMatch
  SINGLE VALUE              TRUE
  LDAP-SYNTAX               boolean.&id
  LDAP-NAME                 {"zimbraVirusWarnAdmin"}
  LDAP-DESC                 "Whether to email admin on virus detection"
  ID                        id-at-zimbraVirusWarnAdmin }

zimbraVirusWarnRecipient ATTRIBUTE ::= {
  WITH SYNTAX               BOOLEAN
  EQUALITY MATCHING RULE    booleanMatch
  SINGLE VALUE              TRUE
  LDAP-SYNTAX               boolean.&id
  LDAP-NAME                 {"zimbraVirusWarnRecipient"}
  LDAP-DESC                 "Whether to email recipient on virus detection"
  ID                        id-at-zimbraVirusWarnRecipient }

-- LDAP syntax length {256} rendered as DirectoryString{256}.
zimbraWebClientAdminReference ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraWebClientAdminReference"}
  LDAP-DESC                 "link for admin users in web client"
  ID                        id-at-zimbraWebClientAdminReference }

-- LDAP syntax length {256} rendered as DirectoryString{256}.
zimbraWebClientLoginURL ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraWebClientLoginURL"}
  LDAP-DESC                 "login URL for web client to send the user to upon failed login, auth expired, or no/invalid auth"
  ID                        id-at-zimbraWebClientLoginURL }

zimbraWebClientLoginURLAllowedIP ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraWebClientLoginURLAllowedIP"}
  LDAP-DESC                 "regex for allowed client IP addresses for honoring zimbraWebClientLoginURL. If not set, all IP addresses are allowed. If multiple values are set, an IP address is allowed as long as it matches any one of the values."
  ID                        id-at-zimbraWebClientLoginURLAllowedIP }

zimbraWebClientLoginURLAllowedUA ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraWebClientLoginURLAllowedUA"}
  LDAP-DESC                 "regex to be matched for allowed user agents for honoring zimbraWebClientLoginURL. If not set, all UAs are allowed. If multiple values are set, an UA is allowed as long as it matches any one of the values. e.g. "".*Windows NT.*Firefox/3.*"" will match firefox 3 or later browsers on Windows. "".*MSIE.*Windows NT.*"" will match IE browsers on Windows."
  ID                        id-at-zimbraWebClientLoginURLAllowedUA }

-- LDAP syntax length {256} rendered as DirectoryString{256}.
zimbraWebClientLogoutURL ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraWebClientLogoutURL"}
  LDAP-DESC                 "logout URL for web client to send the user to upon explicit logging out"
  ID                        id-at-zimbraWebClientLogoutURL }

zimbraWebClientLogoutURLAllowedIP ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraWebClientLogoutURLAllowedIP"}
  LDAP-DESC                 "regex for allowed client IP addresses for honoring zimbraWebClientLogoutURL. If not set, all IP addresses are allowed. If multiple values are set, an IP address is allowed as long as it matches any one of the values."
  ID                        id-at-zimbraWebClientLogoutURLAllowedIP }

zimbraWebClientLogoutURLAllowedUA ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraWebClientLogoutURLAllowedUA"}
  LDAP-DESC                 "regex to be matched for allowed user agents for honoring zimbraWebClientLogoutURL. If not set, all UAs are allowed. If multiple values are set, an UA is allowed as long as it matches any one of the values. e.g. "".*Windows NT.*Firefox/3.*"" will match firefox 3 or later browsers on Windows. "".*MSIE.*Windows NT.*"" will match IE browsers on Windows."
  ID                        id-at-zimbraWebClientLogoutURLAllowedUA }

zimbraWebClientMaxInputBufferLength ATTRIBUTE ::= {
  WITH SYNTAX               INTEGER
  EQUALITY MATCHING RULE    integerMatch
  SINGLE VALUE              TRUE
  LDAP-SYNTAX               integer.&id
  LDAP-NAME                 {"zimbraWebClientMaxInputBufferLength"}
  LDAP-DESC                 "max input buffer length for web client"
  ID                        id-at-zimbraWebClientMaxInputBufferLength }

zimbraWebClientOfflineSyncMaxDays ATTRIBUTE ::= {
  WITH SYNTAX               INTEGER
  EQUALITY MATCHING RULE    integerMatch
  SINGLE VALUE              TRUE
  LDAP-SYNTAX               integer.&id
  LDAP-NAME                 {"zimbraWebClientOfflineSyncMaxDays"}
  LDAP-DESC                 "limit for the number of days that the web client would use to sync any mail folder's data for offline use"
  ID                        id-at-zimbraWebClientOfflineSyncMaxDays }

zimbraWebClientShowOfflineLink ATTRIBUTE ::= {
  WITH SYNTAX               BOOLEAN
  EQUALITY MATCHING RULE    booleanMatch
  SINGLE VALUE              TRUE
  LDAP-SYNTAX               boolean.&id
  LDAP-NAME                 {"zimbraWebClientShowOfflineLink"}
  LDAP-DESC                 "whether or not to show link to offline version in the web UI top bar"
  ID                        id-at-zimbraWebClientShowOfflineLink }

-- LDAP syntax length {512} rendered as DirectoryString{512}.
zimbraWebClientURL ATTRIBUTE ::= {
  WITH SYNTAX               DirectoryString{512}
  EQUALITY MATCHING RULE    caseIgnoreMatch
  SUBSTRINGS MATCHING RULE  caseIgnoreSubstringsMatch
  SINGLE VALUE              TRUE
  LDAP-SYNTAX               directoryString.&id
  LDAP-NAME                 {"zimbraWebClientURL"}
  LDAP-DESC                 "weclient URL to directly connect when making service to JS calls from mail server in split mode"
  ID                        id-at-zimbraWebClientURL }

zimbraWebGzipEnabled ATTRIBUTE ::= {
  WITH SYNTAX               BOOLEAN
  EQUALITY MATCHING RULE    booleanMatch
  SINGLE VALUE              TRUE
  LDAP-SYNTAX               boolean.&id
  LDAP-NAME                 {"zimbraWebGzipEnabled"}
  LDAP-DESC                 "Whether or not to gzip static web content. Defaults to true."
  ID                        id-at-zimbraWebGzipEnabled }

zimbraXMPPComponentCategory ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraXMPPComponentCategory"}
  LDAP-DESC                 "XMPP Category of the component"
  ID                        id-at-zimbraXMPPComponentCategory }

zimbraXMPPComponentClassName ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraXMPPComponentClassName"}
  LDAP-DESC                 "class name of the XMPP component"
  ID                        id-at-zimbraXMPPComponentClassName }

zimbraXMPPComponentFeatures ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraXMPPComponentFeatures"}
  LDAP-DESC                 "XMPP Type of the component"
  ID                        id-at-zimbraXMPPComponentFeatures }

zimbraXMPPComponentName ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraXMPPComponentName"}
  LDAP-DESC                 "Name of the XMPP Component"
  ID                        id-at-zimbraXMPPComponentName }

zimbraXMPPComponentType ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"zimbraXMPPComponentType"}
  LDAP-DESC                 "XMPP Type of the component"
  ID                        id-at-zimbraXMPPComponentType }

zimbraXMPPEnabled ATTRIBUTE ::= {
  WITH SYNTAX               BOOLEAN
  EQUALITY MATCHING RULE    booleanMatch
  SINGLE VALUE              TRUE
  LDAP-SYNTAX               boolean.&id
  LDAP-NAME                 {"zimbraXMPPEnabled"}
  LDAP-DESC                 "Enable XMPP support for IM"
  ID                        id-at-zimbraXMPPEnabled }

zimbraXMPPServerDialbackKey ATTRIBUTE ::= {
  WITH SYNTAX               OCTET STRING (SIZE (1..128))
  EQUALITY MATCHING RULE    octetStringMatch
  LDAP-SYNTAX               octetString.&id
  LDAP-NAME                 {"zimbraXMPPServerDialbackKey"}
  LDAP-DESC                 "Shared Secret for XMPP Server Dialback Protocol"
  ID                        id-at-zimbraXMPPServerDialbackKey }

-- LDAP syntax length {256} rendered as DirectoryString{256}.
zimbraYahooId ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraYahooId"}
  LDAP-DESC                 "Yahoo ID"
  ID                        id-at-zimbraYahooId }

-- LDAP syntax length {256} rendered as DirectoryString{256}.
zimbraZimletAvailableZimlets ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraZimletAvailableZimlets"}
  LDAP-DESC                 "List of Zimlets available to this COS Values can be prefixed with ! or + or - !: mandatory + (or no prefix): enabled by default -: disabled by default"
  ID                        id-at-zimbraZimletAvailableZimlets }

-- LDAP syntax length {10240} rendered as DirectoryString{10240}.
zimbraZimletContentObject ATTRIBUTE ::= {
  WITH SYNTAX               DirectoryString{10240}
  EQUALITY MATCHING RULE    caseIgnoreMatch
  SUBSTRINGS MATCHING RULE  caseIgnoreSubstringsMatch
  SINGLE VALUE              TRUE
  LDAP-SYNTAX               directoryString.&id
  LDAP-NAME                 {"zimbraZimletContentObject"}
  LDAP-DESC                 "The content object section in the Zimlet description"
  ID                        id-at-zimbraZimletContentObject }

zimbraZimletDataSensitiveInMixedModeDisabled ATTRIBUTE ::= {
  WITH SYNTAX               BOOLEAN
  EQUALITY MATCHING RULE    booleanMatch
  SINGLE VALUE              TRUE
  LDAP-SYNTAX               boolean.&id
  LDAP-NAME                 {"zimbraZimletDataSensitiveInMixedModeDisabled"}
  LDAP-DESC                 "whether zimlets that send sensitive data are disabled in ""mixed"" zimbraMailMode"
  ID                        id-at-zimbraZimletDataSensitiveInMixedModeDisabled }

-- LDAP syntax length {256} rendered as DirectoryString{256}.
zimbraZimletDescription ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraZimletDescription"}
  LDAP-DESC                 "Zimlet description"
  ID                        id-at-zimbraZimletDescription }

-- LDAP syntax length {256} rendered as DirectoryString{256}.
zimbraZimletDomainAvailableZimlets ATTRIBUTE ::= {
  WITH SYNTAX               DirectoryString{256}
  EQUALITY MATCHING RULE    caseIgnoreMatch
  SUBSTRINGS MATCHING RULE  caseIgnoreSubstringsMatch
  LDAP-SYNTAX               directoryString.&id
  LDAP-NAME                 {"zimbraZimletDomainAvailableZimlets"}
  LDAP-DESC                 "List of Zimlets available to this domain. Zimlets available to accounts in the domain is the union of account/cos attribute zimbraZimletAvailableZimlets and this attribute. See zimbraZimletAvailableZimlets for value format."
  ID                        id-at-zimbraZimletDomainAvailableZimlets }

zimbraZimletEnabled ATTRIBUTE ::= {
  WITH SYNTAX               BOOLEAN
  EQUALITY MATCHING RULE    booleanMatch
  SINGLE VALUE              TRUE
  LDAP-SYNTAX               boolean.&id
  LDAP-NAME                 {"zimbraZimletEnabled"}
  LDAP-DESC                 "whether this Zimlet is enabled"
  ID                        id-at-zimbraZimletEnabled }

-- LDAP syntax length {256} rendered as DirectoryString{256}.
zimbraZimletHandlerClass ATTRIBUTE ::= {
  WITH SYNTAX               DirectoryString{256}
  EQUALITY MATCHING RULE    caseExactMatch
  SUBSTRINGS MATCHING RULE  caseExactSubstringsMatch
  SINGLE VALUE              TRUE
  LDAP-SYNTAX               directoryString.&id
  LDAP-NAME                 {"zimbraZimletHandlerClass"}
  LDAP-DESC                 "The handler class for server side Zimlet extension"
  ID                        id-at-zimbraZimletHandlerClass }

-- LDAP syntax length {10240} rendered as DirectoryString{10240}.
zimbraZimletHandlerConfig ATTRIBUTE ::= {
  WITH SYNTAX               DirectoryString{10240}
  EQUALITY MATCHING RULE    caseIgnoreMatch
  SUBSTRINGS MATCHING RULE  caseIgnoreSubstringsMatch
  LDAP-SYNTAX               directoryString.&id
  LDAP-NAME                 {"zimbraZimletHandlerConfig"}
  LDAP-DESC                 "The global config for the Zimlet"
  ID                        id-at-zimbraZimletHandlerConfig }

zimbraZimletIndexingEnabled ATTRIBUTE ::= {
  WITH SYNTAX               BOOLEAN
  EQUALITY MATCHING RULE    booleanMatch
  SINGLE VALUE              TRUE
  LDAP-SYNTAX               boolean.&id
  LDAP-NAME                 {"zimbraZimletIndexingEnabled"}
  LDAP-DESC                 "Whether server side keyword indexing enabled"
  ID                        id-at-zimbraZimletIndexingEnabled }

zimbraZimletIsExtension ATTRIBUTE ::= {
  WITH SYNTAX               BOOLEAN
  EQUALITY MATCHING RULE    booleanMatch
  SINGLE VALUE              TRUE
  LDAP-SYNTAX               boolean.&id
  LDAP-NAME                 {"zimbraZimletIsExtension"}
  LDAP-DESC                 "Whether this zimlet is an extension"
  ID                        id-at-zimbraZimletIsExtension }

zimbraZimletJspEnabled ATTRIBUTE ::= {
  WITH SYNTAX               BOOLEAN
  EQUALITY MATCHING RULE    booleanMatch
  SINGLE VALUE              TRUE
  LDAP-SYNTAX               boolean.&id
  LDAP-NAME                 {"zimbraZimletJspEnabled"}
  LDAP-DESC                 "Whether to enable JSP compilation for Zimlets (i.e. for /zimlet webapp)"
  ID                        id-at-zimbraZimletJspEnabled }

-- LDAP syntax length {256} rendered as DirectoryString{256}.
zimbraZimletKeyword ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraZimletKeyword"}
  LDAP-DESC                 "Server side object keyword used for indexing and search for this Zimlet"
  ID                        id-at-zimbraZimletKeyword }

zimbraZimletLoadSynchronously ATTRIBUTE ::= {
  WITH SYNTAX               BOOLEAN
  EQUALITY MATCHING RULE    booleanMatch
  SINGLE VALUE              TRUE
  LDAP-SYNTAX               boolean.&id
  LDAP-NAME                 {"zimbraZimletLoadSynchronously"}
  LDAP-DESC                 "Whether to load zimlets synchronously in the web client. If set to TRUE, users are not allowed to use the core app before zimlets are loaded. If set to FALSE, zimlets are loaded in the background and users are allowed to use the core app before all zimlets finish loading."
  ID                        id-at-zimbraZimletLoadSynchronously }

-- LDAP syntax length {10240} rendered as DirectoryString{10240}.
zimbraZimletPanelItem ATTRIBUTE ::= {
  WITH SYNTAX               DirectoryString{10240}
  EQUALITY MATCHING RULE    caseIgnoreMatch
  SUBSTRINGS MATCHING RULE  caseIgnoreSubstringsMatch
  SINGLE VALUE              TRUE
  LDAP-SYNTAX               directoryString.&id
  LDAP-NAME                 {"zimbraZimletPanelItem"}
  LDAP-DESC                 "The panel item section in the Zimlet description"
  ID                        id-at-zimbraZimletPanelItem }

-- LDAP syntax length {32} rendered as DirectoryString{32}.
zimbraZimletPriority ATTRIBUTE ::= {
  WITH SYNTAX               DirectoryString{32}
  EQUALITY MATCHING RULE    caseIgnoreMatch
  SUBSTRINGS MATCHING RULE  caseIgnoreSubstringsMatch
  SINGLE VALUE              TRUE
  LDAP-SYNTAX               directoryString.&id
  LDAP-NAME                 {"zimbraZimletPriority"}
  LDAP-DESC                 "Object match priority"
  ID                        id-at-zimbraZimletPriority }

-- LDAP syntax length {256} rendered as DirectoryString{256}.
zimbraZimletScript ATTRIBUTE ::= {
  WITH SYNTAX               DirectoryString{256}
  EQUALITY MATCHING RULE    caseExactMatch
  SUBSTRINGS MATCHING RULE  caseExactSubstringsMatch
  LDAP-SYNTAX               directoryString.&id
  LDAP-NAME                 {"zimbraZimletScript"}
  LDAP-DESC                 "URL of extra scripts used by the Zimlet"
  ID                        id-at-zimbraZimletScript }

-- LDAP syntax length {256} rendered as DirectoryString{256}.
zimbraZimletServerIndexRegex ATTRIBUTE ::= {
  WITH SYNTAX               DirectoryString{256}
  EQUALITY MATCHING RULE    caseExactMatch
  SUBSTRINGS MATCHING RULE  caseExactSubstringsMatch
  SINGLE VALUE              TRUE
  LDAP-SYNTAX               directoryString.&id
  LDAP-NAME                 {"zimbraZimletServerIndexRegex"}
  LDAP-DESC                 "Regex of content object"
  ID                        id-at-zimbraZimletServerIndexRegex }

zimbraZimletStoreMatched ATTRIBUTE ::= {
  WITH SYNTAX               BOOLEAN
  EQUALITY MATCHING RULE    booleanMatch
  SINGLE VALUE              TRUE
  LDAP-SYNTAX               boolean.&id
  LDAP-NAME                 {"zimbraZimletStoreMatched"}
  LDAP-DESC                 "Whether store is matched for this type"
  ID                        id-at-zimbraZimletStoreMatched }

-- LDAP syntax length {1024} rendered as DirectoryString{1024}.
zimbraZimletTarget ATTRIBUTE ::= {
  WITH SYNTAX               DirectoryString{1024}
  EQUALITY MATCHING RULE    caseExactMatch
  SUBSTRINGS MATCHING RULE  caseExactSubstringsMatch
  LDAP-SYNTAX               directoryString.&id
  LDAP-NAME                 {"zimbraZimletTarget"}
  LDAP-DESC                 "Zimlet target apps"
  ID                        id-at-zimbraZimletTarget }

-- LDAP syntax length {5120} rendered as DirectoryString{5120}.
zimbraZimletUserProperties ATTRIBUTE ::= {
  WITH SYNTAX               DirectoryString{5120}
  EQUALITY MATCHING RULE    caseExactMatch
  SUBSTRINGS MATCHING RULE  caseExactSubstringsMatch
  LDAP-SYNTAX               directoryString.&id
  LDAP-NAME                 {"zimbraZimletUserProperties"}
  LDAP-DESC                 "User properties for Zimlets"
  ID                        id-at-zimbraZimletUserProperties }

-- LDAP syntax length {256} rendered as DirectoryString{256}.
zimbraZimletVersion ATTRIBUTE ::= {
  WITH SYNTAX               DirectoryString{256}
  EQUALITY MATCHING RULE    caseIgnoreMatch
  SUBSTRINGS MATCHING RULE  caseIgnoreSubstringsMatch
  SINGLE VALUE              TRUE
  LDAP-SYNTAX               directoryString.&id
  LDAP-NAME                 {"zimbraZimletVersion"}
  LDAP-DESC                 "Version of the Zimlet"
  ID                        id-at-zimbraZimletVersion }

zimbraZookeeperClientServerList ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zimbraZookeeperClientServerList"}
  LDAP-DESC                 "list of host:port for zookeeper servers; set to empty value to disable the use of zookeeper"
  ID                        id-at-zimbraZookeeperClientServerList }

-- Object classes

zimbraMailRecipient OBJECT-CLASS ::= {
  SUBCLASS OF               { top }
  KIND                      auxiliary
  MAY CONTAIN               { zimbraHideInGal
                              | zimbraLocale
                              | zimbraMailAddress
                              | zimbraMailAlias
                              | zimbraMailCanonicalAddress
                              | zimbraMailCatchAllAddress
                              | zimbraMailCatchAllCanonicalAddress
                              | zimbraMailCatchAllForwardingAddress
                              | zimbraMailDeliveryAddress
                              | zimbraMailForwardingAddress
                              | zimbraMailHost
                              | zimbraMailStatus
                              | zimbraMailTransport }
  LDAP-NAME                 {"zimbraMailRecipient"}
  LDAP-DESC                 "Mail recipient object"
  ID                        id-oc-zimbraMailRecipient }

-- MAY gn: LDAP name "gn" was taken as givenName. schema2ldif/core.schema lists it on 2.5.4.42, which is already givenName in SelectedAttributeTypes.
zimbraAccount OBJECT-CLASS ::= {
  SUBCLASS OF               { zimbraMailRecipient }
  KIND                      auxiliary
  MUST CONTAIN              { uid
                              | zimbraAccountStatus
                              | zimbraId }
  MAY CONTAIN               { countryName
                              | commonName
                              | co
                              | company
                              | description
                              | destinationIndicator
                              | displayName
                              | facsimileTelephoneNumber
                              | givenName
                              | homePhone
                              | initials
                              | internationalISDNNumber
                              | localityName
                              | mail
                              | mobile
                              | organizationName
                              | organizationalUnitName
                              | pager
                              | physicalDeliveryOfficeName
                              | postOfficeBox
                              | postalAddress
                              | postalCode
                              | preferredDeliveryMethod
                              | registeredAddress
                              | surname
                              | stateOrProvinceName
                              | streetAddress
                              | streetAddress
                              | telephoneNumber
                              | teletexTerminalIdentifier
                              | telexNumber
                              | title
                              | userCertificate
                              | userPassword
                              | userSMIMECertificate
                              | x121Address
                              | zimbraACE
                              | zimbraAccountCalendarUserType
                              | zimbraAdminAuthTokenLifetime
                              | zimbraAdminConsoleUIComponents
                              | zimbraAdminSavedSearches
                              | zimbraAllowAnyFromAddress
                              | zimbraAllowFromAddress
                              | zimbraArchiveAccount
                              | zimbraArchiveAccountDateTemplate
                              | zimbraArchiveAccountNameTemplate
                              | zimbraArchiveEnabled
                              | zimbraAttachmentsBlocked
                              | zimbraAttachmentsIndexingEnabled
                              | zimbraAttachmentsViewInHtmlOnly
                              | zimbraAuthLdapExternalDn
                              | zimbraAuthTokenLifetime
                              | zimbraAuthTokenValidityValue
                              | zimbraAuthTokens
                              | zimbraAvailableLocale
                              | zimbraAvailableSkin
                              | zimbraBatchedIndexingSize
                              | zimbraCOSId
                              | zimbraCalendarCalDavSharedFolderCacheDuration
                              | zimbraCalendarCalDavSyncEnd
                              | zimbraCalendarCalDavSyncStart
                              | zimbraCalendarKeepExceptionsOnSeriesTimeChange
                              | zimbraCalendarLocationDisabledFields
                              | zimbraCalendarMaxRevisions
                              | zimbraCalendarReminderDeviceEmail
                              | zimbraCalendarResourceDoubleBookingAllowed
                              | zimbraCalendarShowResourceTabs
                              | zimbraChildAccount
                              | zimbraChildVisibleAccount
                              | zimbraCommunityAPIClientID
                              | zimbraCommunityAPIClientSecret
                              | zimbraCommunityBaseURL
                              | zimbraCommunityHomeURL
                              | zimbraCommunityID
                              | zimbraCommunityUsernameMapping
                              | zimbraContactAutoCompleteEmailFields
                              | zimbraContactAutoCompleteMaxResults
                              | zimbraContactEmailFields
                              | zimbraContactMaxNumEntries
                              | zimbraContactRankingTableSize
                              | zimbraConverterHints
                              | zimbraCreateTimestamp
                              | zimbraCsrfTokenData
                              | zimbraCustomerCareTier
                              | zimbraDataSourceCaldavPollingInterval
                              | zimbraDataSourceCalendarPollingInterval
                              | zimbraDataSourceGalPollingInterval
                              | zimbraDataSourceImapPollingInterval
                              | zimbraDataSourceImportOnLogin
                              | zimbraDataSourceLivePollingInterval
                              | zimbraDataSourceMaxNumEntries
                              | zimbraDataSourceMinPollingInterval
                              | zimbraDataSourcePollingInterval
                              | zimbraDataSourcePop3PollingInterval
                              | zimbraDataSourceRssPollingInterval
                              | zimbraDataSourceYabPollingInterval
                              | zimbraDebugInfo
                              | zimbraDefaultFolderFlags
                              | zimbraDeviceAllowedPasscodeLockoutDuration
                              | zimbraDeviceCalendarSoftDeleteExcludePattern
                              | zimbraDeviceFileOpenWithEnabled
                              | zimbraDeviceLockWhenInactive
                              | zimbraDeviceOfflineCacheEnabled
                              | zimbraDevicePasscodeEnabled
                              | zimbraDevicePasscodeLockoutDuration
                              | zimbraDomainAdminMaxMailQuota
                              | zimbraDumpsterEnabled
                              | zimbraDumpsterPurgeEnabled
                              | zimbraDumpsterUserVisibleAge
                              | zimbraExcludeFromCMBSearch
                              | zimbraExternalAccountDisabledTime
                              | zimbraExternalAccountLifetimeAfterDisabled
                              | zimbraExternalImapHostname
                              | zimbraExternalImapPort
                              | zimbraExternalImapSSLHostname
                              | zimbraExternalImapSSLPort
                              | zimbraExternalPop3Hostname
                              | zimbraExternalPop3Port
                              | zimbraExternalPop3SSLHostname
                              | zimbraExternalPop3SSLPort
                              | zimbraExternalShareDomainWhitelistEnabled
                              | zimbraExternalShareLifetime
                              | zimbraExternalShareWhitelistDomain
                              | zimbraExternalSharingEnabled
                              | zimbraExternalUserMailAddress
                              | zimbraFeatureAdminMailEnabled
                              | zimbraFeatureAdvancedSearchEnabled
                              | zimbraFeatureAntispamEnabled
                              | zimbraFeatureBriefcaseDocsEnabled
                              | zimbraFeatureBriefcaseSlidesEnabled
                              | zimbraFeatureBriefcaseSpreadsheetEnabled
                              | zimbraFeatureBriefcasesEnabled
                              | zimbraFeatureCalendarEnabled
                              | zimbraFeatureCalendarReminderDeviceEmailEnabled
                              | zimbraFeatureCalendarUpsellEnabled
                              | zimbraFeatureCalendarUpsellURL
                              | zimbraFeatureChangePasswordEnabled
                              | zimbraFeatureComposeInNewWindowEnabled
                              | zimbraFeatureConfirmationPageEnabled
                              | zimbraFeatureContactsDetailedSearchEnabled
                              | zimbraFeatureContactsEnabled
                              | zimbraFeatureContactsUpsellEnabled
                              | zimbraFeatureContactsUpsellURL
                              | zimbraFeatureConversationsEnabled
                              | zimbraFeatureCrocodocEnabled
                              | zimbraFeatureDiscardInFiltersEnabled
                              | zimbraFeatureDistributionListExpandMembersEnabled
                              | zimbraFeatureDistributionListFolderEnabled
                              | zimbraFeatureEwsEnabled
                              | zimbraFeatureExportFolderEnabled
                              | zimbraFeatureExternalFeedbackEnabled
                              | zimbraFeatureFiltersEnabled
                              | zimbraFeatureFlaggingEnabled
                              | zimbraFeatureFreeBusyViewEnabled
                              | zimbraFeatureFromDisplayEnabled
                              | zimbraFeatureGalAutoCompleteEnabled
                              | zimbraFeatureGalEnabled
                              | zimbraFeatureGalSyncEnabled
                              | zimbraFeatureGroupCalendarEnabled
                              | zimbraFeatureHtmlComposeEnabled
                              | zimbraFeatureIMEnabled
                              | zimbraFeatureIdentitiesEnabled
                              | zimbraFeatureImapDataSourceEnabled
                              | zimbraFeatureImportExportFolderEnabled
                              | zimbraFeatureImportFolderEnabled
                              | zimbraFeatureInitialSearchPreferenceEnabled
                              | zimbraFeatureInstantNotify
                              | zimbraFeatureMAPIConnectorEnabled
                              | zimbraFeatureMailEnabled
                              | zimbraFeatureMailForwardingEnabled
                              | zimbraFeatureMailForwardingInFiltersEnabled
                              | zimbraFeatureMailPollingIntervalPreferenceEnabled
                              | zimbraFeatureMailPriorityEnabled
                              | zimbraFeatureMailSendLaterEnabled
                              | zimbraFeatureMailUpsellEnabled
                              | zimbraFeatureMailUpsellURL
                              | zimbraFeatureManageSMIMECertificateEnabled
                              | zimbraFeatureManageZimlets
                              | zimbraFeatureMobilePolicyEnabled
                              | zimbraFeatureMobileSyncEnabled
                              | zimbraFeatureNewAddrBookEnabled
                              | zimbraFeatureNewMailNotificationEnabled
                              | zimbraFeatureNotebookEnabled
                              | zimbraFeatureOpenMailInNewWindowEnabled
                              | zimbraFeatureOptionsEnabled
                              | zimbraFeatureOutOfOfficeReplyEnabled
                              | zimbraFeaturePeopleSearchEnabled
                              | zimbraFeaturePop3DataSourceEnabled
                              | zimbraFeaturePortalEnabled
                              | zimbraFeaturePriorityInboxEnabled
                              | zimbraFeatureReadReceiptsEnabled
                              | zimbraFeatureSMIMEEnabled
                              | zimbraFeatureSavedSearchesEnabled
                              | zimbraFeatureSharingEnabled
                              | zimbraFeatureShortcutAliasesEnabled
                              | zimbraFeatureSignaturesEnabled
                              | zimbraFeatureSkinChangeEnabled
                              | zimbraFeatureSocialEnabled
                              | zimbraFeatureSocialExternalEnabled
                              | zimbraFeatureSocialExternalURL
                              | zimbraFeatureSocialFiltersEnabled
                              | zimbraFeatureSocialName
                              | zimbraFeatureSocialcastEnabled
                              | zimbraFeatureTaggingEnabled
                              | zimbraFeatureTasksEnabled
                              | zimbraFeatureTouchClientEnabled
                              | zimbraFeatureViewInHtmlEnabled
                              | zimbraFeatureVoiceChangePinEnabled
                              | zimbraFeatureVoiceEnabled
                              | zimbraFeatureVoiceUpsellEnabled
                              | zimbraFeatureVoiceUpsellURL
                              | zimbraFeatureWebClientOfflineAccessEnabled
                              | zimbraFeatureWebSearchEnabled
                              | zimbraFeatureZimbraAssistantEnabled
                              | zimbraFileAndroidCrashReportingEnabled
                              | zimbraFileDeletionNotificationBody
                              | zimbraFileDeletionNotificationSubject
                              | zimbraFileExpirationWarningBody
                              | zimbraFileExpirationWarningSubject
                              | zimbraFileExpirationWarningThreshold
                              | zimbraFileExternalShareLifetime
                              | zimbraFileIOSCrashReportingEnabled
                              | zimbraFileLifetime
                              | zimbraFilePreviewMaxSize
                              | zimbraFilePublicShareLifetime
                              | zimbraFileShareLifetime
                              | zimbraFileUploadMaxSizePerFile
                              | zimbraFileVersionLifetime
                              | zimbraFileVersioningEnabled
                              | zimbraFilterBatchSize
                              | zimbraFilterSleepInterval
                              | zimbraForceClearCookies
                              | zimbraForeignPrincipal
                              | zimbraFreebusyExchangeAuthPassword
                              | zimbraFreebusyExchangeAuthScheme
                              | zimbraFreebusyExchangeAuthUsername
                              | zimbraFreebusyExchangeCachedInterval
                              | zimbraFreebusyExchangeCachedIntervalStart
                              | zimbraFreebusyExchangeURL
                              | zimbraFreebusyExchangeUserOrg
                              | zimbraFreebusyLocalMailboxNotActive
                              | zimbraGalSyncAccountBasedAutoCompleteEnabled
                              | zimbraIMAvailableInteropGateways
                              | zimbraIMService
                              | zimbraIdentityMaxNumEntries
                              | zimbraImapEnabled
                              | zimbraInterceptAddress
                              | zimbraInterceptBody
                              | zimbraInterceptFrom
                              | zimbraInterceptSendHeadersOnly
                              | zimbraInterceptSubject
                              | zimbraInternalSendersDomain
                              | zimbraIsAdminAccount
                              | zimbraIsCustomerCareAccount
                              | zimbraIsDelegatedAdminAccount
                              | zimbraIsDomainAdminAccount
                              | zimbraIsExternalVirtualAccount
                              | zimbraIsSystemAccount
                              | zimbraIsSystemResource
                              | zimbraJunkMessagesIndexingEnabled
                              | zimbraLastLogonTimestamp
                              | zimbraLocale
                              | zimbraLogOutFromAllServers
                              | zimbraMailAllowReceiveButNotSendWhenOverQuota
                              | zimbraMailBlacklistMaxNumEntries
                              | zimbraMailDumpsterLifetime
                              | zimbraMailForwardingAddressMaxLength
                              | zimbraMailForwardingAddressMaxNumAddrs
                              | zimbraMailHighlightObjectsMaxSize
                              | zimbraMailIdleSessionTimeout
                              | zimbraMailMessageLifetime
                              | zimbraMailMinPollingInterval
                              | zimbraMailOutgoingSieveScript
                              | zimbraMailPurgeUseChangeDateForSpam
                              | zimbraMailPurgeUseChangeDateForTrash
                              | zimbraMailQuota
                              | zimbraMailSieveScript
                              | zimbraMailSignatureMaxLength
                              | zimbraMailSpamLifetime
                              | zimbraMailThreadingAlgorithm
                              | zimbraMailTrashLifetime
                              | zimbraMailTrustedSenderListMaxNumEntries
                              | zimbraMailWhitelistMaxNumEntries
                              | zimbraMailboxLocationBeforeMove
                              | zimbraMaxContactsPerPage
                              | zimbraMaxMailItemsPerPage
                              | zimbraMaxVoiceItemsPerPage
                              | zimbraMemberOf
                              | zimbraMobileAttachSkippedItemEnabled
                              | zimbraMobileForceProtocol25
                              | zimbraMobileForceSamsungProtocol25
                              | zimbraMobileItemsToTrackPerFolderMaxSize
                              | zimbraMobileMetadataMaxSizeEnabled
                              | zimbraMobileNotificationAdminAddress
                              | zimbraMobileNotificationEnabled
                              | zimbraMobileOutlookSyncEnabled
                              | zimbraMobilePolicyAllowBluetooth
                              | zimbraMobilePolicyAllowBrowser
                              | zimbraMobilePolicyAllowCamera
                              | zimbraMobilePolicyAllowConsumerEmail
                              | zimbraMobilePolicyAllowDesktopSync
                              | zimbraMobilePolicyAllowHTMLEmail
                              | zimbraMobilePolicyAllowInternetSharing
                              | zimbraMobilePolicyAllowIrDA
                              | zimbraMobilePolicyAllowNonProvisionableDevices
                              | zimbraMobilePolicyAllowPOPIMAPEmail
                              | zimbraMobilePolicyAllowPartialProvisioning
                              | zimbraMobilePolicyAllowRemoteDesktop
                              | zimbraMobilePolicyAllowSMIMEEncryptionAlgorithmNegotiation
                              | zimbraMobilePolicyAllowSMIMESoftCerts
                              | zimbraMobilePolicyAllowSimpleDevicePassword
                              | zimbraMobilePolicyAllowStorageCard
                              | zimbraMobilePolicyAllowTextMessaging
                              | zimbraMobilePolicyAllowUnsignedApplications
                              | zimbraMobilePolicyAllowUnsignedInstallationPackages
                              | zimbraMobilePolicyAllowWiFi
                              | zimbraMobilePolicyAlphanumericDevicePasswordRequired
                              | zimbraMobilePolicyApprovedApplication
                              | zimbraMobilePolicyApprovedApplicationList
                              | zimbraMobilePolicyDeviceEncryptionEnabled
                              | zimbraMobilePolicyDevicePasswordEnabled
                              | zimbraMobilePolicyDevicePasswordExpiration
                              | zimbraMobilePolicyDevicePasswordHistory
                              | zimbraMobilePolicyMaxCalendarAgeFilter
                              | zimbraMobilePolicyMaxDevicePasswordFailedAttempts
                              | zimbraMobilePolicyMaxEmailAgeFilter
                              | zimbraMobilePolicyMaxEmailBodyTruncationSize
                              | zimbraMobilePolicyMaxEmailHTMLBodyTruncationSize
                              | zimbraMobilePolicyMaxInactivityTimeDeviceLock
                              | zimbraMobilePolicyMinDevicePasswordComplexCharacters
                              | zimbraMobilePolicyMinDevicePasswordLength
                              | zimbraMobilePolicyPasswordRecoveryEnabled
                              | zimbraMobilePolicyRefreshInterval
                              | zimbraMobilePolicyRequireDeviceEncryption
                              | zimbraMobilePolicyRequireEncryptedSMIMEMessages
                              | zimbraMobilePolicyRequireEncryptionSMIMEAlgorithm
                              | zimbraMobilePolicyRequireManualSyncWhenRoaming
                              | zimbraMobilePolicyRequireSignedSMIMEAlgorithm
                              | zimbraMobilePolicyRequireSignedSMIMEMessages
                              | zimbraMobilePolicyRequireStorageCardEncryption
                              | zimbraMobilePolicySuppressDeviceEncryption
                              | zimbraMobilePolicyUnapprovedInROMApplication
                              | zimbraMobileShareContactEnabled
                              | zimbraMobileSmartForwardRFC822Enabled
                              | zimbraMobileSyncKeyFormatConvertedFolders
                              | zimbraMobileSyncRedoMaxAttempts
                              | zimbraMobileTombstoneEnabled
                              | zimbraNewMailNotificationBody
                              | zimbraNewMailNotificationFrom
                              | zimbraNewMailNotificationSubject
                              | zimbraNotebookMaxRevisions
                              | zimbraNotebookSanitizeHtml
                              | zimbraNotes
                              | zimbraPasswordAllowedChars
                              | zimbraPasswordAllowedPunctuationChars
                              | zimbraPasswordEnforceHistory
                              | zimbraPasswordHistory
                              | zimbraPasswordLocked
                              | zimbraPasswordLockoutDuration
                              | zimbraPasswordLockoutEnabled
                              | zimbraPasswordLockoutFailureLifetime
                              | zimbraPasswordLockoutFailureTime
                              | zimbraPasswordLockoutLockedTime
                              | zimbraPasswordLockoutMaxFailures
                              | zimbraPasswordMaxAge
                              | zimbraPasswordMaxLength
                              | zimbraPasswordMinAge
                              | zimbraPasswordMinAlphaChars
                              | zimbraPasswordMinDigitsOrPuncs
                              | zimbraPasswordMinLength
                              | zimbraPasswordMinLowerCaseChars
                              | zimbraPasswordMinNumericChars
                              | zimbraPasswordMinPunctuationChars
                              | zimbraPasswordMinUpperCaseChars
                              | zimbraPasswordModifiedTime
                              | zimbraPasswordMustChange
                              | zimbraPhoneticCompany
                              | zimbraPhoneticFirstName
                              | zimbraPhoneticLastName
                              | zimbraPop3Enabled
                              | zimbraPortalName
                              | zimbraPrefAccountTreeOpen
                              | zimbraPrefAdminConsoleWarnOnExit
                              | zimbraPrefAdvancedClientEnforceMinDisplay
                              | zimbraPrefAllowAddressForDelegatedSender
                              | zimbraPrefAppleIcalDelegationEnabled
                              | zimbraPrefAutoAddAddressEnabled
                              | zimbraPrefAutoCompleteQuickCompletionOnComma
                              | zimbraPrefAutoSaveDraftInterval
                              | zimbraPrefAutocompleteAddressBubblesEnabled
                              | zimbraPrefBccAddress
                              | zimbraPrefBriefcaseReadingPaneLocation
                              | zimbraPrefCalendarAcceptSignatureId
                              | zimbraPrefCalendarAllowCancelEmailToSelf
                              | zimbraPrefCalendarAllowForwardedInvite
                              | zimbraPrefCalendarAllowPublishMethodInvite
                              | zimbraPrefCalendarAllowedTargetsForInviteDeniedAutoReply
                              | zimbraPrefCalendarAlwaysShowMiniCal
                              | zimbraPrefCalendarApptAllowAtendeeEdit
                              | zimbraPrefCalendarApptReminderWarningTime
                              | zimbraPrefCalendarApptVisibility
                              | zimbraPrefCalendarAutoAcceptSignatureId
                              | zimbraPrefCalendarAutoAddInvites
                              | zimbraPrefCalendarAutoDeclineSignatureId
                              | zimbraPrefCalendarAutoDenySignatureId
                              | zimbraPrefCalendarDayHourEnd
                              | zimbraPrefCalendarDayHourStart
                              | zimbraPrefCalendarDeclineSignatureId
                              | zimbraPrefCalendarDefaultApptDuration
                              | zimbraPrefCalendarFirstDayOfWeek
                              | zimbraPrefCalendarForwardInvitesTo
                              | zimbraPrefCalendarInitialCheckedCalendars
                              | zimbraPrefCalendarInitialView
                              | zimbraPrefCalendarNotifyDelegatedChanges
                              | zimbraPrefCalendarReminderDeviceInfo
                              | zimbraPrefCalendarReminderDuration1
                              | zimbraPrefCalendarReminderDuration2
                              | zimbraPrefCalendarReminderEmail
                              | zimbraPrefCalendarReminderFlashTitle
                              | zimbraPrefCalendarReminderMobile
                              | zimbraPrefCalendarReminderSendEmail
                              | zimbraPrefCalendarReminderSoundsEnabled
                              | zimbraPrefCalendarReminderYMessenger
                              | zimbraPrefCalendarSendInviteDeniedAutoReply
                              | zimbraPrefCalendarShowDeclinedMeetings
                              | zimbraPrefCalendarShowPastDueReminders
                              | zimbraPrefCalendarTentativeSignatureId
                              | zimbraPrefCalendarToasterEnabled
                              | zimbraPrefCalendarUseQuickAdd
                              | zimbraPrefCalendarViewTimeInterval
                              | zimbraPrefCalendarWorkingHours
                              | zimbraPrefChildVisibleAccount
                              | zimbraPrefClientType
                              | zimbraPrefColorMessagesEnabled
                              | zimbraPrefComposeDirection
                              | zimbraPrefComposeFormat
                              | zimbraPrefComposeInNewWindow
                              | zimbraPrefContactsDisableAutocompleteOnContactGroupMembers
                              | zimbraPrefContactsExpandAppleContactGroups
                              | zimbraPrefContactsInitialView
                              | zimbraPrefContactsPerPage
                              | zimbraPrefConvReadingPaneLocation
                              | zimbraPrefConvShowCalendar
                              | zimbraPrefConversationOrder
                              | zimbraPrefDedupeMessagesSentToSelf
                              | zimbraPrefDefaultPrintFontSize
                              | zimbraPrefDefaultSignatureId
                              | zimbraPrefDelegatedSendSaveTarget
                              | zimbraPrefDeleteInviteOnReply
                              | zimbraPrefDisabledZimlets
                              | zimbraPrefDisplayExternalImages
                              | zimbraPrefExternalSendersType
                              | zimbraPrefFileSharingApplication
                              | zimbraPrefFolderColorEnabled
                              | zimbraPrefFolderTreeOpen
                              | zimbraPrefFont
                              | zimbraPrefFontSize
                              | zimbraPrefForwardIncludeOriginalText
                              | zimbraPrefForwardReplyFormat
                              | zimbraPrefForwardReplyInOriginalFormat
                              | zimbraPrefForwardReplyPrefixChar
                              | zimbraPrefForwardReplySignatureId
                              | zimbraPrefFromAddress
                              | zimbraPrefFromAddressType
                              | zimbraPrefFromDisplay
                              | zimbraPrefGalAutoCompleteEnabled
                              | zimbraPrefGalSearchEnabled
                              | zimbraPrefGetMailAction
                              | zimbraPrefGroupMailBy
                              | zimbraPrefHtmlEditorDefaultFontColor
                              | zimbraPrefHtmlEditorDefaultFontFamily
                              | zimbraPrefHtmlEditorDefaultFontSize
                              | zimbraPrefIMAutoLogin
                              | zimbraPrefIMBuddyListSort
                              | zimbraPrefIMCustomStatusMessage
                              | zimbraPrefIMFlashIcon
                              | zimbraPrefIMFlashTitle
                              | zimbraPrefIMHideBlockedBuddies
                              | zimbraPrefIMHideOfflineBuddies
                              | zimbraPrefIMIdleStatus
                              | zimbraPrefIMIdleTimeout
                              | zimbraPrefIMInstantNotify
                              | zimbraPrefIMLogChats
                              | zimbraPrefIMLogChatsEnabled
                              | zimbraPrefIMNotifyPresence
                              | zimbraPrefIMNotifyStatus
                              | zimbraPrefIMReportIdle
                              | zimbraPrefIMSoundsEnabled
                              | zimbraPrefIMToasterEnabled
                              | zimbraPrefIMYahooId
                              | zimbraPrefIdentityName
                              | zimbraPrefImapSearchFoldersEnabled
                              | zimbraPrefInboxReadLifetime
                              | zimbraPrefInboxUnreadLifetime
                              | zimbraPrefIncludeSharedItemsInSearch
                              | zimbraPrefIncludeSpamInSearch
                              | zimbraPrefIncludeTrashInSearch
                              | zimbraPrefItemsPerVirtualPage
                              | zimbraPrefJunkLifetime
                              | zimbraPrefLabel
                              | zimbraPrefListViewColumns
                              | zimbraPrefLocale
                              | zimbraPrefMailDefaultCharset
                              | zimbraPrefMailFlashIcon
                              | zimbraPrefMailFlashTitle
                              | zimbraPrefMailFoldersCheckedForNewMsgIndicator
                              | zimbraPrefMailForwardingAddress
                              | zimbraPrefMailInitialSearch
                              | zimbraPrefMailItemsPerPage
                              | zimbraPrefMailLocalDeliveryDisabled
                              | zimbraPrefMailPollingInterval
                              | zimbraPrefMailRequestReadReceipts
                              | zimbraPrefMailSMIMECertificate
                              | zimbraPrefMailSelectAfterDelete
                              | zimbraPrefMailSendReadReceipts
                              | zimbraPrefMailSignature
                              | zimbraPrefMailSignatureContactId
                              | zimbraPrefMailSignatureEnabled
                              | zimbraPrefMailSignatureHTML
                              | zimbraPrefMailSignatureStyle
                              | zimbraPrefMailSoundsEnabled
                              | zimbraPrefMailToasterEnabled
                              | zimbraPrefMailTrustedSenderList
                              | zimbraPrefMandatorySpellCheckEnabled
                              | zimbraPrefMarkMsgRead
                              | zimbraPrefMessageIdDedupingEnabled
                              | zimbraPrefMessageViewHtmlPreferred
                              | zimbraPrefNewMailNotificationAddress
                              | zimbraPrefNewMailNotificationEnabled
                              | zimbraPrefOpenMailInNewWindow
                              | zimbraPrefOutOfOfficeCacheDuration
                              | zimbraPrefOutOfOfficeDirectAddress
                              | zimbraPrefOutOfOfficeExternalReply
                              | zimbraPrefOutOfOfficeExternalReplyEnabled
                              | zimbraPrefOutOfOfficeFreeBusyStatus
                              | zimbraPrefOutOfOfficeFromDate
                              | zimbraPrefOutOfOfficeReply
                              | zimbraPrefOutOfOfficeReplyEnabled
                              | zimbraPrefOutOfOfficeStatusAlertOnLogin
                              | zimbraPrefOutOfOfficeSuppressExternalReply
                              | zimbraPrefOutOfOfficeUntilDate
                              | zimbraPrefPop3DeleteOption
                              | zimbraPrefPop3DownloadSince
                              | zimbraPrefPop3IncludeSpam
                              | zimbraPrefQuickCommand
                              | zimbraPrefReadReceiptsToAddress
                              | zimbraPrefReadingPaneEnabled
                              | zimbraPrefReadingPaneLocation
                              | zimbraPrefReplyIncludeOriginalText
                              | zimbraPrefReplyToAddress
                              | zimbraPrefReplyToDisplay
                              | zimbraPrefReplyToEnabled
                              | zimbraPrefSaveToSent
                              | zimbraPrefSearchTreeOpen
                              | zimbraPrefSentLifetime
                              | zimbraPrefSentMailFolder
                              | zimbraPrefSharedAddrBookAutoCompleteEnabled
                              | zimbraPrefShortEmailAddress
                              | zimbraPrefShortcuts
                              | zimbraPrefShowCalendarWeek
                              | zimbraPrefShowComposeDirection
                              | zimbraPrefShowFragments
                              | zimbraPrefShowSearchString
                              | zimbraPrefShowSelectionCheckbox
                              | zimbraPrefSkin
                              | zimbraPrefSortOrder
                              | zimbraPrefSpellDictionary
                              | zimbraPrefSpellIgnoreAllCaps
                              | zimbraPrefSpellIgnorePattern
                              | zimbraPrefSpellIgnoreWord
                              | zimbraPrefStandardClientAccessibilityMode
                              | zimbraPrefTagTreeOpen
                              | zimbraPrefTasksFilterBy
                              | zimbraPrefTasksReadingPaneLocation
                              | zimbraPrefTimeZoneId
                              | zimbraPrefTrashLifetime
                              | zimbraPrefUseDefaultIdentitySettings
                              | zimbraPrefUseKeyboardShortcuts
                              | zimbraPrefUseRfc2231
                              | zimbraPrefUseSendMsgShortcut
                              | zimbraPrefUseTimeZoneListInCalendar
                              | zimbraPrefVoiceItemsPerPage
                              | zimbraPrefWarnOnExit
                              | zimbraPrefWebClientOfflineBrowserKey
                              | zimbraPrefWhenInFolderIds
                              | zimbraPrefWhenInFoldersEnabled
                              | zimbraPrefWhenSentToAddresses
                              | zimbraPrefWhenSentToEnabled
                              | zimbraPrefZimletTreeOpen
                              | zimbraPrefZimlets
                              | zimbraProxyAllowedDomains
                              | zimbraPublicShareLifetime
                              | zimbraPublicSharingEnabled
                              | zimbraQuotaLastWarnTime
                              | zimbraQuotaWarnInterval
                              | zimbraQuotaWarnMessage
                              | zimbraQuotaWarnPercent
                              | zimbraReverseProxyUseExternalRoute
                              | zimbraShareInfo
                              | zimbraShareLifetime
                              | zimbraSharedItem
                              | zimbraSignatureId
                              | zimbraSignatureMaxNumEntries
                              | zimbraSignatureMinNumEntries
                              | zimbraSignatureName
                              | zimbraSmtpEnableTrace
                              | zimbraSmtpRestrictEnvelopeFrom
                              | zimbraSocialcastURL
                              | zimbraSpamApplyUserFilters
                              | zimbraStandardClientCustomPrefTab
                              | zimbraStandardClientCustomPrefTabsEnabled
                              | zimbraSyncWindowSize
                              | zimbraTextAnalyzer
                              | zimbraTouchJSErrorTrackingEnabled
                              | zimbraTouchJSErrorTrackingKey
                              | zimbraUCPassword
                              | zimbraUCServiceId
                              | zimbraUCUsername
                              | zimbraVersion
                              | zimbraVirtualAccountInitialPasswordSet
                              | zimbraWebClientOfflineSyncMaxDays
                              | zimbraWebClientShowOfflineLink
                              | zimbraYahooId
                              | zimbraZimletAvailableZimlets
                              | zimbraZimletLoadSynchronously
                              | zimbraZimletUserProperties }
  LDAP-NAME                 {"zimbraAccount"}
  LDAP-DESC                 "Account object"
  ID                        id-oc-zimbraAccount }

zimbraAlias OBJECT-CLASS ::= {
  SUBCLASS OF               { top }
  MUST CONTAIN              { zimbraAliasTargetId
                              | zimbraId }
  MAY CONTAIN               { commonName
                              | uid
                              | zimbraCreateTimestamp
                              | zimbraLocale }
  LDAP-NAME                 {"zimbraAlias"}
  LDAP-DESC                 "An alias to another zimbra object"
  ID                        id-oc-zimbraAlias }

zimbraDistributionList OBJECT-CLASS ::= {
  SUBCLASS OF               { top }
  MUST CONTAIN              { uid
                              | zimbraId }
  MAY CONTAIN               { commonName
                              | description
                              | displayName
                              | mail
                              | zimbraACE
                              | zimbraAdminConsoleUIComponents
                              | zimbraCreateTimestamp
                              | zimbraDistributionListSendShareMessageFromAddress
                              | zimbraDistributionListSendShareMessageToNewMembers
                              | zimbraDistributionListSubscriptionPolicy
                              | zimbraDistributionListUnsubscriptionPolicy
                              | zimbraGroupId
                              | zimbraIsAdminGroup
                              | zimbraLocale
                              | zimbraNotes
                              | zimbraPrefAllowAddressForDelegatedSender
                              | zimbraPrefReplyToAddress
                              | zimbraPrefReplyToDisplay
                              | zimbraPrefReplyToEnabled
                              | zimbraShareInfo }
  LDAP-NAME                 {"zimbraDistributionList"}
  LDAP-DESC                 "Distribution List object"
  ID                        id-oc-zimbraDistributionList }

zimbraCOS OBJECT-CLASS ::= {
  SUBCLASS OF               { top }
  MUST CONTAIN              { commonName
                              | zimbraId }
  MAY CONTAIN               { description
                              | zimbraACE
                              | zimbraAdminAuthTokenLifetime
                              | zimbraAdminSavedSearches
                              | zimbraAllowAnyFromAddress
                              | zimbraArchiveAccountDateTemplate
                              | zimbraArchiveAccountNameTemplate
                              | zimbraArchiveEnabled
                              | zimbraAttachmentsBlocked
                              | zimbraAttachmentsIndexingEnabled
                              | zimbraAttachmentsViewInHtmlOnly
                              | zimbraAuthTokenLifetime
                              | zimbraAvailableLocale
                              | zimbraAvailableSkin
                              | zimbraBatchedIndexingSize
                              | zimbraCalendarCalDavSharedFolderCacheDuration
                              | zimbraCalendarCalDavSyncEnd
                              | zimbraCalendarCalDavSyncStart
                              | zimbraCalendarKeepExceptionsOnSeriesTimeChange
                              | zimbraCalendarLocationDisabledFields
                              | zimbraCalendarMaxRevisions
                              | zimbraCalendarResourceDoubleBookingAllowed
                              | zimbraCalendarShowResourceTabs
                              | zimbraCommunityAPIClientID
                              | zimbraCommunityAPIClientSecret
                              | zimbraCommunityBaseURL
                              | zimbraCommunityHomeURL
                              | zimbraCommunityUsernameMapping
                              | zimbraConstraint
                              | zimbraContactAutoCompleteEmailFields
                              | zimbraContactAutoCompleteMaxResults
                              | zimbraContactEmailFields
                              | zimbraContactMaxNumEntries
                              | zimbraContactRankingTableSize
                              | zimbraConverterHints
                              | zimbraCreateTimestamp
                              | zimbraDataSourceCaldavPollingInterval
                              | zimbraDataSourceCalendarPollingInterval
                              | zimbraDataSourceGalPollingInterval
                              | zimbraDataSourceImapPollingInterval
                              | zimbraDataSourceImportOnLogin
                              | zimbraDataSourceLivePollingInterval
                              | zimbraDataSourceMaxNumEntries
                              | zimbraDataSourceMinPollingInterval
                              | zimbraDataSourcePollingInterval
                              | zimbraDataSourcePop3PollingInterval
                              | zimbraDataSourceRssPollingInterval
                              | zimbraDataSourceYabPollingInterval
                              | zimbraDefaultFolderFlags
                              | zimbraDeviceAllowedPasscodeLockoutDuration
                              | zimbraDeviceCalendarSoftDeleteExcludePattern
                              | zimbraDeviceFileOpenWithEnabled
                              | zimbraDeviceLockWhenInactive
                              | zimbraDeviceOfflineCacheEnabled
                              | zimbraDevicePasscodeEnabled
                              | zimbraDevicePasscodeLockoutDuration
                              | zimbraDomainAdminMaxMailQuota
                              | zimbraDumpsterEnabled
                              | zimbraDumpsterPurgeEnabled
                              | zimbraDumpsterUserVisibleAge
                              | zimbraExternalAccountLifetimeAfterDisabled
                              | zimbraExternalShareDomainWhitelistEnabled
                              | zimbraExternalShareLifetime
                              | zimbraExternalShareWhitelistDomain
                              | zimbraExternalSharingEnabled
                              | zimbraFeatureAdminMailEnabled
                              | zimbraFeatureAdvancedSearchEnabled
                              | zimbraFeatureAntispamEnabled
                              | zimbraFeatureBriefcaseDocsEnabled
                              | zimbraFeatureBriefcaseSlidesEnabled
                              | zimbraFeatureBriefcaseSpreadsheetEnabled
                              | zimbraFeatureBriefcasesEnabled
                              | zimbraFeatureCalendarEnabled
                              | zimbraFeatureCalendarReminderDeviceEmailEnabled
                              | zimbraFeatureCalendarUpsellEnabled
                              | zimbraFeatureCalendarUpsellURL
                              | zimbraFeatureChangePasswordEnabled
                              | zimbraFeatureComposeInNewWindowEnabled
                              | zimbraFeatureConfirmationPageEnabled
                              | zimbraFeatureContactsDetailedSearchEnabled
                              | zimbraFeatureContactsEnabled
                              | zimbraFeatureContactsUpsellEnabled
                              | zimbraFeatureContactsUpsellURL
                              | zimbraFeatureConversationsEnabled
                              | zimbraFeatureCrocodocEnabled
                              | zimbraFeatureDiscardInFiltersEnabled
                              | zimbraFeatureDistributionListExpandMembersEnabled
                              | zimbraFeatureDistributionListFolderEnabled
                              | zimbraFeatureEwsEnabled
                              | zimbraFeatureExportFolderEnabled
                              | zimbraFeatureExternalFeedbackEnabled
                              | zimbraFeatureFiltersEnabled
                              | zimbraFeatureFlaggingEnabled
                              | zimbraFeatureFreeBusyViewEnabled
                              | zimbraFeatureFromDisplayEnabled
                              | zimbraFeatureGalAutoCompleteEnabled
                              | zimbraFeatureGalEnabled
                              | zimbraFeatureGalSyncEnabled
                              | zimbraFeatureGroupCalendarEnabled
                              | zimbraFeatureHtmlComposeEnabled
                              | zimbraFeatureIMEnabled
                              | zimbraFeatureIdentitiesEnabled
                              | zimbraFeatureImapDataSourceEnabled
                              | zimbraFeatureImportExportFolderEnabled
                              | zimbraFeatureImportFolderEnabled
                              | zimbraFeatureInitialSearchPreferenceEnabled
                              | zimbraFeatureInstantNotify
                              | zimbraFeatureMAPIConnectorEnabled
                              | zimbraFeatureMailEnabled
                              | zimbraFeatureMailForwardingEnabled
                              | zimbraFeatureMailForwardingInFiltersEnabled
                              | zimbraFeatureMailPollingIntervalPreferenceEnabled
                              | zimbraFeatureMailPriorityEnabled
                              | zimbraFeatureMailSendLaterEnabled
                              | zimbraFeatureMailUpsellEnabled
                              | zimbraFeatureMailUpsellURL
                              | zimbraFeatureManageSMIMECertificateEnabled
                              | zimbraFeatureManageZimlets
                              | zimbraFeatureMobilePolicyEnabled
                              | zimbraFeatureMobileSyncEnabled
                              | zimbraFeatureNewAddrBookEnabled
                              | zimbraFeatureNewMailNotificationEnabled
                              | zimbraFeatureNotebookEnabled
                              | zimbraFeatureOpenMailInNewWindowEnabled
                              | zimbraFeatureOptionsEnabled
                              | zimbraFeatureOutOfOfficeReplyEnabled
                              | zimbraFeaturePeopleSearchEnabled
                              | zimbraFeaturePop3DataSourceEnabled
                              | zimbraFeaturePortalEnabled
                              | zimbraFeaturePriorityInboxEnabled
                              | zimbraFeatureReadReceiptsEnabled
                              | zimbraFeatureSMIMEEnabled
                              | zimbraFeatureSavedSearchesEnabled
                              | zimbraFeatureSharingEnabled
                              | zimbraFeatureShortcutAliasesEnabled
                              | zimbraFeatureSignaturesEnabled
                              | zimbraFeatureSkinChangeEnabled
                              | zimbraFeatureSocialEnabled
                              | zimbraFeatureSocialExternalEnabled
                              | zimbraFeatureSocialExternalURL
                              | zimbraFeatureSocialFiltersEnabled
                              | zimbraFeatureSocialName
                              | zimbraFeatureSocialcastEnabled
                              | zimbraFeatureTaggingEnabled
                              | zimbraFeatureTasksEnabled
                              | zimbraFeatureTouchClientEnabled
                              | zimbraFeatureViewInHtmlEnabled
                              | zimbraFeatureVoiceChangePinEnabled
                              | zimbraFeatureVoiceEnabled
                              | zimbraFeatureVoiceUpsellEnabled
                              | zimbraFeatureVoiceUpsellURL
                              | zimbraFeatureWebClientOfflineAccessEnabled
                              | zimbraFeatureWebSearchEnabled
                              | zimbraFeatureZimbraAssistantEnabled
                              | zimbraFileAndroidCrashReportingEnabled
                              | zimbraFileDeletionNotificationBody
                              | zimbraFileDeletionNotificationSubject
                              | zimbraFileExpirationWarningBody
                              | zimbraFileExpirationWarningSubject
                              | zimbraFileExpirationWarningThreshold
                              | zimbraFileExternalShareLifetime
                              | zimbraFileIOSCrashReportingEnabled
                              | zimbraFileLifetime
                              | zimbraFilePreviewMaxSize
                              | zimbraFilePublicShareLifetime
                              | zimbraFileShareLifetime
                              | zimbraFileUploadMaxSizePerFile
                              | zimbraFileVersionLifetime
                              | zimbraFileVersioningEnabled
                              | zimbraFilterBatchSize
                              | zimbraFilterSleepInterval
                              | zimbraForceClearCookies
                              | zimbraFreebusyExchangeAuthPassword
                              | zimbraFreebusyExchangeAuthScheme
                              | zimbraFreebusyExchangeAuthUsername
                              | zimbraFreebusyExchangeCachedInterval
                              | zimbraFreebusyExchangeCachedIntervalStart
                              | zimbraFreebusyExchangeURL
                              | zimbraFreebusyExchangeUserOrg
                              | zimbraFreebusyLocalMailboxNotActive
                              | zimbraGalSyncAccountBasedAutoCompleteEnabled
                              | zimbraIMAvailableInteropGateways
                              | zimbraIMService
                              | zimbraIdentityMaxNumEntries
                              | zimbraImapEnabled
                              | zimbraInterceptAddress
                              | zimbraInterceptBody
                              | zimbraInterceptFrom
                              | zimbraInterceptSendHeadersOnly
                              | zimbraInterceptSubject
                              | zimbraInternalSendersDomain
                              | zimbraJunkMessagesIndexingEnabled
                              | zimbraLocale
                              | zimbraLogOutFromAllServers
                              | zimbraMailAllowReceiveButNotSendWhenOverQuota
                              | zimbraMailBlacklistMaxNumEntries
                              | zimbraMailDumpsterLifetime
                              | zimbraMailForwardingAddressMaxLength
                              | zimbraMailForwardingAddressMaxNumAddrs
                              | zimbraMailHighlightObjectsMaxSize
                              | zimbraMailHostPool
                              | zimbraMailIdleSessionTimeout
                              | zimbraMailMessageLifetime
                              | zimbraMailMinPollingInterval
                              | zimbraMailPurgeSystemPolicy
                              | zimbraMailPurgeUseChangeDateForSpam
                              | zimbraMailPurgeUseChangeDateForTrash
                              | zimbraMailQuota
                              | zimbraMailSignatureMaxLength
                              | zimbraMailSpamLifetime
                              | zimbraMailThreadingAlgorithm
                              | zimbraMailTrashLifetime
                              | zimbraMailTrustedSenderListMaxNumEntries
                              | zimbraMailWhitelistMaxNumEntries
                              | zimbraMaxContactsPerPage
                              | zimbraMaxMailItemsPerPage
                              | zimbraMaxVoiceItemsPerPage
                              | zimbraMobileAttachSkippedItemEnabled
                              | zimbraMobileForceProtocol25
                              | zimbraMobileForceSamsungProtocol25
                              | zimbraMobileItemsToTrackPerFolderMaxSize
                              | zimbraMobileMetadataMaxSizeEnabled
                              | zimbraMobileNotificationAdminAddress
                              | zimbraMobileNotificationEnabled
                              | zimbraMobileOutlookSyncEnabled
                              | zimbraMobilePolicyAllowBluetooth
                              | zimbraMobilePolicyAllowBrowser
                              | zimbraMobilePolicyAllowCamera
                              | zimbraMobilePolicyAllowConsumerEmail
                              | zimbraMobilePolicyAllowDesktopSync
                              | zimbraMobilePolicyAllowHTMLEmail
                              | zimbraMobilePolicyAllowInternetSharing
                              | zimbraMobilePolicyAllowIrDA
                              | zimbraMobilePolicyAllowNonProvisionableDevices
                              | zimbraMobilePolicyAllowPOPIMAPEmail
                              | zimbraMobilePolicyAllowPartialProvisioning
                              | zimbraMobilePolicyAllowRemoteDesktop
                              | zimbraMobilePolicyAllowSMIMEEncryptionAlgorithmNegotiation
                              | zimbraMobilePolicyAllowSMIMESoftCerts
                              | zimbraMobilePolicyAllowSimpleDevicePassword
                              | zimbraMobilePolicyAllowStorageCard
                              | zimbraMobilePolicyAllowTextMessaging
                              | zimbraMobilePolicyAllowUnsignedApplications
                              | zimbraMobilePolicyAllowUnsignedInstallationPackages
                              | zimbraMobilePolicyAllowWiFi
                              | zimbraMobilePolicyAlphanumericDevicePasswordRequired
                              | zimbraMobilePolicyApprovedApplication
                              | zimbraMobilePolicyApprovedApplicationList
                              | zimbraMobilePolicyDeviceEncryptionEnabled
                              | zimbraMobilePolicyDevicePasswordEnabled
                              | zimbraMobilePolicyDevicePasswordExpiration
                              | zimbraMobilePolicyDevicePasswordHistory
                              | zimbraMobilePolicyMaxCalendarAgeFilter
                              | zimbraMobilePolicyMaxDevicePasswordFailedAttempts
                              | zimbraMobilePolicyMaxEmailAgeFilter
                              | zimbraMobilePolicyMaxEmailBodyTruncationSize
                              | zimbraMobilePolicyMaxEmailHTMLBodyTruncationSize
                              | zimbraMobilePolicyMaxInactivityTimeDeviceLock
                              | zimbraMobilePolicyMinDevicePasswordComplexCharacters
                              | zimbraMobilePolicyMinDevicePasswordLength
                              | zimbraMobilePolicyPasswordRecoveryEnabled
                              | zimbraMobilePolicyRefreshInterval
                              | zimbraMobilePolicyRequireDeviceEncryption
                              | zimbraMobilePolicyRequireEncryptedSMIMEMessages
                              | zimbraMobilePolicyRequireEncryptionSMIMEAlgorithm
                              | zimbraMobilePolicyRequireManualSyncWhenRoaming
                              | zimbraMobilePolicyRequireSignedSMIMEAlgorithm
                              | zimbraMobilePolicyRequireSignedSMIMEMessages
                              | zimbraMobilePolicyRequireStorageCardEncryption
                              | zimbraMobilePolicySuppressDeviceEncryption
                              | zimbraMobilePolicyUnapprovedInROMApplication
                              | zimbraMobileShareContactEnabled
                              | zimbraMobileSmartForwardRFC822Enabled
                              | zimbraMobileSyncKeyFormatConvertedFolders
                              | zimbraMobileSyncRedoMaxAttempts
                              | zimbraMobileTombstoneEnabled
                              | zimbraNewMailNotificationBody
                              | zimbraNewMailNotificationFrom
                              | zimbraNewMailNotificationSubject
                              | zimbraNotebookMaxRevisions
                              | zimbraNotebookSanitizeHtml
                              | zimbraNotes
                              | zimbraPasswordAllowedChars
                              | zimbraPasswordAllowedPunctuationChars
                              | zimbraPasswordEnforceHistory
                              | zimbraPasswordLocked
                              | zimbraPasswordLockoutDuration
                              | zimbraPasswordLockoutEnabled
                              | zimbraPasswordLockoutFailureLifetime
                              | zimbraPasswordLockoutMaxFailures
                              | zimbraPasswordMaxAge
                              | zimbraPasswordMaxLength
                              | zimbraPasswordMinAge
                              | zimbraPasswordMinAlphaChars
                              | zimbraPasswordMinDigitsOrPuncs
                              | zimbraPasswordMinLength
                              | zimbraPasswordMinLowerCaseChars
                              | zimbraPasswordMinNumericChars
                              | zimbraPasswordMinPunctuationChars
                              | zimbraPasswordMinUpperCaseChars
                              | zimbraPop3Enabled
                              | zimbraPortalName
                              | zimbraPrefAccountTreeOpen
                              | zimbraPrefAdminConsoleWarnOnExit
                              | zimbraPrefAdvancedClientEnforceMinDisplay
                              | zimbraPrefAppleIcalDelegationEnabled
                              | zimbraPrefAutoAddAddressEnabled
                              | zimbraPrefAutoCompleteQuickCompletionOnComma
                              | zimbraPrefAutoSaveDraftInterval
                              | zimbraPrefAutocompleteAddressBubblesEnabled
                              | zimbraPrefBriefcaseReadingPaneLocation
                              | zimbraPrefCalendarAllowCancelEmailToSelf
                              | zimbraPrefCalendarAllowForwardedInvite
                              | zimbraPrefCalendarAllowPublishMethodInvite
                              | zimbraPrefCalendarAllowedTargetsForInviteDeniedAutoReply
                              | zimbraPrefCalendarAlwaysShowMiniCal
                              | zimbraPrefCalendarApptAllowAtendeeEdit
                              | zimbraPrefCalendarApptReminderWarningTime
                              | zimbraPrefCalendarApptVisibility
                              | zimbraPrefCalendarAutoAddInvites
                              | zimbraPrefCalendarDayHourEnd
                              | zimbraPrefCalendarDayHourStart
                              | zimbraPrefCalendarDefaultApptDuration
                              | zimbraPrefCalendarFirstDayOfWeek
                              | zimbraPrefCalendarInitialView
                              | zimbraPrefCalendarNotifyDelegatedChanges
                              | zimbraPrefCalendarReminderDuration1
                              | zimbraPrefCalendarReminderDuration2
                              | zimbraPrefCalendarReminderFlashTitle
                              | zimbraPrefCalendarReminderMobile
                              | zimbraPrefCalendarReminderSendEmail
                              | zimbraPrefCalendarReminderSoundsEnabled
                              | zimbraPrefCalendarReminderYMessenger
                              | zimbraPrefCalendarSendInviteDeniedAutoReply
                              | zimbraPrefCalendarShowDeclinedMeetings
                              | zimbraPrefCalendarShowPastDueReminders
                              | zimbraPrefCalendarToasterEnabled
                              | zimbraPrefCalendarUseQuickAdd
                              | zimbraPrefCalendarViewTimeInterval
                              | zimbraPrefCalendarWorkingHours
                              | zimbraPrefClientType
                              | zimbraPrefColorMessagesEnabled
                              | zimbraPrefComposeDirection
                              | zimbraPrefComposeFormat
                              | zimbraPrefComposeInNewWindow
                              | zimbraPrefContactsDisableAutocompleteOnContactGroupMembers
                              | zimbraPrefContactsExpandAppleContactGroups
                              | zimbraPrefContactsInitialView
                              | zimbraPrefContactsPerPage
                              | zimbraPrefConvReadingPaneLocation
                              | zimbraPrefConvShowCalendar
                              | zimbraPrefConversationOrder
                              | zimbraPrefDedupeMessagesSentToSelf
                              | zimbraPrefDefaultPrintFontSize
                              | zimbraPrefDelegatedSendSaveTarget
                              | zimbraPrefDeleteInviteOnReply
                              | zimbraPrefDisabledZimlets
                              | zimbraPrefDisplayExternalImages
                              | zimbraPrefExternalSendersType
                              | zimbraPrefFileSharingApplication
                              | zimbraPrefFolderColorEnabled
                              | zimbraPrefFolderTreeOpen
                              | zimbraPrefFont
                              | zimbraPrefFontSize
                              | zimbraPrefForwardIncludeOriginalText
                              | zimbraPrefForwardReplyFormat
                              | zimbraPrefForwardReplyInOriginalFormat
                              | zimbraPrefForwardReplyPrefixChar
                              | zimbraPrefGalAutoCompleteEnabled
                              | zimbraPrefGalSearchEnabled
                              | zimbraPrefGetMailAction
                              | zimbraPrefGroupMailBy
                              | zimbraPrefHtmlEditorDefaultFontColor
                              | zimbraPrefHtmlEditorDefaultFontFamily
                              | zimbraPrefHtmlEditorDefaultFontSize
                              | zimbraPrefIMAutoLogin
                              | zimbraPrefIMBuddyListSort
                              | zimbraPrefIMFlashIcon
                              | zimbraPrefIMFlashTitle
                              | zimbraPrefIMHideBlockedBuddies
                              | zimbraPrefIMHideOfflineBuddies
                              | zimbraPrefIMIdleStatus
                              | zimbraPrefIMIdleTimeout
                              | zimbraPrefIMInstantNotify
                              | zimbraPrefIMLogChats
                              | zimbraPrefIMLogChatsEnabled
                              | zimbraPrefIMNotifyPresence
                              | zimbraPrefIMNotifyStatus
                              | zimbraPrefIMReportIdle
                              | zimbraPrefIMSoundsEnabled
                              | zimbraPrefIMToasterEnabled
                              | zimbraPrefImapSearchFoldersEnabled
                              | zimbraPrefInboxReadLifetime
                              | zimbraPrefInboxUnreadLifetime
                              | zimbraPrefIncludeSharedItemsInSearch
                              | zimbraPrefIncludeSpamInSearch
                              | zimbraPrefIncludeTrashInSearch
                              | zimbraPrefItemsPerVirtualPage
                              | zimbraPrefJunkLifetime
                              | zimbraPrefListViewColumns
                              | zimbraPrefLocale
                              | zimbraPrefMailDefaultCharset
                              | zimbraPrefMailFlashIcon
                              | zimbraPrefMailFlashTitle
                              | zimbraPrefMailFoldersCheckedForNewMsgIndicator
                              | zimbraPrefMailInitialSearch
                              | zimbraPrefMailItemsPerPage
                              | zimbraPrefMailPollingInterval
                              | zimbraPrefMailRequestReadReceipts
                              | zimbraPrefMailSelectAfterDelete
                              | zimbraPrefMailSendReadReceipts
                              | zimbraPrefMailSignatureStyle
                              | zimbraPrefMailSoundsEnabled
                              | zimbraPrefMailToasterEnabled
                              | zimbraPrefMailTrustedSenderList
                              | zimbraPrefMandatorySpellCheckEnabled
                              | zimbraPrefMarkMsgRead
                              | zimbraPrefMessageIdDedupingEnabled
                              | zimbraPrefMessageViewHtmlPreferred
                              | zimbraPrefOpenMailInNewWindow
                              | zimbraPrefOutOfOfficeCacheDuration
                              | zimbraPrefOutOfOfficeStatusAlertOnLogin
                              | zimbraPrefPop3DeleteOption
                              | zimbraPrefPop3DownloadSince
                              | zimbraPrefPop3IncludeSpam
                              | zimbraPrefReadingPaneEnabled
                              | zimbraPrefReadingPaneLocation
                              | zimbraPrefReplyIncludeOriginalText
                              | zimbraPrefSaveToSent
                              | zimbraPrefSearchTreeOpen
                              | zimbraPrefSentLifetime
                              | zimbraPrefSentMailFolder
                              | zimbraPrefSharedAddrBookAutoCompleteEnabled
                              | zimbraPrefShortEmailAddress
                              | zimbraPrefShortcuts
                              | zimbraPrefShowCalendarWeek
                              | zimbraPrefShowComposeDirection
                              | zimbraPrefShowFragments
                              | zimbraPrefShowSearchString
                              | zimbraPrefShowSelectionCheckbox
                              | zimbraPrefSkin
                              | zimbraPrefSortOrder
                              | zimbraPrefSpellDictionary
                              | zimbraPrefSpellIgnoreAllCaps
                              | zimbraPrefSpellIgnorePattern
                              | zimbraPrefSpellIgnoreWord
                              | zimbraPrefStandardClientAccessibilityMode
                              | zimbraPrefTagTreeOpen
                              | zimbraPrefTasksFilterBy
                              | zimbraPrefTasksReadingPaneLocation
                              | zimbraPrefTimeZoneId
                              | zimbraPrefTrashLifetime
                              | zimbraPrefUseKeyboardShortcuts
                              | zimbraPrefUseRfc2231
                              | zimbraPrefUseSendMsgShortcut
                              | zimbraPrefUseTimeZoneListInCalendar
                              | zimbraPrefVoiceItemsPerPage
                              | zimbraPrefWarnOnExit
                              | zimbraPrefZimletTreeOpen
                              | zimbraPrefZimlets
                              | zimbraProxyAllowedDomains
                              | zimbraProxyCacheableContentTypes
                              | zimbraPublicShareLifetime
                              | zimbraPublicSharingEnabled
                              | zimbraQuotaWarnInterval
                              | zimbraQuotaWarnMessage
                              | zimbraQuotaWarnPercent
                              | zimbraShareLifetime
                              | zimbraSignatureMaxNumEntries
                              | zimbraSignatureMinNumEntries
                              | zimbraSmtpEnableTrace
                              | zimbraSmtpRestrictEnvelopeFrom
                              | zimbraSocialcastURL
                              | zimbraSpamApplyUserFilters
                              | zimbraStandardClientCustomPrefTab
                              | zimbraStandardClientCustomPrefTabsEnabled
                              | zimbraSyncWindowSize
                              | zimbraTextAnalyzer
                              | zimbraTouchJSErrorTrackingEnabled
                              | zimbraTouchJSErrorTrackingKey
                              | zimbraUCServiceId
                              | zimbraWebClientOfflineSyncMaxDays
                              | zimbraWebClientShowOfflineLink
                              | zimbraZimletAvailableZimlets
                              | zimbraZimletLoadSynchronously }
  LDAP-NAME                 {"zimbraCOS"}
  LDAP-DESC                 "Class of Service data"
  ID                        id-oc-zimbraCOS }

zimbraGlobalConfig OBJECT-CLASS ::= {
  SUBCLASS OF               { top }
  KIND                      auxiliary
  MAY CONTAIN               { description
                              | zimbraACE
                              | zimbraAccountClientAttr
                              | zimbraAccountExtraObjectClass
                              | zimbraAdminAccessControlMech
                              | zimbraAdminConsoleCatchAllAddressEnabled
                              | zimbraAdminConsoleDNSCheckEnabled
                              | zimbraAdminConsoleLDAPAuthEnabled
                              | zimbraAdminConsoleLoginMessage
                              | zimbraAdminConsoleLoginURL
                              | zimbraAdminConsoleLogoutURL
                              | zimbraAdminConsoleSkinEnabled
                              | zimbraAdminImapImportNumThreads
                              | zimbraAdminPort
                              | zimbraAdminProxyPort
                              | zimbraAdminURL
                              | zimbraAllowNonLDHCharsInDomain
                              | zimbraAlwaysOnClusterId
                              | zimbraAmavisDSPAMEnabled
                              | zimbraAmavisEnableDKIMVerification
                              | zimbraAmavisFinalSpamDestiny
                              | zimbraAmavisLogLevel
                              | zimbraAmavisMaxServers
                              | zimbraAmavisOriginatingBypassSA
                              | zimbraAmavisOutboundDisclaimersOnly
                              | zimbraAmavisQuarantineAccount
                              | zimbraAmavisSALogLevel
                              | zimbraAntispamExtractionBatchDelay
                              | zimbraAntispamExtractionBatchSize
                              | zimbraArchiveEnabled
                              | zimbraArchiveMailFrom
                              | zimbraAttachmentsBlocked
                              | zimbraAttachmentsIndexedTextLimit
                              | zimbraAttachmentsScanClass
                              | zimbraAttachmentsScanEnabled
                              | zimbraAttachmentsScanURL
                              | zimbraAttachmentsViewInHtmlOnly
                              | zimbraAuthTokenKey
                              | zimbraAuthTokenNotificationInterval
                              | zimbraAuthTokenValidityValueEnabled
                              | zimbraAutoProvBatchSize
                              | zimbraAutoProvNotificationBody
                              | zimbraAutoProvNotificationSubject
                              | zimbraAutoProvPollingInterval
                              | zimbraAutoSubmittedNullReturnPath
                              | zimbraBackupAutoGroupedInterval
                              | zimbraBackupAutoGroupedNumGroups
                              | zimbraBackupAutoGroupedThrottled
                              | zimbraBackupMinFreeSpace
                              | zimbraBackupMode
                              | zimbraBackupReportEmailRecipients
                              | zimbraBackupReportEmailSender
                              | zimbraBackupReportEmailSubjectPrefix
                              | zimbraBackupSkipBlobs
                              | zimbraBackupSkipHsmBlobs
                              | zimbraBackupSkipSearchIndex
                              | zimbraBackupTarget
                              | zimbraBasicAuthRealm
                              | zimbraCBPolicydAccessControlEnabled
                              | zimbraCBPolicydAccountingEnabled
                              | zimbraCBPolicydAmavisEnabled
                              | zimbraCBPolicydBindPort
                              | zimbraCBPolicydBypassMode
                              | zimbraCBPolicydBypassTimeout
                              | zimbraCBPolicydCheckHeloEnabled
                              | zimbraCBPolicydCheckSPFEnabled
                              | zimbraCBPolicydGreylistingBlacklistMsg
                              | zimbraCBPolicydGreylistingDeferMsg
                              | zimbraCBPolicydGreylistingEnabled
                              | zimbraCBPolicydGreylistingTrainingEnabled
                              | zimbraCBPolicydLogLevel
                              | zimbraCBPolicydMaxRequests
                              | zimbraCBPolicydMaxServers
                              | zimbraCBPolicydMaxSpareServers
                              | zimbraCBPolicydMinServers
                              | zimbraCBPolicydMinSpareServers
                              | zimbraCBPolicydQuotasEnabled
                              | zimbraCBPolicydTimeoutBusy
                              | zimbraCBPolicydTimeoutIdle
                              | zimbraCOSInheritedAttr
                              | zimbraCalendarCalDavAlternateCalendarHomeSet
                              | zimbraCalendarCalDavCalendarAutoScheduleEnabled
                              | zimbraCalendarCalDavClearTextPasswordEnabled
                              | zimbraCalendarCalDavDefaultCalendarId
                              | zimbraCalendarCalDavDisableFreebusy
                              | zimbraCalendarCalDavDisableScheduling
                              | zimbraCalendarCalDavUseDistinctAppointmentAndToDoCollection
                              | zimbraCalendarCompatibilityMode
                              | zimbraCalendarRecurrenceDailyMaxDays
                              | zimbraCalendarRecurrenceMaxInstances
                              | zimbraCalendarRecurrenceMonthlyMaxMonths
                              | zimbraCalendarRecurrenceOtherFrequencyMaxYears
                              | zimbraCalendarRecurrenceWeeklyMaxWeeks
                              | zimbraCalendarRecurrenceYearlyMaxYears
                              | zimbraCalendarResourceExtraObjectClass
                              | zimbraCertAuthorityCertSelfSigned
                              | zimbraCertAuthorityKeySelfSigned
                              | zimbraChangePasswordURL
                              | zimbraClamAVBindAddress
                              | zimbraClamAVListenPort
                              | zimbraClamAVMaxThreads
                              | zimbraClientTypeRegex
                              | zimbraClusterType
                              | zimbraCommunityAPIClientID
                              | zimbraCommunityAPIClientSecret
                              | zimbraCommunityBaseURL
                              | zimbraCommunityHomeURL
                              | zimbraCommunityUsernameMapping
                              | zimbraComponentAvailable
                              | zimbraConfiguredServerIDForBlobDirEnabled
                              | zimbraConstraint
                              | zimbraContactHiddenAttributes
                              | zimbraContactRankingTableRefreshInterval
                              | zimbraConvertdURL
                              | zimbraCosExtraObjectClass
                              | zimbraCreateTimestamp
                              | zimbraCsrfAllowedRefererHosts
                              | zimbraCsrfRefererCheckEnabled
                              | zimbraCsrfTokenCheckEnabled
                              | zimbraCsrfTokenKey
                              | zimbraCustomMimeHeaderNameAllowed
                              | zimbraDNSCheckHostname
                              | zimbraDNSMasterIP
                              | zimbraDNSTCPUpstream
                              | zimbraDNSUseTCP
                              | zimbraDNSUseUDP
                              | zimbraDataSourceConnectTimeout
                              | zimbraDataSourceConnectionType
                              | zimbraDataSourceReadTimeout
                              | zimbraDatabaseSlowSqlThreshold
                              | zimbraDefaultAnalyzerStopWords
                              | zimbraDefaultDomainName
                              | zimbraDomainAdminModifiableAttr
                              | zimbraDomainAggregateQuota
                              | zimbraDomainAggregateQuotaPolicy
                              | zimbraDomainAggregateQuotaWarnEmailRecipient
                              | zimbraDomainAggregateQuotaWarnPercent
                              | zimbraDomainExtraObjectClass
                              | zimbraDomainInheritedAttr
                              | zimbraDomainMandatoryMailSignatureEnabled
                              | zimbraDomainMandatoryMailSignatureHTML
                              | zimbraDomainMandatoryMailSignatureText
                              | zimbraDomainStatus
                              | zimbraEmptyFolderOpTimeout
                              | zimbraErrorReportUrl
                              | zimbraExternalAccountProvisioningKey
                              | zimbraExternalAccountStatusCheckInterval
                              | zimbraExternalShareInvitationUrlExpiration
                              | zimbraFeatureDistributionListFolderEnabled
                              | zimbraFileUploadMaxSize
                              | zimbraFileUploadMaxSizePerFile
                              | zimbraForceClearCookies
                              | zimbraFreebusyExchangeAuthPassword
                              | zimbraFreebusyExchangeAuthScheme
                              | zimbraFreebusyExchangeAuthUsername
                              | zimbraFreebusyExchangeCachedInterval
                              | zimbraFreebusyExchangeCachedIntervalStart
                              | zimbraFreebusyExchangeServerType
                              | zimbraFreebusyExchangeURL
                              | zimbraFreebusyExchangeUserOrg
                              | zimbraFreebusyExternalZimbraURL
                              | zimbraFreebusyPropagationRetryInterval
                              | zimbraGalAlwaysIncludeLocalCalendarResources
                              | zimbraGalAutoCompleteLdapFilter
                              | zimbraGalGroupIndicatorEnabled
                              | zimbraGalInternalSearchBase
                              | zimbraGalLdapAttrMap
                              | zimbraGalLdapFilterDef
                              | zimbraGalLdapGroupHandlerClass
                              | zimbraGalLdapPageSize
                              | zimbraGalLdapValueMap
                              | zimbraGalMaxResults
                              | zimbraGalSyncInternalSearchBase
                              | zimbraGalSyncLdapPageSize
                              | zimbraGalSyncMaxConcurrentClients
                              | zimbraGalSyncTimestampFormat
                              | zimbraGalTokenizeAutoCompleteKey
                              | zimbraGalTokenizeSearchKey
                              | zimbraGlobalConfigExtraObjectClass
                              | zimbraHelpAdminURL
                              | zimbraHelpAdvancedURL
                              | zimbraHelpDelegatedURL
                              | zimbraHelpStandardURL
                              | zimbraHsmAge
                              | zimbraHsmBatchSize
                              | zimbraHsmMovePreviousRevisions
                              | zimbraHsmPolicy
                              | zimbraHttpCompressionEnabled
                              | zimbraHttpConnectorMaxIdleTimeMillis
                              | zimbraHttpContextPathBasedThreadPoolBalancingFilterRules
                              | zimbraHttpDebugHandlerEnabled
                              | zimbraHttpDosFilterDelayMillis
                              | zimbraHttpDosFilterMaxRequestsPerSec
                              | zimbraHttpHeaderCacheSize
                              | zimbraHttpMaxFormContentSize
                              | zimbraHttpNumThreads
                              | zimbraHttpOutputBufferSize
                              | zimbraHttpProxyURL
                              | zimbraHttpRequestHeaderSize
                              | zimbraHttpResponseHeaderSize
                              | zimbraHttpSSLNumThreads
                              | zimbraHttpThreadPoolMaxIdleTimeMillis
                              | zimbraHttpThrottleSafeIPs
                              | zimbraIPMode
                              | zimbraImapBindOnStartup
                              | zimbraImapBindPort
                              | zimbraImapCleartextLoginEnabled
                              | zimbraImapDisabledCapability
                              | zimbraImapExposeVersionOnBanner
                              | zimbraImapMaxConnections
                              | zimbraImapMaxRequestSize
                              | zimbraImapNumThreads
                              | zimbraImapProxyBindPort
                              | zimbraImapSSLBindOnStartup
                              | zimbraImapSSLBindPort
                              | zimbraImapSSLDisabledCapability
                              | zimbraImapSSLProxyBindPort
                              | zimbraImapSSLServerEnabled
                              | zimbraImapSaslGssapiEnabled
                              | zimbraImapServerEnabled
                              | zimbraImapShutdownGraceSeconds
                              | zimbraInstalledSkin
                              | zimbraInternalSharingCrossDomainEnabled
                              | zimbraInvalidLoginFilterDelayInMinBetwnReqBeforeReinstating
                              | zimbraInvalidLoginFilterMaxFailedLogin
                              | zimbraInvalidLoginFilterMaxSizeOfFailedIpDb
                              | zimbraInvalidLoginFilterReinstateIpTaskIntervalInMin
                              | zimbraItemActionBatchSize
                              | zimbraLastLogonTimestampFrequency
                              | zimbraLastPurgeMaxDuration
                              | zimbraLdapGalSyncDisabled
                              | zimbraLmtpBindOnStartup
                              | zimbraLmtpBindPort
                              | zimbraLmtpExposeVersionOnBanner
                              | zimbraLmtpLHLORequired
                              | zimbraLmtpNumThreads
                              | zimbraLmtpPermanentFailureWhenOverQuota
                              | zimbraLmtpServerEnabled
                              | zimbraLmtpShutdownGraceSeconds
                              | zimbraLocale
                              | zimbraLogHostname
                              | zimbraLogRawLifetime
                              | zimbraLogSummaryLifetime
                              | zimbraLogToSyslog
                              | zimbraLowestSupportedAuthVersion
                              | zimbraMailAddressValidationRegex
                              | zimbraMailClearTextPasswordEnabled
                              | zimbraMailContentMaxSize
                              | zimbraMailDiskStreamingThreshold
                              | zimbraMailDomainQuota
                              | zimbraMailEmptyFolderBatchSize
                              | zimbraMailEmptyFolderBatchThreshold
                              | zimbraMailFileDescriptorBufferSize
                              | zimbraMailFileDescriptorCacheSize
                              | zimbraMailKeepOutWebCrawlers
                              | zimbraMailMode
                              | zimbraMailPort
                              | zimbraMailProxyMaxFails
                              | zimbraMailProxyPort
                              | zimbraMailProxyReconnectTimeout
                              | zimbraMailPurgeBatchSize
                              | zimbraMailPurgeSleepInterval
                              | zimbraMailPurgeSystemPolicy
                              | zimbraMailRedirectSetEnvelopeSender
                              | zimbraMailReferMode
                              | zimbraMailSSLClientCertMode
                              | zimbraMailSSLClientCertOCSPEnabled
                              | zimbraMailSSLClientCertPort
                              | zimbraMailSSLClientCertPrincipalMap
                              | zimbraMailSSLClientCertPrincipalMapLdapFilterEnabled
                              | zimbraMailSSLPort
                              | zimbraMailSSLProxyClientCertPort
                              | zimbraMailSSLProxyPort
                              | zimbraMailTrustedIP
                              | zimbraMailURL
                              | zimbraMailUncompressedCacheMaxBytes
                              | zimbraMailUncompressedCacheMaxFiles
                              | zimbraMailUseDirectBuffers
                              | zimbraMailboxMoveSkipBlobs
                              | zimbraMailboxMoveSkipHsmBlobs
                              | zimbraMailboxMoveSkipSearchIndex
                              | zimbraMailboxMoveTempDir
                              | zimbraMailboxdSSLProtocols
                              | zimbraMemcachedBindPort
                              | zimbraMemcachedClientBinaryProtocolEnabled
                              | zimbraMemcachedClientExpirySeconds
                              | zimbraMemcachedClientHashAlgorithm
                              | zimbraMemcachedClientServerList
                              | zimbraMemcachedClientTimeoutMillis
                              | zimbraMessageCacheSize
                              | zimbraMessageChannelEnabled
                              | zimbraMessageChannelPort
                              | zimbraMessageIdDedupeCacheSize
                              | zimbraMessageIdDedupeCacheTimeout
                              | zimbraMilterBindPort
                              | zimbraMilterMaxConnections
                              | zimbraMilterNumThreads
                              | zimbraMilterServerEnabled
                              | zimbraMobileItemsToTrackPerFolderMaxSize
                              | zimbraMobileMaxMessageSize
                              | zimbraMobileMetadataMaxSizeEnabled
                              | zimbraMobileMetadataRetentionPolicy
                              | zimbraMtaAddressVerifyNegativeRefreshTime
                              | zimbraMtaAddressVerifyPollCount
                              | zimbraMtaAddressVerifyPollDelay
                              | zimbraMtaAddressVerifyPositiveRefreshTime
                              | zimbraMtaAliasMaps
                              | zimbraMtaAlwaysAddMissingHeaders
                              | zimbraMtaAntiSpamLockMethod
                              | zimbraMtaAuthEnabled
                              | zimbraMtaAuthHost
                              | zimbraMtaAuthTarget
                              | zimbraMtaAuthURL
                              | zimbraMtaBlockedExtension
                              | zimbraMtaBlockedExtensionWarnAdmin
                              | zimbraMtaBlockedExtensionWarnRecipient
                              | zimbraMtaBounceNoticeRecipient
                              | zimbraMtaBounceQueueLifetime
                              | zimbraMtaBrokenSaslAuthClients
                              | zimbraMtaCommandDirectory
                              | zimbraMtaCommonBlockedExtension
                              | zimbraMtaDaemonDirectory
                              | zimbraMtaDefaultProcessLimit
                              | zimbraMtaDelayWarningTime
                              | zimbraMtaDnsLookupsEnabled
                              | zimbraMtaEnableSmtpdPolicyd
                              | zimbraMtaFallbackRelayHost
                              | zimbraMtaHeaderChecks
                              | zimbraMtaImportEnvironment
                              | zimbraMtaInFlowDelay
                              | zimbraMtaLmdbMapSize
                              | zimbraMtaLmtpConnectionCacheDestinations
                              | zimbraMtaLmtpConnectionCacheTimeLimit
                              | zimbraMtaLmtpHostLookup
                              | zimbraMtaLmtpTlsCAfile
                              | zimbraMtaLmtpTlsCApath
                              | zimbraMtaLmtpTlsCiphers
                              | zimbraMtaLmtpTlsExcludeCiphers
                              | zimbraMtaLmtpTlsLoglevel
                              | zimbraMtaLmtpTlsMandatoryCiphers
                              | zimbraMtaLmtpTlsProtocols
                              | zimbraMtaLmtpTlsSecurityLevel
                              | zimbraMtaMailqPath
                              | zimbraMtaManpageDirectory
                              | zimbraMtaMaxMessageSize
                              | zimbraMtaMaxUse
                              | zimbraMtaMaximalBackoffTime
                              | zimbraMtaMilterCommandTimeout
                              | zimbraMtaMilterConnectTimeout
                              | zimbraMtaMilterContentTimeout
                              | zimbraMtaMilterDefaultAction
                              | zimbraMtaMinimalBackoffTime
                              | zimbraMtaMyDestination
                              | zimbraMtaMyHostname
                              | zimbraMtaMyNetworks
                              | zimbraMtaMyOrigin
                              | zimbraMtaNewaliasesPath
                              | zimbraMtaNonSmtpdMilters
                              | zimbraMtaNotifyClasses
                              | zimbraMtaPolicyTimeLimit
                              | zimbraMtaPropagateUnmatchedExtensions
                              | zimbraMtaQueueDirectory
                              | zimbraMtaQueueRunDelay
                              | zimbraMtaRecipientDelimiter
                              | zimbraMtaRelayHost
                              | zimbraMtaRestriction
                              | zimbraMtaSaslAuthEnable
                              | zimbraMtaSaslSmtpdMechList
                              | zimbraMtaSenderCanonicalMaps
                              | zimbraMtaSendmailPath
                              | zimbraMtaSmtpCnameOverridesServername
                              | zimbraMtaSmtpGenericMaps
                              | zimbraMtaSmtpHeloName
                              | zimbraMtaSmtpSaslAuthEnable
                              | zimbraMtaSmtpSaslMechanismFilter
                              | zimbraMtaSmtpSaslPasswordMaps
                              | zimbraMtaSmtpSaslSecurityOptions
                              | zimbraMtaSmtpTlsCAfile
                              | zimbraMtaSmtpTlsCApath
                              | zimbraMtaSmtpTlsCiphers
                              | zimbraMtaSmtpTlsLoglevel
                              | zimbraMtaSmtpTlsMandatoryCiphers
                              | zimbraMtaSmtpTlsProtocols
                              | zimbraMtaSmtpTlsSecurityLevel
                              | zimbraMtaSmtpdBanner
                              | zimbraMtaSmtpdClientPortLogging
                              | zimbraMtaSmtpdClientRestrictions
                              | zimbraMtaSmtpdDataRestrictions
                              | zimbraMtaSmtpdErrorSleepTime
                              | zimbraMtaSmtpdHardErrorLimit
                              | zimbraMtaSmtpdHeloRequired
                              | zimbraMtaSmtpdMilters
                              | zimbraMtaSmtpdProxyTimeout
                              | zimbraMtaSmtpdRejectUnlistedRecipient
                              | zimbraMtaSmtpdRejectUnlistedSender
                              | zimbraMtaSmtpdSaslAuthenticatedHeader
                              | zimbraMtaSmtpdSaslSecurityOptions
                              | zimbraMtaSmtpdSaslTlsSecurityOptions
                              | zimbraMtaSmtpdSenderLoginMaps
                              | zimbraMtaSmtpdSenderRestrictions
                              | zimbraMtaSmtpdTlsAskCcert
                              | zimbraMtaSmtpdTlsCAfile
                              | zimbraMtaSmtpdTlsCApath
                              | zimbraMtaSmtpdTlsCcertVerifydepth
                              | zimbraMtaSmtpdTlsCiphers
                              | zimbraMtaSmtpdTlsExcludeCiphers
                              | zimbraMtaSmtpdTlsLoglevel
                              | zimbraMtaSmtpdTlsMandatoryCiphers
                              | zimbraMtaSmtpdTlsProtocols
                              | zimbraMtaSmtpdVirtualTransport
                              | zimbraMtaStpdSoftErrorLimit
                              | zimbraMtaTlsAppendDefaultCA
                              | zimbraMtaTlsAuthOnly
                              | zimbraMtaTlsSecurityLevel
                              | zimbraMtaTransportMaps
                              | zimbraMtaUnverifiedRecipientDeferCode
                              | zimbraMtaVirtualAliasDomains
                              | zimbraMtaVirtualAliasExpansionLimit
                              | zimbraMtaVirtualAliasMaps
                              | zimbraMtaVirtualMailboxDomains
                              | zimbraMtaVirtualMailboxMaps
                              | zimbraMyoneloginSamlSigningCert
                              | zimbraNetworkActivation
                              | zimbraNetworkLicense
                              | zimbraNotebookAccount
                              | zimbraNotebookFolderCacheSize
                              | zimbraNotebookMaxCachedTemplatesPerFolder
                              | zimbraNotebookPageCacheSize
                              | zimbraNotifyBindAddress
                              | zimbraNotifyBindPort
                              | zimbraNotifySSLBindAddress
                              | zimbraNotifySSLBindPort
                              | zimbraNotifySSLServerEnabled
                              | zimbraNotifyServerEnabled
                              | zimbraOAuthConsumerCredentials
                              | zimbraOpenidConsumerAllowedOPEndpointURL
                              | zimbraOpenidConsumerStatelessModeEnabled
                              | zimbraPasswordChangeListener
                              | zimbraPop3BindOnStartup
                              | zimbraPop3BindPort
                              | zimbraPop3CleartextLoginEnabled
                              | zimbraPop3ExposeVersionOnBanner
                              | zimbraPop3MaxConnections
                              | zimbraPop3NumThreads
                              | zimbraPop3ProxyBindPort
                              | zimbraPop3SSLBindOnStartup
                              | zimbraPop3SSLBindPort
                              | zimbraPop3SSLProxyBindPort
                              | zimbraPop3SSLServerEnabled
                              | zimbraPop3SaslGssapiEnabled
                              | zimbraPop3ServerEnabled
                              | zimbraPop3ShutdownGraceSeconds
                              | zimbraPrevFoldersToTrackMax
                              | zimbraProduct
                              | zimbraPublicServiceHostname
                              | zimbraPublicServicePort
                              | zimbraPublicServiceProtocol
                              | zimbraRedoLogArchiveDir
                              | zimbraRedoLogCrashRecoveryLookbackSec
                              | zimbraRedoLogDeleteOnRollover
                              | zimbraRedoLogEnabled
                              | zimbraRedoLogFsyncIntervalMS
                              | zimbraRedoLogLogPath
                              | zimbraRedoLogProvider
                              | zimbraRedoLogRolloverFileSizeKB
                              | zimbraRedoLogRolloverHardMaxFileSizeKB
                              | zimbraRedoLogRolloverMinFileAge
                              | zimbraRegexMaxAccessesWhenMatching
                              | zimbraRemoteManagementCommand
                              | zimbraRemoteManagementPort
                              | zimbraRemoteManagementPrivateKeyPath
                              | zimbraRemoteManagementUser
                              | zimbraResponseHeader
                              | zimbraReverseProxyAcceptMutex
                              | zimbraReverseProxyAdminEnabled
                              | zimbraReverseProxyAdminIPAddress
                              | zimbraReverseProxyAdminPortAttribute
                              | zimbraReverseProxyAuthWaitInterval
                              | zimbraReverseProxyAvailableLookupTargets
                              | zimbraReverseProxyCacheEntryTTL
                              | zimbraReverseProxyCacheFetchTimeout
                              | zimbraReverseProxyCacheReconnectInterval
                              | zimbraReverseProxyClientCertCA
                              | zimbraReverseProxyClientCertMode
                              | zimbraReverseProxyConnectTimeout
                              | zimbraReverseProxyDefaultRealm
                              | zimbraReverseProxyDnsLookupInServerEnabled
                              | zimbraReverseProxyDomainNameAttribute
                              | zimbraReverseProxyDomainNameQuery
                              | zimbraReverseProxyDomainNameSearchBase
                              | zimbraReverseProxyErrorHandlerURL
                              | zimbraReverseProxyExactServerVersionCheck
                              | zimbraReverseProxyExternalRouteIncludeOriginalAuthusername
                              | zimbraReverseProxyGenConfigPerVirtualHostname
                              | zimbraReverseProxyHttpEnabled
                              | zimbraReverseProxyHttpPortAttribute
                              | zimbraReverseProxyHttpSSLPortAttribute
                              | zimbraReverseProxyIPLoginLimit
                              | zimbraReverseProxyIPLoginLimitTime
                              | zimbraReverseProxyImapEnabledCapability
                              | zimbraReverseProxyImapExposeVersionOnBanner
                              | zimbraReverseProxyImapPortAttribute
                              | zimbraReverseProxyImapSSLPortAttribute
                              | zimbraReverseProxyImapSaslGssapiEnabled
                              | zimbraReverseProxyImapSaslPlainEnabled
                              | zimbraReverseProxyImapStartTlsMode
                              | zimbraReverseProxyInactivityTimeout
                              | zimbraReverseProxyIpThrottleMsg
                              | zimbraReverseProxyLogLevel
                              | zimbraReverseProxyLookupTarget
                              | zimbraReverseProxyMailEnabled
                              | zimbraReverseProxyMailHostAttribute
                              | zimbraReverseProxyMailHostQuery
                              | zimbraReverseProxyMailHostSearchBase
                              | zimbraReverseProxyMailImapEnabled
                              | zimbraReverseProxyMailImapsEnabled
                              | zimbraReverseProxyMailMode
                              | zimbraReverseProxyMailPop3Enabled
                              | zimbraReverseProxyMailPop3sEnabled
                              | zimbraReverseProxyPassErrors
                              | zimbraReverseProxyPop3EnabledCapability
                              | zimbraReverseProxyPop3ExposeVersionOnBanner
                              | zimbraReverseProxyPop3PortAttribute
                              | zimbraReverseProxyPop3SSLPortAttribute
                              | zimbraReverseProxyPop3SaslGssapiEnabled
                              | zimbraReverseProxyPop3SaslPlainEnabled
                              | zimbraReverseProxyPop3StartTlsMode
                              | zimbraReverseProxyPortQuery
                              | zimbraReverseProxyPortSearchBase
                              | zimbraReverseProxyRouteLookupTimeout
                              | zimbraReverseProxyRouteLookupTimeoutCache
                              | zimbraReverseProxySSLCiphers
                              | zimbraReverseProxySSLECDHCurve
                              | zimbraReverseProxySSLProtocols
                              | zimbraReverseProxySSLToUpstreamEnabled
                              | zimbraReverseProxySendImapId
                              | zimbraReverseProxySendPop3Xoip
                              | zimbraReverseProxyUpstreamConnectTimeout
                              | zimbraReverseProxyUpstreamEwsServers
                              | zimbraReverseProxyUpstreamLoginServers
                              | zimbraReverseProxyUpstreamPollingTimeout
                              | zimbraReverseProxyUpstreamReadTimeout
                              | zimbraReverseProxyUpstreamSendTimeout
                              | zimbraReverseProxyUpstreamServers
                              | zimbraReverseProxyUserLoginLimit
                              | zimbraReverseProxyUserLoginLimitTime
                              | zimbraReverseProxyUserNameAttribute
                              | zimbraReverseProxyUserThrottleMsg
                              | zimbraReverseProxyWorkerConnections
                              | zimbraReverseProxyWorkerProcesses
                              | zimbraSMIMELdapAttribute
                              | zimbraSMIMELdapBindDn
                              | zimbraSMIMELdapBindPassword
                              | zimbraSMIMELdapDiscoverSearchBaseEnabled
                              | zimbraSMIMELdapFilter
                              | zimbraSMIMELdapSearchBase
                              | zimbraSMIMELdapStartTlsEnabled
                              | zimbraSMIMELdapURL
                              | zimbraSSLCertificate
                              | zimbraSSLExcludeCipherSuites
                              | zimbraSSLIncludeCipherSuites
                              | zimbraSSLPrivateKey
                              | zimbraSaslGssapiRequiresTls
                              | zimbraScheduledTaskNumThreads
                              | zimbraServerExtraObjectClass
                              | zimbraServerInheritedAttr
                              | zimbraShareNotificationMtaAuthAccount
                              | zimbraShareNotificationMtaAuthPassword
                              | zimbraShareNotificationMtaAuthRequired
                              | zimbraShareNotificationMtaConnectionType
                              | zimbraShareNotificationMtaEnabled
                              | zimbraShareNotificationMtaHostname
                              | zimbraShareNotificationMtaPort
                              | zimbraSharingUpdatePublishInterval
                              | zimbraSkinBackgroundColor
                              | zimbraSkinFavicon
                              | zimbraSkinForegroundColor
                              | zimbraSkinLogoAppBanner
                              | zimbraSkinLogoLoginBanner
                              | zimbraSkinLogoURL
                              | zimbraSkinSecondaryColor
                              | zimbraSkinSelectionColor
                              | zimbraSmtpHostname
                              | zimbraSmtpPort
                              | zimbraSmtpSendAddAuthenticatedUser
                              | zimbraSmtpSendAddMailer
                              | zimbraSmtpSendAddOriginatingIP
                              | zimbraSmtpSendPartial
                              | zimbraSmtpTimeout
                              | zimbraSoapExposeVersion
                              | zimbraSoapRequestMaxSize
                              | zimbraSpamCheckEnabled
                              | zimbraSpamHeader
                              | zimbraSpamHeaderValue
                              | zimbraSpamIsNotSpamAccount
                              | zimbraSpamIsSpamAccount
                              | zimbraSpamKillPercent
                              | zimbraSpamReportEnvelopeFrom
                              | zimbraSpamReportSenderHeader
                              | zimbraSpamReportTypeHam
                              | zimbraSpamReportTypeHeader
                              | zimbraSpamReportTypeSpam
                              | zimbraSpamSubjectTag
                              | zimbraSpamTagPercent
                              | zimbraSpamTrashAlias
                              | zimbraSpamWhitelistHeader
                              | zimbraSpamWhitelistHeaderValue
                              | zimbraSpellAvailableDictionary
                              | zimbraSpellCheckURL
                              | zimbraSpnegoAuthEnabled
                              | zimbraSpnegoAuthErrorURL
                              | zimbraSpnegoAuthRealm
                              | zimbraSslCaCert
                              | zimbraSslCaKey
                              | zimbraStatThreadNamePrefix
                              | zimbraTableMaintenanceGrowthFactor
                              | zimbraTableMaintenanceMaxRows
                              | zimbraTableMaintenanceMinRows
                              | zimbraTableMaintenanceOperation
                              | zimbraThreadMonitorEnabled
                              | zimbraThrottleSafeHosts
                              | zimbraThrottleWhitelist
                              | zimbraUCProviderEnabled
                              | zimbraVersionCheckInterval
                              | zimbraVersionCheckLastAttempt
                              | zimbraVersionCheckLastResponse
                              | zimbraVersionCheckLastSuccess
                              | zimbraVersionCheckNotificationBody
                              | zimbraVersionCheckNotificationEmail
                              | zimbraVersionCheckNotificationEmailFrom
                              | zimbraVersionCheckNotificationSubject
                              | zimbraVersionCheckSendNotifications
                              | zimbraVersionCheckServer
                              | zimbraVersionCheckURL
                              | zimbraVirusBlockEncryptedArchive
                              | zimbraVirusCheckEnabled
                              | zimbraVirusDefinitionsUpdateFrequency
                              | zimbraVirusWarnAdmin
                              | zimbraVirusWarnRecipient
                              | zimbraWebClientAdminReference
                              | zimbraWebClientLoginURL
                              | zimbraWebClientLoginURLAllowedIP
                              | zimbraWebClientLoginURLAllowedUA
                              | zimbraWebClientLogoutURL
                              | zimbraWebClientLogoutURLAllowedIP
                              | zimbraWebClientLogoutURLAllowedUA
                              | zimbraWebClientMaxInputBufferLength
                              | zimbraWebClientURL
                              | zimbraWebGzipEnabled
                              | zimbraXMPPEnabled
                              | zimbraXMPPServerDialbackKey
                              | zimbraZimletDataSensitiveInMixedModeDisabled
                              | zimbraZimletDomainAvailableZimlets
                              | zimbraZimletJspEnabled
                              | zimbraZookeeperClientServerList }
  LDAP-NAME                 {"zimbraGlobalConfig"}
  LDAP-DESC                 "global config"
  ID                        id-oc-zimbraGlobalConfig }

zimbraDomain OBJECT-CLASS ::= {
  SUBCLASS OF               { zimbraMailRecipient }
  KIND                      auxiliary
  MUST CONTAIN              { zimbraDomainName
                              | zimbraDomainType
                              | zimbraId }
  MAY CONTAIN               { description
                              | zimbraACE
                              | zimbraAdminConsoleCatchAllAddressEnabled
                              | zimbraAdminConsoleDNSCheckEnabled
                              | zimbraAdminConsoleLDAPAuthEnabled
                              | zimbraAdminConsoleLoginMessage
                              | zimbraAdminConsoleLoginURL
                              | zimbraAdminConsoleLogoutURL
                              | zimbraAdminConsoleSkinEnabled
                              | zimbraAggregateQuotaLastUsage
                              | zimbraAmavisDomainDisclaimerHTML
                              | zimbraAmavisDomainDisclaimerText
                              | zimbraAuthFallbackToLocal
                              | zimbraAuthKerberos5Realm
                              | zimbraAuthLdapBindDn
                              | zimbraAuthLdapSearchBase
                              | zimbraAuthLdapSearchBindDn
                              | zimbraAuthLdapSearchBindPassword
                              | zimbraAuthLdapSearchFilter
                              | zimbraAuthLdapStartTlsEnabled
                              | zimbraAuthLdapURL
                              | zimbraAuthMech
                              | zimbraAuthMechAdmin
                              | zimbraAutoProvAccountNameMap
                              | zimbraAutoProvAttrMap
                              | zimbraAutoProvAuthMech
                              | zimbraAutoProvBatchSize
                              | zimbraAutoProvLastPolledTimestamp
                              | zimbraAutoProvLdapAdminBindDn
                              | zimbraAutoProvLdapAdminBindPassword
                              | zimbraAutoProvLdapBindDn
                              | zimbraAutoProvLdapSearchBase
                              | zimbraAutoProvLdapSearchFilter
                              | zimbraAutoProvLdapStartTlsEnabled
                              | zimbraAutoProvLdapURL
                              | zimbraAutoProvListenerClass
                              | zimbraAutoProvLock
                              | zimbraAutoProvMode
                              | zimbraAutoProvNotificationBody
                              | zimbraAutoProvNotificationFromAddress
                              | zimbraAutoProvNotificationSubject
                              | zimbraAvailableSkin
                              | zimbraBasicAuthRealm
                              | zimbraCalendarLocationDisabledFields
                              | zimbraChangePasswordURL
                              | zimbraCommunityAPIClientID
                              | zimbraCommunityAPIClientSecret
                              | zimbraCommunityBaseURL
                              | zimbraCommunityHomeURL
                              | zimbraCommunityUsernameMapping
                              | zimbraCreateTimestamp
                              | zimbraCsrfAllowedRefererHosts
                              | zimbraDNSCheckHostname
                              | zimbraDomainAggregateQuota
                              | zimbraDomainAggregateQuotaPolicy
                              | zimbraDomainAggregateQuotaWarnEmailRecipient
                              | zimbraDomainAggregateQuotaWarnPercent
                              | zimbraDomainAliasTargetId
                              | zimbraDomainCOSMaxAccounts
                              | zimbraDomainDefaultCOSId
                              | zimbraDomainDefaultExternalUserCOSId
                              | zimbraDomainFeatureMaxAccounts
                              | zimbraDomainMandatoryMailSignatureEnabled
                              | zimbraDomainMandatoryMailSignatureHTML
                              | zimbraDomainMandatoryMailSignatureText
                              | zimbraDomainMaxAccounts
                              | zimbraDomainRenameInfo
                              | zimbraDomainStatus
                              | zimbraErrorReportUrl
                              | zimbraExternalGroupHandlerClass
                              | zimbraExternalGroupLdapSearchBase
                              | zimbraExternalGroupLdapSearchFilter
                              | zimbraExternalImapHostname
                              | zimbraExternalImapPort
                              | zimbraExternalImapSSLHostname
                              | zimbraExternalImapSSLPort
                              | zimbraExternalPop3Hostname
                              | zimbraExternalPop3Port
                              | zimbraExternalPop3SSLHostname
                              | zimbraExternalPop3SSLPort
                              | zimbraExternalShareDomainWhitelistEnabled
                              | zimbraExternalShareInvitationUrlExpiration
                              | zimbraExternalShareWhitelistDomain
                              | zimbraExternalSharingEnabled
                              | zimbraFeatureCalendarReminderDeviceEmailEnabled
                              | zimbraFeatureDistributionListFolderEnabled
                              | zimbraFeatureSocialEnabled
                              | zimbraFeatureSocialExternalEnabled
                              | zimbraFeatureSocialExternalURL
                              | zimbraFeatureSocialName
                              | zimbraFileUploadMaxSizePerFile
                              | zimbraForceClearCookies
                              | zimbraForeignName
                              | zimbraForeignNameHandler
                              | zimbraFreebusyExchangeAuthPassword
                              | zimbraFreebusyExchangeAuthScheme
                              | zimbraFreebusyExchangeAuthUsername
                              | zimbraFreebusyExchangeCachedInterval
                              | zimbraFreebusyExchangeCachedIntervalStart
                              | zimbraFreebusyExchangeServerType
                              | zimbraFreebusyExchangeURL
                              | zimbraFreebusyExchangeUserOrg
                              | zimbraGalAccountId
                              | zimbraGalAlwaysIncludeLocalCalendarResources
                              | zimbraGalAutoCompleteLdapFilter
                              | zimbraGalDefinitionLastModifiedTime
                              | zimbraGalGroupIndicatorEnabled
                              | zimbraGalInternalSearchBase
                              | zimbraGalLdapAttrMap
                              | zimbraGalLdapAuthMech
                              | zimbraGalLdapBindDn
                              | zimbraGalLdapBindPassword
                              | zimbraGalLdapFilter
                              | zimbraGalLdapGroupHandlerClass
                              | zimbraGalLdapKerberos5Keytab
                              | zimbraGalLdapKerberos5Principal
                              | zimbraGalLdapPageSize
                              | zimbraGalLdapSearchBase
                              | zimbraGalLdapStartTlsEnabled
                              | zimbraGalLdapURL
                              | zimbraGalLdapValueMap
                              | zimbraGalMaxResults
                              | zimbraGalMode
                              | zimbraGalSyncInternalSearchBase
                              | zimbraGalSyncLdapAuthMech
                              | zimbraGalSyncLdapBindDn
                              | zimbraGalSyncLdapBindPassword
                              | zimbraGalSyncLdapFilter
                              | zimbraGalSyncLdapKerberos5Keytab
                              | zimbraGalSyncLdapKerberos5Principal
                              | zimbraGalSyncLdapPageSize
                              | zimbraGalSyncLdapSearchBase
                              | zimbraGalSyncLdapStartTlsEnabled
                              | zimbraGalSyncLdapURL
                              | zimbraGalSyncMaxConcurrentClients
                              | zimbraGalSyncTimestampFormat
                              | zimbraGalTokenizeAutoCompleteKey
                              | zimbraGalTokenizeSearchKey
                              | zimbraHelpAdminURL
                              | zimbraHelpAdvancedURL
                              | zimbraHelpDelegatedURL
                              | zimbraHelpStandardURL
                              | zimbraInternalSendersDomain
                              | zimbraInternalSharingCrossDomainEnabled
                              | zimbraInternalSharingDomain
                              | zimbraLdapGalSyncDisabled
                              | zimbraLocale
                              | zimbraMailAddressValidationRegex
                              | zimbraMailDomainQuota
                              | zimbraMailSSLClientCertPrincipalMap
                              | zimbraMailTrustedSenderListMaxNumEntries
                              | zimbraMobileItemsToTrackPerFolderMaxSize
                              | zimbraMobileMetadataMaxSizeEnabled
                              | zimbraMyoneloginSamlSigningCert
                              | zimbraNotebookAccount
                              | zimbraNotes
                              | zimbraOAuthConsumerCredentials
                              | zimbraOpenidConsumerAllowedOPEndpointURL
                              | zimbraPasswordChangeListener
                              | zimbraPreAuthKey
                              | zimbraPrefColorMessagesEnabled
                              | zimbraPrefMailTrustedSenderList
                              | zimbraPrefSkin
                              | zimbraPrefSpellIgnoreWord
                              | zimbraPrefTimeZoneId
                              | zimbraPublicServiceHostname
                              | zimbraPublicServicePort
                              | zimbraPublicServiceProtocol
                              | zimbraPublicSharingEnabled
                              | zimbraResponseHeader
                              | zimbraReverseProxyClientCertCA
                              | zimbraReverseProxyClientCertMode
                              | zimbraReverseProxyExternalRouteIncludeOriginalAuthusername
                              | zimbraReverseProxyUseExternalRoute
                              | zimbraReverseProxyUseExternalRouteIfAccountNotExist
                              | zimbraSMIMELdapAttribute
                              | zimbraSMIMELdapBindDn
                              | zimbraSMIMELdapBindPassword
                              | zimbraSMIMELdapDiscoverSearchBaseEnabled
                              | zimbraSMIMELdapFilter
                              | zimbraSMIMELdapSearchBase
                              | zimbraSMIMELdapStartTlsEnabled
                              | zimbraSMIMELdapURL
                              | zimbraSSLCertificate
                              | zimbraSSLPrivateKey
                              | zimbraSkinBackgroundColor
                              | zimbraSkinFavicon
                              | zimbraSkinForegroundColor
                              | zimbraSkinLogoAppBanner
                              | zimbraSkinLogoLoginBanner
                              | zimbraSkinLogoURL
                              | zimbraSkinSecondaryColor
                              | zimbraSkinSelectionColor
                              | zimbraSmtpHostname
                              | zimbraSmtpPort
                              | zimbraSmtpSendPartial
                              | zimbraSmtpTimeout
                              | zimbraSpamTrashAlias
                              | zimbraStandardClientCustomPrefTab
                              | zimbraStandardClientCustomPrefTabsEnabled
                              | zimbraUCServiceId
                              | zimbraVirtualHostname
                              | zimbraVirtualIPAddress
                              | zimbraWebClientAdminReference
                              | zimbraWebClientLoginURL
                              | zimbraWebClientLoginURLAllowedIP
                              | zimbraWebClientLoginURLAllowedUA
                              | zimbraWebClientLogoutURL
                              | zimbraWebClientLogoutURLAllowedIP
                              | zimbraWebClientLogoutURLAllowedUA
                              | zimbraWebClientMaxInputBufferLength
                              | zimbraZimletDataSensitiveInMixedModeDisabled
                              | zimbraZimletDomainAvailableZimlets }
  LDAP-NAME                 {"zimbraDomain"}
  LDAP-DESC                 "Domain object"
  ID                        id-oc-zimbraDomain }

zimbraSecurityGroup OBJECT-CLASS ::= {
  SUBCLASS OF               { top }
  KIND                      auxiliary
  MUST CONTAIN              { zimbraGroupId }
  LDAP-NAME                 {"zimbraSecurityGroup"}
  LDAP-DESC                 "Security Group"
  ID                        id-oc-zimbraSecurityGroup }

zimbraServer OBJECT-CLASS ::= {
  SUBCLASS OF               { top }
  MUST CONTAIN              { commonName
                              | zimbraId }
  MAY CONTAIN               { description
                              | zimbraACE
                              | zimbraAdminBindAddress
                              | zimbraAdminImapImportNumThreads
                              | zimbraAdminLocalBind
                              | zimbraAdminPort
                              | zimbraAdminProxyPort
                              | zimbraAdminURL
                              | zimbraAlwaysOnClusterId
                              | zimbraAmavisDSPAMEnabled
                              | zimbraAmavisEnableDKIMVerification
                              | zimbraAmavisFinalSpamDestiny
                              | zimbraAmavisLogLevel
                              | zimbraAmavisMaxServers
                              | zimbraAmavisOriginatingBypassSA
                              | zimbraAmavisSALogLevel
                              | zimbraAntispamExtractionBatchDelay
                              | zimbraAntispamExtractionBatchSize
                              | zimbraAttachmentsIndexedTextLimit
                              | zimbraAttachmentsScanEnabled
                              | zimbraAttachmentsScanURL
                              | zimbraAuthTokenNotificationInterval
                              | zimbraAutoProvPollingInterval
                              | zimbraAutoProvScheduledDomains
                              | zimbraBackupAutoGroupedInterval
                              | zimbraBackupAutoGroupedNumGroups
                              | zimbraBackupAutoGroupedThrottled
                              | zimbraBackupMinFreeSpace
                              | zimbraBackupMode
                              | zimbraBackupReportEmailRecipients
                              | zimbraBackupReportEmailSender
                              | zimbraBackupReportEmailSubjectPrefix
                              | zimbraBackupSkipBlobs
                              | zimbraBackupSkipHsmBlobs
                              | zimbraBackupSkipSearchIndex
                              | zimbraBackupTarget
                              | zimbraCBPolicydAccessControlEnabled
                              | zimbraCBPolicydAccountingEnabled
                              | zimbraCBPolicydAmavisEnabled
                              | zimbraCBPolicydBindPort
                              | zimbraCBPolicydBypassMode
                              | zimbraCBPolicydBypassTimeout
                              | zimbraCBPolicydCheckHeloEnabled
                              | zimbraCBPolicydCheckSPFEnabled
                              | zimbraCBPolicydGreylistingBlacklistMsg
                              | zimbraCBPolicydGreylistingDeferMsg
                              | zimbraCBPolicydGreylistingEnabled
                              | zimbraCBPolicydGreylistingTrainingEnabled
                              | zimbraCBPolicydLogLevel
                              | zimbraCBPolicydMaxRequests
                              | zimbraCBPolicydMaxServers
                              | zimbraCBPolicydMaxSpareServers
                              | zimbraCBPolicydMinServers
                              | zimbraCBPolicydMinSpareServers
                              | zimbraCBPolicydQuotasEnabled
                              | zimbraCBPolicydTimeoutBusy
                              | zimbraCBPolicydTimeoutIdle
                              | zimbraCalendarCalDavClearTextPasswordEnabled
                              | zimbraCalendarCalDavDefaultCalendarId
                              | zimbraCalendarRecurrenceDailyMaxDays
                              | zimbraCalendarRecurrenceMaxInstances
                              | zimbraCalendarRecurrenceMonthlyMaxMonths
                              | zimbraCalendarRecurrenceOtherFrequencyMaxYears
                              | zimbraCalendarRecurrenceWeeklyMaxWeeks
                              | zimbraCalendarRecurrenceYearlyMaxYears
                              | zimbraClamAVBindAddress
                              | zimbraClamAVListenPort
                              | zimbraClamAVMaxThreads
                              | zimbraClusterType
                              | zimbraConfiguredServerIDForBlobDirEnabled
                              | zimbraContactHiddenAttributes
                              | zimbraContactRankingTableRefreshInterval
                              | zimbraConvertdURL
                              | zimbraCreateTimestamp
                              | zimbraDNSMasterIP
                              | zimbraDNSTCPUpstream
                              | zimbraDNSUseTCP
                              | zimbraDNSUseUDP
                              | zimbraDatabaseSlowSqlThreshold
                              | zimbraEmptyFolderOpTimeout
                              | zimbraExtensionBindAddress
                              | zimbraExternalAccountStatusCheckInterval
                              | zimbraFileUploadMaxSize
                              | zimbraFreebusyPropagationRetryInterval
                              | zimbraHsmAge
                              | zimbraHsmBatchSize
                              | zimbraHsmMovePreviousRevisions
                              | zimbraHsmPolicy
                              | zimbraHttpCompressionEnabled
                              | zimbraHttpConnectorMaxIdleTimeMillis
                              | zimbraHttpContextPathBasedThreadPoolBalancingFilterRules
                              | zimbraHttpDebugHandlerEnabled
                              | zimbraHttpDosFilterDelayMillis
                              | zimbraHttpDosFilterMaxRequestsPerSec
                              | zimbraHttpHeaderCacheSize
                              | zimbraHttpMaxFormContentSize
                              | zimbraHttpNumThreads
                              | zimbraHttpOutputBufferSize
                              | zimbraHttpProxyURL
                              | zimbraHttpRequestHeaderSize
                              | zimbraHttpResponseHeaderSize
                              | zimbraHttpSSLNumThreads
                              | zimbraHttpThreadPoolMaxIdleTimeMillis
                              | zimbraHttpThrottleSafeIPs
                              | zimbraIMBindAddress
                              | zimbraIPMode
                              | zimbraImapAdvertisedName
                              | zimbraImapBindAddress
                              | zimbraImapBindOnStartup
                              | zimbraImapBindPort
                              | zimbraImapCleartextLoginEnabled
                              | zimbraImapDisabledCapability
                              | zimbraImapExposeVersionOnBanner
                              | zimbraImapMaxConnections
                              | zimbraImapMaxRequestSize
                              | zimbraImapNumThreads
                              | zimbraImapProxyBindPort
                              | zimbraImapSSLBindAddress
                              | zimbraImapSSLBindOnStartup
                              | zimbraImapSSLBindPort
                              | zimbraImapSSLDisabledCapability
                              | zimbraImapSSLProxyBindPort
                              | zimbraImapSSLServerEnabled
                              | zimbraImapSaslGssapiEnabled
                              | zimbraImapServerEnabled
                              | zimbraImapShutdownGraceSeconds
                              | zimbraInvalidLoginFilterDelayInMinBetwnReqBeforeReinstating
                              | zimbraInvalidLoginFilterMaxFailedLogin
                              | zimbraInvalidLoginFilterMaxSizeOfFailedIpDb
                              | zimbraInvalidLoginFilterReinstateIpTaskIntervalInMin
                              | zimbraIsMonitorHost
                              | zimbraItemActionBatchSize
                              | zimbraLastPurgeMaxDuration
                              | zimbraLmtpAdvertisedName
                              | zimbraLmtpBindAddress
                              | zimbraLmtpBindOnStartup
                              | zimbraLmtpBindPort
                              | zimbraLmtpExposeVersionOnBanner
                              | zimbraLmtpLHLORequired
                              | zimbraLmtpNumThreads
                              | zimbraLmtpPermanentFailureWhenOverQuota
                              | zimbraLmtpServerEnabled
                              | zimbraLmtpShutdownGraceSeconds
                              | zimbraLocale
                              | zimbraLogToSyslog
                              | zimbraLowestSupportedAuthVersion
                              | zimbraMailBindAddress
                              | zimbraMailClearTextPasswordEnabled
                              | zimbraMailContentMaxSize
                              | zimbraMailDiskStreamingThreshold
                              | zimbraMailEmptyFolderBatchSize
                              | zimbraMailEmptyFolderBatchThreshold
                              | zimbraMailFileDescriptorBufferSize
                              | zimbraMailFileDescriptorCacheSize
                              | zimbraMailKeepOutWebCrawlers
                              | zimbraMailLastPurgedMailboxId
                              | zimbraMailLocalBind
                              | zimbraMailMode
                              | zimbraMailPort
                              | zimbraMailProxyMaxFails
                              | zimbraMailProxyPort
                              | zimbraMailProxyReconnectTimeout
                              | zimbraMailPurgeBatchSize
                              | zimbraMailPurgeSleepInterval
                              | zimbraMailRedirectSetEnvelopeSender
                              | zimbraMailReferMode
                              | zimbraMailSSLBindAddress
                              | zimbraMailSSLClientCertBindAddress
                              | zimbraMailSSLClientCertMode
                              | zimbraMailSSLClientCertOCSPEnabled
                              | zimbraMailSSLClientCertPort
                              | zimbraMailSSLPort
                              | zimbraMailSSLProxyClientCertPort
                              | zimbraMailSSLProxyPort
                              | zimbraMailTrustedIP
                              | zimbraMailURL
                              | zimbraMailUncompressedCacheMaxBytes
                              | zimbraMailUncompressedCacheMaxFiles
                              | zimbraMailUseDirectBuffers
                              | zimbraMailboxMoveSkipBlobs
                              | zimbraMailboxMoveSkipHsmBlobs
                              | zimbraMailboxMoveSkipSearchIndex
                              | zimbraMailboxMoveTempDir
                              | zimbraMailboxdSSLProtocols
                              | zimbraMemcachedBindAddress
                              | zimbraMemcachedBindPort
                              | zimbraMemcachedClientBinaryProtocolEnabled
                              | zimbraMemcachedClientExpirySeconds
                              | zimbraMemcachedClientHashAlgorithm
                              | zimbraMemcachedClientServerList
                              | zimbraMemcachedClientTimeoutMillis
                              | zimbraMessageCacheSize
                              | zimbraMessageChannelEnabled
                              | zimbraMessageChannelPort
                              | zimbraMilterBindAddress
                              | zimbraMilterBindPort
                              | zimbraMilterMaxConnections
                              | zimbraMilterNumThreads
                              | zimbraMilterServerEnabled
                              | zimbraMobileMaxMessageSize
                              | zimbraMobileMetadataRetentionPolicy
                              | zimbraMtaAddressVerifyNegativeRefreshTime
                              | zimbraMtaAddressVerifyPollCount
                              | zimbraMtaAddressVerifyPollDelay
                              | zimbraMtaAddressVerifyPositiveRefreshTime
                              | zimbraMtaAliasMaps
                              | zimbraMtaAlwaysAddMissingHeaders
                              | zimbraMtaAntiSpamLockMethod
                              | zimbraMtaAuthEnabled
                              | zimbraMtaAuthHost
                              | zimbraMtaAuthTarget
                              | zimbraMtaAuthURL
                              | zimbraMtaBounceNoticeRecipient
                              | zimbraMtaBounceQueueLifetime
                              | zimbraMtaBrokenSaslAuthClients
                              | zimbraMtaCommandDirectory
                              | zimbraMtaDaemonDirectory
                              | zimbraMtaDefaultProcessLimit
                              | zimbraMtaDelayWarningTime
                              | zimbraMtaDnsLookupsEnabled
                              | zimbraMtaEnableSmtpdPolicyd
                              | zimbraMtaFallbackRelayHost
                              | zimbraMtaHeaderChecks
                              | zimbraMtaImportEnvironment
                              | zimbraMtaInFlowDelay
                              | zimbraMtaLmdbMapSize
                              | zimbraMtaLmtpConnectionCacheDestinations
                              | zimbraMtaLmtpConnectionCacheTimeLimit
                              | zimbraMtaLmtpHostLookup
                              | zimbraMtaLmtpTlsCAfile
                              | zimbraMtaLmtpTlsCApath
                              | zimbraMtaLmtpTlsCiphers
                              | zimbraMtaLmtpTlsExcludeCiphers
                              | zimbraMtaLmtpTlsLoglevel
                              | zimbraMtaLmtpTlsMandatoryCiphers
                              | zimbraMtaLmtpTlsProtocols
                              | zimbraMtaLmtpTlsSecurityLevel
                              | zimbraMtaMailqPath
                              | zimbraMtaManpageDirectory
                              | zimbraMtaMaxUse
                              | zimbraMtaMaximalBackoffTime
                              | zimbraMtaMilterCommandTimeout
                              | zimbraMtaMilterConnectTimeout
                              | zimbraMtaMilterContentTimeout
                              | zimbraMtaMilterDefaultAction
                              | zimbraMtaMinimalBackoffTime
                              | zimbraMtaMyDestination
                              | zimbraMtaMyHostname
                              | zimbraMtaMyNetworks
                              | zimbraMtaMyOrigin
                              | zimbraMtaNewaliasesPath
                              | zimbraMtaNonSmtpdMilters
                              | zimbraMtaNotifyClasses
                              | zimbraMtaPolicyTimeLimit
                              | zimbraMtaPropagateUnmatchedExtensions
                              | zimbraMtaQueueDirectory
                              | zimbraMtaQueueRunDelay
                              | zimbraMtaRelayHost
                              | zimbraMtaRestriction
                              | zimbraMtaSaslAuthEnable
                              | zimbraMtaSaslSmtpdMechList
                              | zimbraMtaSenderCanonicalMaps
                              | zimbraMtaSendmailPath
                              | zimbraMtaSmtpCnameOverridesServername
                              | zimbraMtaSmtpGenericMaps
                              | zimbraMtaSmtpHeloName
                              | zimbraMtaSmtpSaslAuthEnable
                              | zimbraMtaSmtpSaslMechanismFilter
                              | zimbraMtaSmtpSaslPasswordMaps
                              | zimbraMtaSmtpSaslSecurityOptions
                              | zimbraMtaSmtpTlsCAfile
                              | zimbraMtaSmtpTlsCApath
                              | zimbraMtaSmtpTlsCiphers
                              | zimbraMtaSmtpTlsLoglevel
                              | zimbraMtaSmtpTlsMandatoryCiphers
                              | zimbraMtaSmtpTlsProtocols
                              | zimbraMtaSmtpTlsSecurityLevel
                              | zimbraMtaSmtpdBanner
                              | zimbraMtaSmtpdClientPortLogging
                              | zimbraMtaSmtpdClientRestrictions
                              | zimbraMtaSmtpdDataRestrictions
                              | zimbraMtaSmtpdErrorSleepTime
                              | zimbraMtaSmtpdHardErrorLimit
                              | zimbraMtaSmtpdHeloRequired
                              | zimbraMtaSmtpdMilters
                              | zimbraMtaSmtpdProxyTimeout
                              | zimbraMtaSmtpdRejectUnlistedRecipient
                              | zimbraMtaSmtpdRejectUnlistedSender
                              | zimbraMtaSmtpdSaslAuthenticatedHeader
                              | zimbraMtaSmtpdSaslSecurityOptions
                              | zimbraMtaSmtpdSaslTlsSecurityOptions
                              | zimbraMtaSmtpdSenderLoginMaps
                              | zimbraMtaSmtpdSenderRestrictions
                              | zimbraMtaSmtpdTlsAskCcert
                              | zimbraMtaSmtpdTlsCAfile
                              | zimbraMtaSmtpdTlsCApath
                              | zimbraMtaSmtpdTlsCcertVerifydepth
                              | zimbraMtaSmtpdTlsCiphers
                              | zimbraMtaSmtpdTlsExcludeCiphers
                              | zimbraMtaSmtpdTlsLoglevel
                              | zimbraMtaSmtpdTlsMandatoryCiphers
                              | zimbraMtaSmtpdTlsProtocols
                              | zimbraMtaSmtpdVirtualTransport
                              | zimbraMtaStpdSoftErrorLimit
                              | zimbraMtaTlsAppendDefaultCA
                              | zimbraMtaTlsAuthOnly
                              | zimbraMtaTlsSecurityLevel
                              | zimbraMtaTransportMaps
                              | zimbraMtaUnverifiedRecipientDeferCode
                              | zimbraMtaVirtualAliasDomains
                              | zimbraMtaVirtualAliasExpansionLimit
                              | zimbraMtaVirtualAliasMaps
                              | zimbraMtaVirtualMailboxDomains
                              | zimbraMtaVirtualMailboxMaps
                              | zimbraNotebookFolderCacheSize
                              | zimbraNotebookMaxCachedTemplatesPerFolder
                              | zimbraNotebookPageCacheSize
                              | zimbraNotes
                              | zimbraNotifyBindAddress
                              | zimbraNotifyBindPort
                              | zimbraNotifySSLBindAddress
                              | zimbraNotifySSLBindPort
                              | zimbraNotifySSLServerEnabled
                              | zimbraNotifyServerEnabled
                              | zimbraOpenidConsumerStatelessModeEnabled
                              | zimbraPop3AdvertisedName
                              | zimbraPop3BindAddress
                              | zimbraPop3BindOnStartup
                              | zimbraPop3BindPort
                              | zimbraPop3CleartextLoginEnabled
                              | zimbraPop3ExposeVersionOnBanner
                              | zimbraPop3MaxConnections
                              | zimbraPop3NumThreads
                              | zimbraPop3ProxyBindPort
                              | zimbraPop3SSLBindAddress
                              | zimbraPop3SSLBindOnStartup
                              | zimbraPop3SSLBindPort
                              | zimbraPop3SSLProxyBindPort
                              | zimbraPop3SSLServerEnabled
                              | zimbraPop3SaslGssapiEnabled
                              | zimbraPop3ServerEnabled
                              | zimbraPop3ShutdownGraceSeconds
                              | zimbraPrevFoldersToTrackMax
                              | zimbraRedoLogArchiveDir
                              | zimbraRedoLogCrashRecoveryLookbackSec
                              | zimbraRedoLogDeleteOnRollover
                              | zimbraRedoLogEnabled
                              | zimbraRedoLogFsyncIntervalMS
                              | zimbraRedoLogLogPath
                              | zimbraRedoLogProvider
                              | zimbraRedoLogRolloverFileSizeKB
                              | zimbraRedoLogRolloverHardMaxFileSizeKB
                              | zimbraRedoLogRolloverMinFileAge
                              | zimbraRemoteManagementCommand
                              | zimbraRemoteManagementPort
                              | zimbraRemoteManagementPrivateKeyPath
                              | zimbraRemoteManagementUser
                              | zimbraReverseProxyAcceptMutex
                              | zimbraReverseProxyAdminEnabled
                              | zimbraReverseProxyAvailableLookupTargets
                              | zimbraReverseProxyClientCertCA
                              | zimbraReverseProxyClientCertMode
                              | zimbraReverseProxyConnectTimeout
                              | zimbraReverseProxyDefaultRealm
                              | zimbraReverseProxyDnsLookupInServerEnabled
                              | zimbraReverseProxyErrorHandlerURL
                              | zimbraReverseProxyExactServerVersionCheck
                              | zimbraReverseProxyGenConfigPerVirtualHostname
                              | zimbraReverseProxyHttpEnabled
                              | zimbraReverseProxyImapEnabledCapability
                              | zimbraReverseProxyImapExposeVersionOnBanner
                              | zimbraReverseProxyImapSaslGssapiEnabled
                              | zimbraReverseProxyImapSaslPlainEnabled
                              | zimbraReverseProxyImapStartTlsMode
                              | zimbraReverseProxyInactivityTimeout
                              | zimbraReverseProxyLogLevel
                              | zimbraReverseProxyLookupTarget
                              | zimbraReverseProxyMailEnabled
                              | zimbraReverseProxyMailImapEnabled
                              | zimbraReverseProxyMailImapsEnabled
                              | zimbraReverseProxyMailMode
                              | zimbraReverseProxyMailPop3Enabled
                              | zimbraReverseProxyMailPop3sEnabled
                              | zimbraReverseProxyPassErrors
                              | zimbraReverseProxyPop3EnabledCapability
                              | zimbraReverseProxyPop3ExposeVersionOnBanner
                              | zimbraReverseProxyPop3SaslGssapiEnabled
                              | zimbraReverseProxyPop3SaslPlainEnabled
                              | zimbraReverseProxyPop3StartTlsMode
                              | zimbraReverseProxyRouteLookupTimeout
                              | zimbraReverseProxyRouteLookupTimeoutCache
                              | zimbraReverseProxySSLProtocols
                              | zimbraReverseProxySSLToUpstreamEnabled
                              | zimbraReverseProxyUpstreamConnectTimeout
                              | zimbraReverseProxyUpstreamEwsServers
                              | zimbraReverseProxyUpstreamLoginServers
                              | zimbraReverseProxyUpstreamPollingTimeout
                              | zimbraReverseProxyUpstreamReadTimeout
                              | zimbraReverseProxyUpstreamSendTimeout
                              | zimbraReverseProxyUpstreamServers
                              | zimbraReverseProxyWorkerConnections
                              | zimbraReverseProxyWorkerProcesses
                              | zimbraSSLCertificate
                              | zimbraSSLPrivateKey
                              | zimbraSaslGssapiRequiresTls
                              | zimbraScheduledTaskNumThreads
                              | zimbraServerVersion
                              | zimbraServerVersionBuild
                              | zimbraServerVersionMajor
                              | zimbraServerVersionMicro
                              | zimbraServerVersionMinor
                              | zimbraServerVersionType
                              | zimbraServiceEnabled
                              | zimbraServiceHostname
                              | zimbraServiceInstalled
                              | zimbraShareNotificationMtaAuthAccount
                              | zimbraShareNotificationMtaAuthPassword
                              | zimbraShareNotificationMtaAuthRequired
                              | zimbraShareNotificationMtaConnectionType
                              | zimbraShareNotificationMtaEnabled
                              | zimbraShareNotificationMtaHostname
                              | zimbraShareNotificationMtaPort
                              | zimbraSharingUpdatePublishInterval
                              | zimbraSmtpHostname
                              | zimbraSmtpPort
                              | zimbraSmtpSendPartial
                              | zimbraSmtpTimeout
                              | zimbraSoapExposeVersion
                              | zimbraSoapRequestMaxSize
                              | zimbraSpellAvailableDictionary
                              | zimbraSpellCheckURL
                              | zimbraSpnegoAuthPrincipal
                              | zimbraSpnegoAuthTargetName
                              | zimbraSshPublicKey
                              | zimbraStatThreadNamePrefix
                              | zimbraTableMaintenanceGrowthFactor
                              | zimbraTableMaintenanceMaxRows
                              | zimbraTableMaintenanceMinRows
                              | zimbraTableMaintenanceOperation
                              | zimbraThreadMonitorEnabled
                              | zimbraThrottleSafeHosts
                              | zimbraThrottleWhitelist
                              | zimbraUserServicesEnabled
                              | zimbraVirusDefinitionsUpdateFrequency
                              | zimbraWebClientURL
                              | zimbraWebGzipEnabled
                              | zimbraXMPPEnabled
                              | zimbraZimletJspEnabled
                              | zimbraZookeeperClientServerList }
  LDAP-NAME                 {"zimbraServer"}
  LDAP-DESC                 "Server in the cluster"
  ID                        id-oc-zimbraServer }

zimbraAlwaysOnCluster OBJECT-CLASS ::= {
  SUBCLASS OF               { top }
  MUST CONTAIN              { commonName
                              | zimbraId }
  MAY CONTAIN               { description
                              | zimbraACE
                              | zimbraCreateTimestamp
                              | zimbraMemcachedClientServerList
                              | zimbraZookeeperClientServerList }
  LDAP-NAME                 {"zimbraAlwaysOnCluster"}
  LDAP-DESC                 "AlwaysOn Cluster"
  ID                        id-oc-zimbraAlwaysOnCluster }

zimbraUCService OBJECT-CLASS ::= {
  SUBCLASS OF               { top }
  MUST CONTAIN              { commonName
                              | zimbraId
                              | zimbraUCProvider }
  MAY CONTAIN               { description
                              | zimbraACE
                              | zimbraCreateTimestamp
                              | zimbraUCCallControlURL
                              | zimbraUCPresenceSessionId
                              | zimbraUCPresenceURL
                              | zimbraUCUserURL
                              | zimbraUCVoicemailURL }
  LDAP-NAME                 {"zimbraUCService"}
  LDAP-DESC                 "Unified Communication service in the cluster"
  ID                        id-oc-zimbraUCService }

zimbraMimeEntry OBJECT-CLASS ::= {
  SUBCLASS OF               { top }
  MUST CONTAIN              { commonName
                              | zimbraMimeIndexingEnabled }
  MAY CONTAIN               { description
                              | zimbraMimeFileExtension
                              | zimbraMimeHandlerClass
                              | zimbraMimeHandlerExtension
                              | zimbraMimePriority
                              | zimbraMimeType }
  LDAP-NAME                 {"zimbraMimeEntry"}
  LDAP-DESC                 "MIME type info"
  ID                        id-oc-zimbraMimeEntry }

zimbraObjectEntry OBJECT-CLASS ::= {
  SUBCLASS OF               { top }
  MUST CONTAIN              { commonName
                              | zimbraObjectIndexingEnabled
                              | zimbraObjectStoreMatched
                              | zimbraObjectType }
  MAY CONTAIN               { description
                              | zimbraObjectHandlerClass
                              | zimbraObjectHandlerConfig }
  LDAP-NAME                 {"zimbraObjectEntry"}
  LDAP-DESC                 "Object type info"
  ID                        id-oc-zimbraObjectEntry }

zimbraTimeZone OBJECT-CLASS ::= {
  SUBCLASS OF               { top }
  MUST CONTAIN              { zimbraTimeZoneStandardDtStart
                              | zimbraTimeZoneStandardOffset }
  MAY CONTAIN               { zimbraTimeZoneDaylightDtStart
                              | zimbraTimeZoneDaylightOffset
                              | zimbraTimeZoneDaylightRRule
                              | zimbraTimeZoneStandardRRule }
  LDAP-NAME                 {"zimbraTimeZone"}
  LDAP-DESC                 "Time Zone info"
  ID                        id-oc-zimbraTimeZone }

zimbraZimletEntry OBJECT-CLASS ::= {
  SUBCLASS OF               { top }
  MUST CONTAIN              { commonName
                              | zimbraZimletEnabled
                              | zimbraZimletVersion }
  MAY CONTAIN               { description
                              | zimbraACE
                              | zimbraAdminExtDisableUIUndeploy
                              | zimbraCreateTimestamp
                              | zimbraZimletDescription
                              | zimbraZimletHandlerClass
                              | zimbraZimletHandlerConfig
                              | zimbraZimletIndexingEnabled
                              | zimbraZimletIsExtension
                              | zimbraZimletKeyword
                              | zimbraZimletPriority
                              | zimbraZimletScript
                              | zimbraZimletServerIndexRegex
                              | zimbraZimletTarget }
  LDAP-NAME                 {"zimbraZimletEntry"}
  LDAP-DESC                 "Zimlet info"
  ID                        id-oc-zimbraZimletEntry }

zimbraCalendarResource OBJECT-CLASS ::= {
  SUBCLASS OF               { top }
  KIND                      auxiliary
  MUST CONTAIN              { displayName
                              | zimbraAccountCalendarUserType
                              | zimbraCalResType
                              | zimbraId }
  MAY CONTAIN               { zimbraCalResAutoAcceptDecline
                              | zimbraCalResAutoDeclineIfBusy
                              | zimbraCalResAutoDeclineRecurring
                              | zimbraCalResBuilding
                              | zimbraCalResCapacity
                              | zimbraCalResContactEmail
                              | zimbraCalResContactName
                              | zimbraCalResContactPhone
                              | zimbraCalResFloor
                              | zimbraCalResLocationDisplayName
                              | zimbraCalResMaxNumConflictsAllowed
                              | zimbraCalResMaxPercentConflictsAllowed
                              | zimbraCalResRoom
                              | zimbraCalResSite
                              | zimbraCreateTimestamp
                              | zimbraLocale }
  LDAP-NAME                 {"zimbraCalendarResource"}
  LDAP-DESC                 "Calendar resource object"
  ID                        id-oc-zimbraCalendarResource }

zimbraIdentity OBJECT-CLASS ::= {
  SUBCLASS OF               { top }
  MUST CONTAIN              { zimbraPrefIdentityName }
  MAY CONTAIN               { zimbraCreateTimestamp
                              | zimbraPrefBccAddress
                              | zimbraPrefCalendarAcceptSignatureId
                              | zimbraPrefCalendarAutoAcceptSignatureId
                              | zimbraPrefCalendarAutoDeclineSignatureId
                              | zimbraPrefCalendarAutoDenySignatureId
                              | zimbraPrefCalendarDeclineSignatureId
                              | zimbraPrefCalendarTentativeSignatureId
                              | zimbraPrefDefaultSignatureId
                              | zimbraPrefForwardIncludeOriginalText
                              | zimbraPrefForwardReplyFormat
                              | zimbraPrefForwardReplyPrefixChar
                              | zimbraPrefForwardReplySignatureId
                              | zimbraPrefFromAddress
                              | zimbraPrefFromAddressType
                              | zimbraPrefFromDisplay
                              | zimbraPrefIdentityId
                              | zimbraPrefMailSignature
                              | zimbraPrefMailSignatureEnabled
                              | zimbraPrefMailSignatureStyle
                              | zimbraPrefReadReceiptsToAddress
                              | zimbraPrefReplyIncludeOriginalText
                              | zimbraPrefReplyToAddress
                              | zimbraPrefReplyToDisplay
                              | zimbraPrefReplyToEnabled
                              | zimbraPrefSaveToSent
                              | zimbraPrefSentMailFolder
                              | zimbraPrefUseDefaultIdentitySettings
                              | zimbraPrefWhenInFolderIds
                              | zimbraPrefWhenInFoldersEnabled
                              | zimbraPrefWhenSentToAddresses
                              | zimbraPrefWhenSentToEnabled }
  LDAP-NAME                 {"zimbraIdentity"}
  LDAP-DESC                 "Account Email Identity information"
  ID                        id-oc-zimbraIdentity }

zimbraDataSource OBJECT-CLASS ::= {
  SUBCLASS OF               { top }
  MUST CONTAIN              { zimbraDataSourceEnabled
                              | zimbraDataSourceFolderId
                              | zimbraDataSourceId
                              | zimbraDataSourceName }
  MAY CONTAIN               { zimbraCreateTimestamp
                              | zimbraDataSourceAttribute
                              | zimbraDataSourceConnectTimeout
                              | zimbraDataSourceConnectionType
                              | zimbraDataSourceDomain
                              | zimbraDataSourceEmailAddress
                              | zimbraDataSourceEnableTrace
                              | zimbraDataSourceFailingSince
                              | zimbraDataSourceHost
                              | zimbraDataSourceImportClassName
                              | zimbraDataSourceImportOnly
                              | zimbraDataSourceIsInternal
                              | zimbraDataSourceLastError
                              | zimbraDataSourceMaxTraceSize
                              | zimbraDataSourcePassword
                              | zimbraDataSourcePollingInterval
                              | zimbraDataSourcePort
                              | zimbraDataSourceReadTimeout
                              | zimbraDataSourceType
                              | zimbraDataSourceUseAddressForForwardReply
                              | zimbraDataSourceUsername
                              | zimbraPrefCalendarAcceptSignatureId
                              | zimbraPrefCalendarAutoAcceptSignatureId
                              | zimbraPrefCalendarAutoDeclineSignatureId
                              | zimbraPrefCalendarAutoDenySignatureId
                              | zimbraPrefCalendarDeclineSignatureId
                              | zimbraPrefCalendarTentativeSignatureId
                              | zimbraPrefDefaultSignatureId
                              | zimbraPrefForwardReplySignatureId
                              | zimbraPrefFromAddress
                              | zimbraPrefFromDisplay
                              | zimbraPrefReadReceiptsToAddress
                              | zimbraPrefReplyToAddress
                              | zimbraPrefReplyToDisplay }
  LDAP-NAME                 {"zimbraDataSource"}
  LDAP-DESC                 "base class for data source objects"
  ID                        id-oc-zimbraDataSource }

zimbraPop3DataSource OBJECT-CLASS ::= {
  SUBCLASS OF               { zimbraDataSource }
  MUST CONTAIN              { zimbraDataSourceConnectionType
                              | zimbraDataSourceHost
                              | zimbraDataSourcePort }
  MAY CONTAIN               { zimbraDataSourceLeaveOnServer }
  LDAP-NAME                 {"zimbraPop3DataSource"}
  LDAP-DESC                 "POP3 data source object"
  ID                        id-oc-zimbraPop3DataSource }

zimbraImapDataSource OBJECT-CLASS ::= {
  SUBCLASS OF               { zimbraDataSource }
  MUST CONTAIN              { zimbraDataSourceConnectionType
                              | zimbraDataSourceHost
                              | zimbraDataSourcePort }
  MAY CONTAIN               { zimbraDataSourceAuthMechanism
                              | zimbraDataSourceAuthorizationId }
  LDAP-NAME                 {"zimbraImapDataSource"}
  LDAP-DESC                 "IMAP data source object"
  ID                        id-oc-zimbraImapDataSource }

zimbraRssDataSource OBJECT-CLASS ::= {
  SUBCLASS OF               { zimbraDataSource }
  LDAP-NAME                 {"zimbraRssDataSource"}
  LDAP-DESC                 "RSS data source object"
  ID                        id-oc-zimbraRssDataSource }

zimbraLiveDataSource OBJECT-CLASS ::= {
  SUBCLASS OF               { zimbraDataSource }
  LDAP-NAME                 {"zimbraLiveDataSource"}
  LDAP-DESC                 "Hotmail data source object"
  ID                        id-oc-zimbraLiveDataSource }

zimbraGalDataSource OBJECT-CLASS ::= {
  SUBCLASS OF               { zimbraDataSource }
  MUST CONTAIN              { zimbraGalStatus
                              | zimbraGalType }
  MAY CONTAIN               { zimbraGalLastFailedSyncTimestamp
                              | zimbraGalLastSuccessfulSyncTimestamp
                              | zimbraGalLdapAttrMap
                              | zimbraGalLdapGroupHandlerClass
                              | zimbraGalLdapValueMap
                              | zimbraGalSyncIgnoredAttributes
                              | zimbraGalSyncLdapAuthMech
                              | zimbraGalSyncLdapBindDn
                              | zimbraGalSyncLdapBindPassword
                              | zimbraGalSyncLdapFilter
                              | zimbraGalSyncLdapKerberos5Keytab
                              | zimbraGalSyncLdapKerberos5Principal
                              | zimbraGalSyncLdapPageSize
                              | zimbraGalSyncLdapSearchBase
                              | zimbraGalSyncLdapStartTlsEnabled
                              | zimbraGalSyncLdapURL
                              | zimbraGalSyncTimestampFormat }
  LDAP-NAME                 {"zimbraGalDataSource"}
  LDAP-DESC                 "GAL data source object"
  ID                        id-oc-zimbraGalDataSource }

zimbraSignature OBJECT-CLASS ::= {
  SUBCLASS OF               { top }
  MUST CONTAIN              { zimbraSignatureId
                              | zimbraSignatureName }
  MAY CONTAIN               { zimbraCreateTimestamp
                              | zimbraPrefMailSignature
                              | zimbraPrefMailSignatureContactId
                              | zimbraPrefMailSignatureHTML }
  LDAP-NAME                 {"zimbraSignature"}
  LDAP-DESC                 "Account Email Signature information"
  ID                        id-oc-zimbraSignature }

zimbraXMPPComponent OBJECT-CLASS ::= {
  SUBCLASS OF               { top }
  MUST CONTAIN              { commonName
                              | zimbraDomainId
                              | zimbraId
                              | zimbraServerId
                              | zimbraXMPPComponentCategory
                              | zimbraXMPPComponentClassName
                              | zimbraXMPPComponentType }
  MAY CONTAIN               { description
                              | zimbraACE
                              | zimbraCreateTimestamp
                              | zimbraXMPPComponentFeatures
                              | zimbraXMPPComponentName }
  LDAP-NAME                 {"zimbraXMPPComponent"}
  LDAP-DESC                 "XMPP Component Configuration Record"
  ID                        id-oc-zimbraXMPPComponent }

zimbraAclTarget OBJECT-CLASS ::= {
  SUBCLASS OF               { top }
  MUST CONTAIN              { commonName }
  MAY CONTAIN               { description
                              | zimbraACE }
  LDAP-NAME                 {"zimbraAclTarget"}
  LDAP-DESC                 "acl target"
  ID                        id-oc-zimbraAclTarget }

zimbraGroup OBJECT-CLASS ::= {
  SUBCLASS OF               { top }
  KIND                      auxiliary
  MUST CONTAIN              { memberURL
                              | zimbraId
                              | zimbraIsACLGroup }
  MAY CONTAIN               { description
                              | displayName
                              | mail
                              | zimbraACE
                              | zimbraAdminConsoleUIComponents
                              | zimbraCreateTimestamp
                              | zimbraDistributionListSubscriptionPolicy
                              | zimbraDistributionListUnsubscriptionPolicy
                              | zimbraHideInGal
                              | zimbraIsAdminGroup
                              | zimbraLocale
                              | zimbraMailAlias
                              | zimbraMailHost
                              | zimbraMailStatus
                              | zimbraNotes
                              | zimbraPrefAllowAddressForDelegatedSender
                              | zimbraPrefReplyToAddress
                              | zimbraPrefReplyToDisplay
                              | zimbraPrefReplyToEnabled }
  LDAP-NAME                 {"zimbraGroup"}
  LDAP-DESC                 "hold attributes for dynamic groups"
  ID                        id-oc-zimbraGroup }

zimbraGroupDynamicUnit OBJECT-CLASS ::= {
  SUBCLASS OF               { top }
  KIND                      auxiliary
  MUST CONTAIN              { memberURL
                              | zimbraGroupId
                              | zimbraId }
  MAY CONTAIN               { description
                              | displayName
                              | mail
                              | zimbraCreateTimestamp
                              | zimbraMailAlias
                              | zimbraMailStatus }
  LDAP-NAME                 {"zimbraGroupDynamicUnit"}
  LDAP-DESC                 "hold attributes for the dynamic entry of dynamic groups."
  ID                        id-oc-zimbraGroupDynamicUnit }

zimbraGroupStaticUnit OBJECT-CLASS ::= {
  SUBCLASS OF               { top }
  MUST CONTAIN              { commonName
                              | zimbraGroupId
                              | zimbraId }
  MAY CONTAIN               { description
                              | zimbraCreateTimestamp
                              | zimbraMailForwardingAddress }
  LDAP-NAME                 {"zimbraGroupStaticUnit"}
  LDAP-DESC                 "hold attributes for the static entry of dynamic groups."
  ID                        id-oc-zimbraGroupStaticUnit }

zimbraShareLocator OBJECT-CLASS ::= {
  SUBCLASS OF               { top }
  MUST CONTAIN              { commonName
                              | zimbraShareOwnerAccountId }
  LDAP-NAME                 {"zimbraShareLocator"}
  LDAP-DESC                 "Share locator"
  ID                        id-oc-zimbraShareLocator }
END
