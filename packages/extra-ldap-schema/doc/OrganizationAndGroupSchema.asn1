OrganizationAndGroupSchema {
    iso(1) identified-organization(3) dod(6) internet(1) private(4)
    enterprise(1) wildboar(56490) module(1) org-group-schema(166)
}
DEFINITIONS ::= BEGIN

EXPORTS ALL;

IMPORTS

    id-at, id-nf, id-oc, id-vetreq
        FROM Wildboar
        {iso(1) identified-organization(3) dod(6) internet(1) private(4)
        enterprise(1) wildboar(56490) module(1) wildboar(1)}
        WITH SUCCESSORS

    ATTRIBUTE, OBJECT-CLASS, NAME-FORM, objectIdentifierMatch, top
        FROM InformationFramework
        {joint-iso-itu-t ds(5) module(1) informationFramework(1) 9}
        WITH SUCCESSORS

    UnboundedDirectoryString, directoryString, caseIgnoreMatch,
    caseIgnoreOrderingMatch, caseIgnoreSubstringsMatch, integer, integerMatch,
    integerOrderingMatch, boolean, booleanMatch, dn, oid, octetString, member,
    uniqueMember, organizationIdentifier, owner, CountryName, countryString,
    distinguishedName, dnsName
        FROM SelectedAttributeTypes
        {joint-iso-itu-t ds(5) module(1) selectedAttributeTypes(5) 9}
        WITH SUCCESSORS

    organization, organizationalUnit, organizationalRole, groupOfNames,
    groupOfUniqueNames, orgNameForm, orgRoleNameForm, gONNameForm,
    orgUnitNameForm
        FROM SelectedObjectClasses
        {joint-iso-itu-t ds(5) module(1) selectedObjectClasses(6) 9}
        WITH SUCCESSORS

    BusinessCategoryTypes
        FROM BusinessCategorySubtypes
        {iso(1) identified-organization(3) dod(6) internet(1) private(4)
        enterprise(1) wildboar(56490) module(1) biz-cat-subtypes(85)}
        WITH SUCCESSORS

    OrganizationIdentifierTypes
        FROM OrganizationIdentifierSubtypes
        {iso(1) identified-organization(3) dod(6) internet(1) private(4)
        enterprise(1) wildboar(56490) module(1) org-id-subtypes(87)}
        WITH SUCCESSORS

    BillingPostalAttributeSet, HeadquartersPostalAttributeSet,
    MailingPostalAttributeSet, PrincipalPostalAttributeSet
        FROM PostalSubtypes
        {iso(1) identified-organization(3) dod(6) internet(1) private(4)
        enterprise(1) wildboar(56490) module(1) postal-subtypes(80)}
        WITH SUCCESSORS

    OrganizationalPhoneAttributeSet, OrganizationalFaxAttributeSet
        FROM TelephoneSubtypes
        {iso(1) identified-organization(3) dod(6) internet(1) private(4)
        enterprise(1) wildboar(56490) module(1) telephone-subtypes(81)}
        WITH SUCCESSORS

    OrganizationalEmailAttributeSet
        FROM EmailSubtypes
        {iso(1) identified-organization(3) dod(6) internet(1) private(4)
        enterprise(1) wildboar(56490) module(1) email-subtypes(79)}
        WITH SUCCESSORS

    OrganizationalUrls
        FROM UrlSubtypes
        {iso(1) identified-organization(3) dod(6) internet(1) private(4)
        enterprise(1) wildboar(56490) module(1) url-subtypes(89)}
        WITH SUCCESSORS

    OrganizationalDescriptionAttributes
        FROM DescriptionSubtypes
        {iso(1) identified-organization(3) dod(6) internet(1) private(4)
        enterprise(1) wildboar(56490) module(1) description-subtypes(99)}
        WITH SUCCESSORS

    ThemeColorAttributes
        FROM ThemeColorSchema
        {iso(1) identified-organization(3) dod(6) internet(1) private(4)
        enterprise(1) wildboar(56490) module(1) theme-color-schema(162)}

    timeToLiveDuration
        FROM ProtocolSchema
        {iso(1) identified-organization(3) dod(6) internet(1) private(4)
        enterprise(1) wildboar(56490) module(1) protocol-schema(116)}

    DrugTestPanels
        FROM DrugTestingSchema
        {iso(1) identified-organization(3) dod(6) internet(1) private(4)
        enterprise(1) wildboar(56490) module(1) drug-testing-schema(163)}

    Religions
        FROM ReligiousSchema
        {iso(1) identified-organization(3) dod(6) internet(1) private(4)
        enterprise(1) wildboar(56490) module(1) religious-schema(164)}

    Continent, UnitedNationsContinentalSubregion
        FROM RacialSchema
        {iso(1) identified-organization(3) dod(6) internet(1) private(4)
        enterprise(1) wildboar(56490) module(1) racial-schema(106)}

    requiredVaccinationAgainst
        FROM VaccinationSchema
        {iso(1) identified-organization(3) dod(6) internet(1) private(4)
        enterprise(1) wildboar(56490) module(1) vax-schema(177)}

    associatedDomain
        FROM Cosine
        {iso(1) identified-organization(3) dod(6) internet(1) private(4)
        enterprise(1) wildboar(56490) module(1) cosine(3)}

    FundingAttributes
        FROM FundingSchema
        {iso(1) identified-organization(3) dod(6) internet(1) private(4)
        enterprise(1) wildboar(56490) module(1) funding-schema(141)}

    BasicBalanceSheetAttributes, BasicIncomeStatementAttributes,
    FinanceAttributes, AccountingAttributes
        FROM MicroeconomicSchema
        {iso(1) identified-organization(3) dod(6) internet(1) private(4)
        enterprise(1) wildboar(56490) module(1) microecon-schema(104)}

    PositiveComplianceAttributes
        FROM ComplianceSchema
        {iso(1) identified-organization(3) dod(6) internet(1) private(4)
        enterprise(1) wildboar(56490) module(1) compliance-schema(139)}

    CreationAttributes
        FROM CreationSchema
        {iso(1) identified-organization(3) dod(6) internet(1) private(4)
        enterprise(1) wildboar(56490) module(1) creation-schema(153)}

    VerbalContentAttributes
        FROM LanguageSchema
        {iso(1) identified-organization(3) dod(6) internet(1) private(4)
        enterprise(1) wildboar(56490) module(1) language-schema(100)}

    TaxpayerAttributes
        FROM TaxationSchema
        {iso(1) identified-organization(3) dod(6) internet(1) private(4)
        enterprise(1) wildboar(56490) module(1) taxation-schema(161)}

    category, rules, keyword
        FROM Useful-Schema
        {iso(1) identified-organization(3) dod(6) internet(1) private(4)
        enterprise(1) wildboar(56490) module(1) useful-schema(20)}

    stakeholderDN, beneficiaryDN
        FROM PrincipalAgentSchema
        {iso(1) identified-organization(3) dod(6) internet(1) private(4)
        enterprise(1) wildboar(56490) module(1) principal-agent-schema(137)}

    real, realMatch, realOrderingMatch, BoundedPercentage
        FROM RealTypeSchema
        {iso(1) identified-organization(3) dod(6) internet(1) private(4)
        enterprise(1) wildboar(56490) module(1) real-type-schema(98)}
        WITH SUCCESSORS

    Currency, currencySyntax, currencyMatch, currencyOrderingMatch
        FROM CurrencySchema
        {iso(1) identified-organization(3) dod(6) internet(1) private(4)
        enterprise(1) wildboar(56490) module(1) currency-schema(105)}
        WITH SUCCESSORS

    ;

-- Object Identifiers

id-at-membersCount                          OBJECT IDENTIFIER ::= { id-at 2624 }
id-at-activeMembersCount                    OBJECT IDENTIFIER ::= { id-at 2625 }
id-at-dormantMembersCount                   OBJECT IDENTIFIER ::= { id-at 2626 }
id-at-formerMembersCount                    OBJECT IDENTIFIER ::= { id-at 2627 }
id-at-minAgeToJoin                          OBJECT IDENTIFIER ::= { id-at 2628 }
id-at-maxAgeToJoin                          OBJECT IDENTIFIER ::= { id-at 2629 }
id-at-membershipTerm                        OBJECT IDENTIFIER ::= { id-at 2630 }
id-at-memberNoun                            OBJECT IDENTIFIER ::= { id-at 2631 }
id-at-memberSingularNoun                    OBJECT IDENTIFIER ::= { id-at 2632 }
id-at-memberPluralNoun                      OBJECT IDENTIFIER ::= { id-at 2633 }
id-at-memberSlangNoun                       OBJECT IDENTIFIER ::= { id-at 2634 }
id-at-vettingProcedureDescription           OBJECT IDENTIFIER ::= { id-at 2635 }
id-at-onboardingProcedureDescription        OBJECT IDENTIFIER ::= { id-at 2636 }
id-at-offboardingProcedureDescription       OBJECT IDENTIFIER ::= { id-at 2637 }
id-at-renewalProcedureDescription           OBJECT IDENTIFIER ::= { id-at 2638 }
id-at-healthRequirementsDescription         OBJECT IDENTIFIER ::= { id-at 2639 }
id-at-membershipOath                        OBJECT IDENTIFIER ::= { id-at 2640 }
id-at-bylawsText                            OBJECT IDENTIFIER ::= { id-at 2641 }
id-at-allowsMen                             OBJECT IDENTIFIER ::= { id-at 2642 }
id-at-allowsWomen                           OBJECT IDENTIFIER ::= { id-at 2643 }
id-at-allowsHeterosexuals                   OBJECT IDENTIFIER ::= { id-at 2644 }
id-at-allowsAltSexuals                      OBJECT IDENTIFIER ::= { id-at 2645 }
id-at-allowsForeigners                      OBJECT IDENTIFIER ::= { id-at 2646 }
id-at-hasDrugTestingRequirement             OBJECT IDENTIFIER ::= { id-at 2647 }
id-at-hasNonDisclosureRequirement           OBJECT IDENTIFIER ::= { id-at 2648 }
id-at-membershipIsSecret                    OBJECT IDENTIFIER ::= { id-at 2649 }
id-at-ownMembershipIsSecret                 OBJECT IDENTIFIER ::= { id-at 2650 }
id-at-drugTestRequired                      OBJECT IDENTIFIER ::= { id-at 2651 }
id-at-requiresReligion                      OBJECT IDENTIFIER ::= { id-at 2652 }
id-at-forbidsReligion                       OBJECT IDENTIFIER ::= { id-at 2653 }
id-at-requiredCountryRace                   OBJECT IDENTIFIER ::= { id-at 2654 }
id-at-requiredContinentalRace               OBJECT IDENTIFIER ::= { id-at 2655 }
id-at-requiredRegionalRace                  OBJECT IDENTIFIER ::= { id-at 2656 }
id-at-forbiddenCountryRace                  OBJECT IDENTIFIER ::= { id-at 2657 }
id-at-forbiddenContinentalRace              OBJECT IDENTIFIER ::= { id-at 2658 }
id-at-forbiddenRegionalRace                 OBJECT IDENTIFIER ::= { id-at 2659 }
id-at-forbidsMembershipWithDN               OBJECT IDENTIFIER ::= { id-at 2660 }
id-at-leaderDN                              OBJECT IDENTIFIER ::= { id-at 2661 }
id-at-presidentDN                           OBJECT IDENTIFIER ::= { id-at 2662 }
id-at-vicePresidentDN                       OBJECT IDENTIFIER ::= { id-at 2663 }
id-at-treasurerDN                           OBJECT IDENTIFIER ::= { id-at 2664 }
id-at-secretaryDN                           OBJECT IDENTIFIER ::= { id-at 2665 }
id-at-historianDN                           OBJECT IDENTIFIER ::= { id-at 2666 }
id-at-bylawsUrl                             OBJECT IDENTIFIER ::= { id-at 2667 }
-- id-at-symbolUrl                             OBJECT IDENTIFIER ::= { id-at 2668 } (Moved to UrlSubtypes)
-- id-at-faviconUrl                            OBJECT IDENTIFIER ::= { id-at 2669 } (Moved to UrlSubtypes)
id-at-bannerImageUrl                        OBJECT IDENTIFIER ::= { id-at 2670 }
id-at-symbolDescription                     OBJECT IDENTIFIER ::= { id-at 2671 }
id-at-anthemName                            OBJECT IDENTIFIER ::= { id-at 2672 }
id-at-taxIdentifier                         OBJECT IDENTIFIER ::= { id-at 2673 }
id-at-ideologicalRequirementsDescription    OBJECT IDENTIFIER ::= { id-at 2674 }
id-at-faviconPNG                            OBJECT IDENTIFIER ::= { id-at 2675 }
id-at-publicMemberDN                        OBJECT IDENTIFIER ::= { id-at 2676 }
id-at-privateMemberDN                       OBJECT IDENTIFIER ::= { id-at 2677 }
id-at-publicUniqueMember                    OBJECT IDENTIFIER ::= { id-at 2678 }
id-at-privateUniqueMember                   OBJECT IDENTIFIER ::= { id-at 2679 }
id-at-memberOf                              OBJECT IDENTIFIER ::= { id-at 2680 }
id-at-publicMemberOf                        OBJECT IDENTIFIER ::= { id-at 2681 }
id-at-privateMemberOf                       OBJECT IDENTIFIER ::= { id-at 2682 }
id-at-eligibilityFilter                     OBJECT IDENTIFIER ::= { id-at 2683 }
id-at-eligibilityNoSubtypesFilter           OBJECT IDENTIFIER ::= { id-at 2684 }
id-at-topDonorDN                            OBJECT IDENTIFIER ::= { id-at 2685 }
id-at-directorDN                            OBJECT IDENTIFIER ::= { id-at 2686 }
id-at-chiefExecutiveOfficerDN               OBJECT IDENTIFIER ::= { id-at 2687 }
id-at-chiefFinancialOfficerDN               OBJECT IDENTIFIER ::= { id-at 2688 }
id-at-chiefOperationsOfficerDN              OBJECT IDENTIFIER ::= { id-at 2689 }
id-at-chiefInformationOfficerDN             OBJECT IDENTIFIER ::= { id-at 2690 }
id-at-chiefTechnologyOfficerDN              OBJECT IDENTIFIER ::= { id-at 2691 }
id-at-chiefMarketingOfficerDN               OBJECT IDENTIFIER ::= { id-at 2692 }
id-at-chiefHumanResourcesOfficerDN          OBJECT IDENTIFIER ::= { id-at 2693 }
id-at-chiefInformationSecurityOfficerDN     OBJECT IDENTIFIER ::= { id-at 2694 }
id-at-chiefLegalOfficerDN                   OBJECT IDENTIFIER ::= { id-at 2695 }
id-at-chiefDiversityOfficerDN               OBJECT IDENTIFIER ::= { id-at 2696 }
id-at-affiliateDN                           OBJECT IDENTIFIER ::= { id-at 2697 }
id-at-subsidiaryDN                          OBJECT IDENTIFIER ::= { id-at 2698 }
id-at-parentOrganizationDN                  OBJECT IDENTIFIER ::= { id-at 2699 }
id-at-mergedWithDN                          OBJECT IDENTIFIER ::= { id-at 2700 }
id-at-acquiredDN                            OBJECT IDENTIFIER ::= { id-at 2701 }
id-at-acquiredByDN                          OBJECT IDENTIFIER ::= { id-at 2702 }
id-at-contributorDN                         OBJECT IDENTIFIER ::= { id-at 2703 }
id-at-topContributorDN                      OBJECT IDENTIFIER ::= { id-at 2704 }
id-at-shellCorporationDN                    OBJECT IDENTIFIER ::= { id-at 2705 }
id-at-frontOrganizationDN                   OBJECT IDENTIFIER ::= { id-at 2706 }
-- WARNING: Discontinuity in OID numbering
id-at-missionStatement                      OBJECT IDENTIFIER ::= { id-at 7389 }
id-at-applicantsCount                       OBJECT IDENTIFIER ::= { id-at 7390 }
id-at-applicantsCountTTM                    OBJECT IDENTIFIER ::= { id-at 7391 }
id-at-malePopulationPercentage              OBJECT IDENTIFIER ::= { id-at 7392 }
id-at-admissionRate                         OBJECT IDENTIFIER ::= { id-at 7393 }
id-at-admissionRateForMales                 OBJECT IDENTIFIER ::= { id-at 7394 }
id-at-admissionRateForFemales               OBJECT IDENTIFIER ::= { id-at 7395 }
id-at-admissionRateForCollegeEducated       OBJECT IDENTIFIER ::= { id-at 7396 }
id-at-admissionRateForMarried               OBJECT IDENTIFIER ::= { id-at 7397 }
id-at-admissionRateForNonCollegeEduca       OBJECT IDENTIFIER ::= { id-at 7398 }
id-at-admissionRateForNonMarried            OBJECT IDENTIFIER ::= { id-at 7399 }
id-at-collegeEducatedMembersPercentag       OBJECT IDENTIFIER ::= { id-at 7400 }
id-at-marriedMembersPercentage              OBJECT IDENTIFIER ::= { id-at 7401 }
id-at-admissionConsiderationAttribute       OBJECT IDENTIFIER ::= { id-at 7402 }
id-at-admissionNonConsiderationAttrib       OBJECT IDENTIFIER ::= { id-at 7403 }
id-at-applicationFee                        OBJECT IDENTIFIER ::= { id-at 7404 }
id-at-meanSalary                            OBJECT IDENTIFIER ::= { id-at 7405 }
id-at-medianSalary                          OBJECT IDENTIFIER ::= { id-at 7406 }
id-at-highestSalary                         OBJECT IDENTIFIER ::= { id-at 7407 }
id-at-lowestSalary                          OBJECT IDENTIFIER ::= { id-at 7408 }
id-at-meanMemberAge                         OBJECT IDENTIFIER ::= { id-at 7409 }
id-at-medianMemberAge                       OBJECT IDENTIFIER ::= { id-at 7410 }
id-at-highestMemberAge                      OBJECT IDENTIFIER ::= { id-at 7411 }
id-at-lowestMemberAge                       OBJECT IDENTIFIER ::= { id-at 7412 }
id-at-donorDN                               OBJECT IDENTIFIER ::= { id-at 7413 }
id-at-vettingRequirements                   OBJECT IDENTIFIER ::= { id-at 7414 }

id-oc-organizationExt                       OBJECT IDENTIFIER ::= { id-oc 368 }
id-oc-organizationalRoleExt                 OBJECT IDENTIFIER ::= { id-oc 369 }
id-oc-groupOfNamesExt                       OBJECT IDENTIFIER ::= { id-oc 370 }
id-oc-groupOfUniqueNamesExt                 OBJECT IDENTIFIER ::= { id-oc 371 }
id-oc-organizationalUnitExt                 OBJECT IDENTIFIER ::= { id-oc 372 }
-- WARNING: Discontinuity in OID numbering
id-oc-boardOfDirectors		                OBJECT IDENTIFIER ::= { id-oc  }
id-oc-vorstand		                        OBJECT IDENTIFIER ::= { id-oc  }
id-oc-committee		                        OBJECT IDENTIFIER ::= { id-oc  }
id-oc-caucus		                        OBJECT IDENTIFIER ::= { id-oc  }

-- Vetting Requirements
id-vetreq-backgroundCheck                   OBJECT IDENTIFIER ::= { id-vetreq 1 }
id-vetreq-creditCheck                       OBJECT IDENTIFIER ::= { id-vetreq 2 }
id-vetreq-criminalHistoryCheck              OBJECT IDENTIFIER ::= { id-vetreq 3 }
id-vetreq-employmentHistoryCheck            OBJECT IDENTIFIER ::= { id-vetreq 4 }
id-vetreq-drugTest                          OBJECT IDENTIFIER ::= { id-vetreq 5 }
id-vetreq-medicalRecordsCheck               OBJECT IDENTIFIER ::= { id-vetreq 6 }
id-vetreq-familyBackgroundCheck             OBJECT IDENTIFIER ::= { id-vetreq 7 }
id-vetreq-letterOfRecommendation            OBJECT IDENTIFIER ::= { id-vetreq 8 }
id-vetreq-intelligenceTest                  OBJECT IDENTIFIER ::= { id-vetreq 9 }
id-vetreq-medicalInspection                 OBJECT IDENTIFIER ::= { id-vetreq 10 }
id-vetreq-physicalFitness                   OBJECT IDENTIFIER ::= { id-vetreq 11 }
id-vetreq-residentialHistoryCheck           OBJECT IDENTIFIER ::= { id-vetreq 12 }
id-vetreq-relationshipHistoryCheck          OBJECT IDENTIFIER ::= { id-vetreq 13 }
id-vetreq-oath                              OBJECT IDENTIFIER ::= { id-vetreq 14 }
id-vetreq-nonDisclsoureAgreement            OBJECT IDENTIFIER ::= { id-vetreq 15 }
id-vetreq-polygraph                         OBJECT IDENTIFIER ::= { id-vetreq 16 }
id-vetreq-demonstrativeAct                  OBJECT IDENTIFIER ::= { id-vetreq 17 } -- Donating to a like-minded non-profit for instance.
id-vetreq-incomeVerification                OBJECT IDENTIFIER ::= { id-vetreq 18 }
id-vetreq-academicHistoryCheck              OBJECT IDENTIFIER ::= { id-vetreq 19 }

-- Value Sets

VettingRequirements OBJECT IDENTIFIER ::= {
    id-vetreq-backgroundCheck
    | id-vetreq-creditCheck
    | id-vetreq-criminalHistoryCheck
    | id-vetreq-employmentHistoryCheck
    | id-vetreq-drugTest
    | id-vetreq-medicalRecordsCheck
    | id-vetreq-familyBackgroundCheck
    | id-vetreq-letterOfRecommendation
    | id-vetreq-intelligenceTest
    | id-vetreq-medicalInspection
    | id-vetreq-physicalFitness
    | id-vetreq-residentialHistoryCheck
    | id-vetreq-relationshipHistoryCheck
    | id-vetreq-oath
    | id-vetreq-nonDisclsoureAgreement
    | id-vetreq-polygraph
    | id-vetreq-demonstrativeAct
    | id-vetreq-incomeVerification
    | id-vetreq-academicHistoryCheck,
    ...
}

-- Attribute Types

membersCount ATTRIBUTE ::= {
    WITH SYNTAX				    INTEGER (0..MAX)
    EQUALITY MATCHING RULE	    integerMatch
    ORDERING MATCHING RULE	    integerOrderingMatch
    LDAP-SYNTAX				    integer.&id
    LDAP-NAME				    {"membersCount"}
    LDAP-DESC				    "The number of members in a group, organization, unit, team, etc."
    ID						    id-at-membersCount
}

activeMembersCount ATTRIBUTE ::= {
    SUBTYPE OF                  membersCount
    LDAP-SYNTAX				    integer.&id
    LDAP-NAME				    {"activeMembersCount"}
    LDAP-DESC				    "The active number of members, in contrast to dormant, reserve, retired, etc. members"
    ID						    id-at-activeMembersCount
}

dormantMembersCount ATTRIBUTE ::= {
    SUBTYPE OF                  membersCount
    LDAP-SYNTAX				    integer.&id
    LDAP-NAME				    {"dormantMembersCount"}
    LDAP-DESC				    "The number of members that have memberships that have lapsed, but which did not formally leave"
    ID						    id-at-dormantMembersCount
}

formerMembersCount ATTRIBUTE ::= {
    SUBTYPE OF                  membersCount
    LDAP-SYNTAX				    integer.&id
    LDAP-NAME				    {"formerMembersCount"}
    LDAP-DESC				    "The number of former members of a group, organization, unit, team, etc."
    ID						    id-at-formerMembersCount
}

minAgeToJoin ATTRIBUTE ::= {
    WITH SYNTAX				    INTEGER (0..MAX)
    EQUALITY MATCHING RULE	    integerMatch
    ORDERING MATCHING RULE	    integerOrderingMatch
    LDAP-SYNTAX				    integer.&id
    LDAP-NAME				    {"minAgeToJoin"}
    LDAP-DESC				    "The minimum age (inclusively) required to be a member of a group, organization, unit, team, etc."
    ID						    id-at-minAgeToJoin
}

maxAgeToJoin ATTRIBUTE ::= {
    WITH SYNTAX				    INTEGER (0..MAX)
    EQUALITY MATCHING RULE      integerMatch
    ORDERING MATCHING RULE      integerOrderingMatch
    LDAP-SYNTAX				    integer.&id
    LDAP-NAME				    {"maxAgeToJoin"}
    LDAP-DESC				    "The maximum age (inclusively) allowed to be a member of a group, organization, unit, team, etc."
    ID						    id-at-maxAgeToJoin
}

membershipTerm ATTRIBUTE ::= {
    WITH SYNTAX				    UnboundedDirectoryString
    EQUALITY MATCHING RULE	    caseIgnoreMatch
    ORDERING MATCHING RULE	    caseIgnoreOrderingMatch
    SUBSTRINGS MATCHING RULE    caseIgnoreSubstringsMatch
    LDAP-SYNTAX				    directoryString.&id
    LDAP-NAME				    {"membershipTerm"}
    LDAP-DESC				    "The term used to describe membership, such as 'Brotherhood', 'Goobership', etc."
    ID						    id-at-membershipTerm
}

memberNoun ATTRIBUTE ::= {
    WITH SYNTAX				    UnboundedDirectoryString
    EQUALITY MATCHING RULE	    caseIgnoreMatch
    ORDERING MATCHING RULE	    caseIgnoreOrderingMatch
    SUBSTRINGS MATCHING RULE    caseIgnoreSubstringsMatch
    LDAP-SYNTAX				    directoryString.&id
    LDAP-NAME				    {"memberNoun"}
    LDAP-DESC				    "Term used to describe a member of a group, such as 'Wombat', 'Sister', 'Viking', etc."
    ID						    id-at-memberNoun
}

memberSingularNoun ATTRIBUTE ::= {
    SUBTYPE OF                  memberNoun
    LDAP-SYNTAX			        directoryString.&id
    LDAP-NAME			        {"memberSingularNoun"}
    LDAP-DESC			        "Singular noun used as a term for a member of this group, such as 'Goober'"
    ID					        id-at-memberSingularNoun
}

memberPluralNoun ATTRIBUTE ::= {
    SUBTYPE OF                  memberNoun
    LDAP-SYNTAX				    directoryString.&id
    LDAP-NAME				    {"memberPluralNoun"}
    LDAP-DESC				    "Plural noun used as a term for members of this group, such as 'Goobers'"
    ID						    id-at-memberPluralNoun
}

memberSlangNoun ATTRIBUTE ::= {
    SUBTYPE OF                  memberNoun
    LDAP-SYNTAX				    directoryString.&id
    LDAP-NAME				    {"memberSlangNoun"}
    LDAP-DESC				    "A slang term used for members of this group, such as 'Goobs'"
    ID						    id-at-memberSlangNoun
}

vettingProcedureDescription ATTRIBUTE ::= {
    WITH SYNTAX				    UnboundedDirectoryString
    SUBSTRINGS MATCHING RULE    caseIgnoreSubstringsMatch
    LDAP-SYNTAX				    directoryString.&id
    LDAP-NAME				    {"vettingProcedureDescription"}
    LDAP-DESC				    "A description of the vetting procedures for obtaining membership in a group"
    ID						    id-at-vettingProcedureDescription
}

onboardingProcedureDescription ATTRIBUTE ::= {
    WITH SYNTAX				    UnboundedDirectoryString
    SUBSTRINGS MATCHING RULE    caseIgnoreSubstringsMatch
    LDAP-SYNTAX				    directoryString.&id
    LDAP-NAME				    {"onboardingProcedureDescription"}
    LDAP-DESC				    "A description of the onboarding procedures for becoming a member of a group"
    ID						    id-at-onboardingProcedureDescription
}

offboardingProcedureDescription ATTRIBUTE ::= {
    WITH SYNTAX				    UnboundedDirectoryString
    SUBSTRINGS MATCHING RULE    caseIgnoreSubstringsMatch
    LDAP-SYNTAX				    directoryString.&id
    LDAP-NAME				    {"offboardingProcedureDescription"}
    LDAP-DESC				    "A description of the offboarding procedures for members leaving a group"
    ID						    id-at-offboardingProcedureDescription
}

renewalProcedureDescription ATTRIBUTE ::= {
    WITH SYNTAX				    UnboundedDirectoryString
    SUBSTRINGS MATCHING RULE    caseIgnoreSubstringsMatch
    LDAP-SYNTAX				    directoryString.&id
    LDAP-NAME				    {"renewalProcedureDescription"}
    LDAP-DESC				    "A description of the procedures for renewing membership in a group"
    ID						    id-at-renewalProcedureDescription
}

healthRequirementsDescription ATTRIBUTE ::= {
    WITH SYNTAX				    UnboundedDirectoryString
    SUBSTRINGS MATCHING RULE    caseIgnoreSubstringsMatch
    LDAP-SYNTAX				    directoryString.&id
    LDAP-NAME				    {"healthRequirementsDescription"}
    LDAP-DESC				    "A description of health requirements for membership in a group"
    ID						    id-at-healthRequirementsDescription
}

membershipOath ATTRIBUTE ::= {
    WITH SYNTAX				    UnboundedDirectoryString
    SUBSTRINGS MATCHING RULE    caseIgnoreSubstringsMatch
    LDAP-SYNTAX				    directoryString.&id
    LDAP-NAME				    {"membershipOath"}
    LDAP-DESC				    "The oath required of members to join a group"
    ID						    id-at-membershipOath
}

bylawsText ATTRIBUTE ::= {
    WITH SYNTAX				    UnboundedDirectoryString
    SUBSTRINGS MATCHING RULE    caseIgnoreSubstringsMatch
    LDAP-SYNTAX				    directoryString.&id
    LDAP-NAME				    {"bylawsText"}
    LDAP-DESC				    "The text of the bylaws of a group, organization, unit, team, etc"
    ID						    id-at-bylawsText
}

allowsMen ATTRIBUTE ::= {
    WITH SYNTAX				    BOOLEAN
    EQUALITY MATCHING RULE	    booleanMatch
    LDAP-SYNTAX				    boolean.&id
    LDAP-NAME				    {"allowsMen"}
    LDAP-DESC				    "Whether a group / organization allows men to join"
    ID						    id-at-allowsMen
}

allowsWomen ATTRIBUTE ::= {
    WITH SYNTAX				    BOOLEAN
    EQUALITY MATCHING RULE	    booleanMatch
    LDAP-SYNTAX				    boolean.&id
    LDAP-NAME				    {"allowsWomen"}
    LDAP-DESC				    "Whether a group / organization allows women to join"
    ID						    id-at-allowsWomen
}

allowsHeterosexuals ATTRIBUTE ::= {
    WITH SYNTAX				    BOOLEAN
    EQUALITY MATCHING RULE	    booleanMatch
    LDAP-SYNTAX				    boolean.&id
    LDAP-NAME				    {"allowsHeterosexuals"}
    LDAP-DESC				    "Whether a group / organization allows heterosexuals to join"
    ID						    id-at-allowsHeterosexuals
}

allowsAltSexuals ATTRIBUTE ::= {
    WITH SYNTAX				    BOOLEAN
    EQUALITY MATCHING RULE	    booleanMatch
    LDAP-SYNTAX				    boolean.&id
    LDAP-NAME				    {"allowsAltSexuals"}
    LDAP-DESC				    "Whether a group / organization allows non-heterosexuals to join"
    ID						    id-at-allowsAltSexuals
}

allowsForeigners ATTRIBUTE ::= {
    WITH SYNTAX				    BOOLEAN
    EQUALITY MATCHING RULE	    booleanMatch
    LDAP-SYNTAX				    boolean.&id
    LDAP-NAME				    {"allowsForeigners"}
    LDAP-DESC				    "Whether a group / organization allows foreigners to join"
    ID						    id-at-allowsForeigners
}

hasDrugTestingRequirement ATTRIBUTE ::= {
    WITH SYNTAX				    BOOLEAN
    EQUALITY MATCHING RULE	    booleanMatch
    LDAP-SYNTAX				    boolean.&id
    LDAP-NAME				    {"hasDrugTestingRequirement"}
    LDAP-DESC				    "Whether a group / organization requires a passing drug test for membership"
    ID						    id-at-hasDrugTestingRequirement
}

hasNonDisclosureRequirement ATTRIBUTE ::= {
    WITH SYNTAX				    BOOLEAN
    EQUALITY MATCHING RULE	    booleanMatch
    LDAP-SYNTAX				    boolean.&id
    LDAP-NAME				    {"hasNonDisclosureRequirement"}
    LDAP-DESC				    "Whether "
    ID						    id-at-hasNonDisclosureRequirement
}

membershipIsSecret ATTRIBUTE ::= {
    WITH SYNTAX				    BOOLEAN
    EQUALITY MATCHING RULE	    booleanMatch
    LDAP-SYNTAX				    boolean.&id
    LDAP-NAME				    {"membershipIsSecret"}
    LDAP-DESC				    "Whether membership in this group is secret"
    ID						    id-at-membershipIsSecret
}

ownMembershipIsSecret ATTRIBUTE ::= {
    WITH SYNTAX				    BOOLEAN
    EQUALITY MATCHING RULE	    booleanMatch
    LDAP-SYNTAX				    boolean.&id
    LDAP-NAME				    {"ownMembershipIsSecret"}
    LDAP-DESC				    "Whether one's own membership in this group is secret"
    ID						    id-at-ownMembershipIsSecret
}

drugTestRequired ATTRIBUTE ::= {
    WITH SYNTAX				    DrugTestPanels
    EQUALITY MATCHING RULE	    objectIdentifierMatch
    LDAP-SYNTAX				    oid.&id
    LDAP-NAME				    {"drugTestRequired"}
    LDAP-DESC				    "The object identifier of a passing drug test panel required for membership"
    ID						    id-at-drugTestRequired
}

requiresReligion ATTRIBUTE ::= {
    WITH SYNTAX                 Religions
    EQUALITY MATCHING RULE      objectIdentifierMatch
    LDAP-SYNTAX                 oid.&id
    LDAP-NAME                   {"requiresReligion"}
    LDAP-DESC                   "Religious belief required for membership"
    ID                          id-at-requiresReligion
}

forbidsReligion ATTRIBUTE ::= {
    WITH SYNTAX                 Religions
    EQUALITY MATCHING RULE      objectIdentifierMatch
    LDAP-SYNTAX                 oid.&id
    LDAP-NAME                   {"forbidsReligion"}
    LDAP-DESC                   "Religious belief forbidden for membership"
    ID                          id-at-forbidsReligion
}

requiredCountryRace ATTRIBUTE ::= {
    WITH SYNTAX				    CountryName
    EQUALITY MATCHING RULE	    caseIgnoreMatch
    LDAP-SYNTAX                 countryString.&id
    LDAP-NAME				    {"requiredCountryRace"}
    LDAP-DESC				    "Race, as identified by country, required for membership"
    ID						    id-at-requiredCountryRace
}

requiredContinentalRace ATTRIBUTE ::= {
    WITH SYNTAX				    Continent
    EQUALITY MATCHING RULE      integerMatch
    LDAP-SYNTAX				    integer.&id
    LDAP-NAME				    {"requiredContinentalRace"}
    LDAP-DESC				    "Race, as identified by continent, required for membership"
    ID						    id-at-requiredContinentalRace
}

requiredRegionalRace ATTRIBUTE ::= {
    WITH SYNTAX				    UnitedNationsContinentalSubregion
    EQUALITY MATCHING RULE	    integerMatch
    LDAP-SYNTAX				    integer.&id
    LDAP-NAME				    {"requiredRegionalRace"}
    LDAP-DESC				    "Race, as identified by UN continental subregion, required for membership"
    ID						    id-at-requiredRegionalRace
}

forbiddenCountryRace ATTRIBUTE ::= {
    WITH SYNTAX				    CountryName
    EQUALITY MATCHING RULE	    caseIgnoreMatch
    LDAP-SYNTAX                 countryString.&id
    LDAP-NAME				    {"forbiddenCountryRace"}
    LDAP-DESC				    "Race, as identified by country, forbidden from membership"
    ID						    id-at-forbiddenCountryRace
}

forbiddenContinentalRace ATTRIBUTE ::= {
    WITH SYNTAX				    Continent
    EQUALITY MATCHING RULE	    integerMatch
    LDAP-SYNTAX				    integer.&id
    LDAP-NAME				    {"forbiddenContinentalRace"}
    LDAP-DESC				    "Race, as identified by continent, forbidden from membership"
    ID						    id-at-forbiddenContinentalRace
}

forbiddenRegionalRace ATTRIBUTE ::= {
    WITH SYNTAX				    UnitedNationsContinentalSubregion
    EQUALITY MATCHING RULE	    integerMatch
    LDAP-SYNTAX				    integer.&id
    LDAP-NAME				    {"forbiddenRegionalRace"}
    LDAP-DESC				    "Race, as identified by UN continental subregion, forbidden from membership"
    ID						    id-at-forbiddenRegionalRace
}

forbidsMembershipWithDN ATTRIBUTE ::= {
    SUBTYPE OF                  distinguishedName
    LDAP-SYNTAX                 dn.&id
    LDAP-NAME                   {"forbidsMembershipWithDN"}
    LDAP-DESC                   "DN of a group or organization whose membership this group or organization forbids"
    ID                          id-at-forbidsMembershipWithDN
}

leaderDN ATTRIBUTE ::= {
    SUBTYPE OF                  distinguishedName
    LDAP-SYNTAX                 dn.&id
    LDAP-NAME                   {"leaderDN"}
    LDAP-DESC                   "DN of the leader of a group or organization"
    ID                          id-at-leaderDN
}

presidentDN ATTRIBUTE ::= {
    SUBTYPE OF                  leaderDN
    LDAP-SYNTAX                 dn.&id
    LDAP-NAME                   {"presidentDN"}
    LDAP-DESC                   "DN of the president of a group or organization"
    ID                          id-at-presidentDN
}

vicePresidentDN ATTRIBUTE ::= {
    SUBTYPE OF                  leaderDN
    LDAP-SYNTAX                 dn.&id
    LDAP-NAME                   {"vicePresidentDN"}
    LDAP-DESC                   "DN of the vice president of a group or organization"
    ID                          id-at-vicePresidentDN
}

treasurerDN ATTRIBUTE ::= {
    SUBTYPE OF                  distinguishedName
    LDAP-SYNTAX                 dn.&id
    LDAP-NAME                   {"treasurerDN"}
    LDAP-DESC                   "DN of the treasurer of a group or organization"
    ID                          id-at-treasurerDN
}

secretaryDN ATTRIBUTE ::= {
    SUBTYPE OF                  distinguishedName
    LDAP-SYNTAX                 dn.&id
    LDAP-NAME                   {"secretaryDN"}
    LDAP-DESC                   "DN of the secretary of a group or organization"
    ID                          id-at-secretaryDN
}

historianDN ATTRIBUTE ::= {
    SUBTYPE OF                  distinguishedName
    LDAP-SYNTAX                 dn.&id
    LDAP-NAME                   {"historianDN"}
    LDAP-DESC                   "DN of the historian of a group or organization"
    ID                          id-at-historianDN
}

bylawsUrl ATTRIBUTE ::= {
    SUBTYPE OF                  url
    LDAP-NAME                   {"bylawsUrl"}
    LDAP-DESC                   "URL to the bylaws for this group or organization"
    ID                          id-at-bylawsUrl
}

symbolUrl ATTRIBUTE ::= {
    SUBTYPE OF                  url
    LDAP-NAME                   {"symbolUrl", "logoUrl"}
    LDAP-DESC                   "URL to the symbol / logo"
    ID                          id-at-symbolUrl
}

faviconUrl ATTRIBUTE ::= {
    SUBTYPE OF                  url
    LDAP-NAME                   {"faviconUrl"}
    LDAP-DESC                   "URL to the favicon"
    ID                          id-at-faviconUrl
}

-- A banner image is just a large (particularly wide) image for use on social
-- media sites, usually as a backdrop at the top of a profile page for a person
-- or organization
bannerImageUrl ATTRIBUTE ::= {
    SUBTYPE OF                  url
    LDAP-NAME                   {"bannerImageUrl"}
    LDAP-DESC                   "URL to the banner image"
    ID                          id-at-bannerImageUrl
}

symbolDescription ATTRIBUTE ::= {
    WITH SYNTAX				    UnboundedDirectoryString
    SUBSTRINGS MATCHING RULE    caseIgnoreSubstringsMatch
    LDAP-SYNTAX				    directoryString.&id
    LDAP-NAME				    {"symbolDescription"}
    LDAP-DESC				    "A description of the symbol associated with this entry"
    ID						    id-at-symbolDescription
}

anthemName ATTRIBUTE ::= {
    WITH SYNTAX				    UnboundedDirectoryString
    EQUALITY MATCHING RULE      caseIgnoreMatch
    ORDERING MATCHING RULE      caseIgnoreOrderingMatch
    SUBSTRINGS MATCHING RULE    caseIgnoreSubstringsMatch
    LDAP-SYNTAX				    directoryString.&id
    LDAP-NAME				    {"anthemName"}
    LDAP-DESC				    "The name of the anthem associated with this entry"
    ID						    id-at-anthemName
}

taxIdentifier ATTRIBUTE ::= {
    WITH SYNTAX				    UnboundedDirectoryString
    EQUALITY MATCHING RULE      caseIgnoreMatch
    ORDERING MATCHING RULE      caseIgnoreOrderingMatch
    SUBSTRINGS MATCHING RULE    caseIgnoreSubstringsMatch
    LDAP-SYNTAX				    directoryString.&id
    LDAP-NAME				    {"taxIdentifier"}
    LDAP-DESC				    "The tax identifier for this person, organization, business, etc."
    ID						    id-at-taxIdentifier
}

ideologicalRequirementsDescription ATTRIBUTE ::= {
    WITH SYNTAX				    UnboundedDirectoryString
    SUBSTRINGS MATCHING RULE    caseIgnoreSubstringsMatch
    LDAP-SYNTAX				    directoryString.&id
    LDAP-NAME				    {"ideologicalRequirementsDescription"}
    LDAP-DESC				    "A description of the ideological requirements for membership"
    ID						    id-at-ideologicalRequirementsDescription
}

faviconPNG ATTRIBUTE ::= {
    WITH SYNTAX				    OCTET STRING
    LDAP-SYNTAX				    octetString.&id
    LDAP-NAME				    {"faviconPNG"}
    LDAP-DESC				    "A PNG-formatted favicon"
    ID						    id-at-faviconPNG
}

publicMemberDN ATTRIBUTE ::= {
    SUBTYPE OF                  member
    LDAP-SYNTAX                 dn.&id
    LDAP-NAME                   {"publicMemberDN"}
    LDAP-DESC                   "DN of a member whose involvement is public / non-secret information"
    ID                          id-at-publicMemberDN
}

privateMemberDN ATTRIBUTE ::= {
    SUBTYPE OF                  member
    LDAP-SYNTAX                 dn.&id
    LDAP-NAME                   {"privateMemberDN"}
    LDAP-DESC                   "DN of a member whose involvement is private / secret information"
    ID                          id-at-privateMemberDN
}

publicUniqueMember ATTRIBUTE ::= {
    SUBTYPE OF                  uniqueMember
    LDAP-SYNTAX                 nameAndOptionalUID.&id
    LDAP-NAME                   {"publicUniqueMember"}
    LDAP-DESC                   "A member whose involvement is public / non-secret information"
    ID                          id-at-publicUniqueMember
}

privateUniqueMember ATTRIBUTE ::= {
    SUBTYPE OF                  uniqueMember
    LDAP-SYNTAX                 nameAndOptionalUID.&id
    LDAP-NAME                   {"privateUniqueMember"}
    LDAP-DESC                   "A member whose involvement is private / secret information"
    ID                          id-at-privateUniqueMember
}

-- NOTE: There is a similar attribute "isMemberOf" defined in EduMemberSchema and OpenDJCoreSchema.
memberOf ATTRIBUTE ::= {
    SUBTYPE OF                  distinguishedName
    LDAP-SYNTAX                 dn.&id
    LDAP-NAME                   {"memberOf"}
    LDAP-DESC                   "DN of a group or organization to which this entry is a member"
    ID                          id-at-memberOf
}

publicMemberOf ATTRIBUTE ::= {
    SUBTYPE OF                  memberOf
    LDAP-SYNTAX                 dn.&id
    LDAP-NAME                   {"publicMemberOf"}
    LDAP-DESC                   "DN of a group or organization to which this entry is publicly a member"
    ID                          id-at-publicMemberOf
}

privateMemberOf ATTRIBUTE ::= {
    SUBTYPE OF                  memberOf
    LDAP-SYNTAX                 dn.&id
    LDAP-NAME                   {"privateMemberOf"}
    LDAP-DESC                   "DN of a group or organization to which this entry is privately / secretly a member"
    ID                          id-at-privateMemberOf
}

/* A filter used to evaluate an entry for its eligibility for membership. If the
entry matches this filter, that entry describes a person that is eligible for
membership. */
eligibilityFilter ATTRIBUTE ::= {
    WITH SYNTAX                 Filter
    ID                          id-at-eligibilityFilter
}

-- Like eligibilityFilter, except it does not match against attribute subtypes.
eligibilityNoSubtypesFilter ATTRIBUTE ::= {
    WITH SYNTAX                 Filter
    ID                          id-at-eligibilityNoSubtypesFilter
}

donorDN ATTRIBUTE ::= {
    SUBTYPE OF                  distinguishedName
    LDAP-SYNTAX                 dn.&id
    LDAP-NAME                   {"donorDN"}
    LDAP-DESC                   "DN of a donor to this person or organization"
    ID                          id-at-donorDN
}

topDonorDN ATTRIBUTE ::= {
    SUBTYPE OF                  donorDN
    LDAP-SYNTAX                 dn.&id
    LDAP-NAME                   {"topDonorDN"}
    LDAP-DESC                   "DN of a top donor to this person or organization"
    ID                          id-at-topDonorDN
}

directorDN ATTRIBUTE ::= {
    SUBTYPE OF                  leaderDN
    LDAP-SYNTAX                 dn.&id
    LDAP-NAME                   {"directorDN"}
    LDAP-DESC                   "DN of a member of the board of directors"
    ID                          id-at-directorDN
}

chiefExecutiveOfficerDN ATTRIBUTE ::= {
    SUBTYPE OF                  leaderDN
    LDAP-SYNTAX                 dn.&id
    LDAP-NAME                   {"chiefExecutiveOfficerDN"}
    LDAP-DESC                   "DN of the Chief Executive Officer (CEO)"
    ID                          id-at-chiefExecutiveOfficerDN
}

chiefFinancialOfficerDN ATTRIBUTE ::= {
    SUBTYPE OF                  leaderDN
    LDAP-SYNTAX                 dn.&id
    LDAP-NAME                   {"chiefFinancialOfficerDN"}
    LDAP-DESC                   "DN of the Chief Financial Officer (CFO)"
    ID                          id-at-chiefFinancialOfficerDN
}

chiefOperationsOfficerDN ATTRIBUTE ::= {
    SUBTYPE OF                  leaderDN
    LDAP-SYNTAX                 dn.&id
    LDAP-NAME                   {"chiefOperationsOfficerDN"}
    LDAP-DESC                   "DN of the Chief Operations Officer (COO)"
    ID                          id-at-chiefOperationsOfficerDN
}

chiefInformationOfficerDN ATTRIBUTE ::= {
    SUBTYPE OF                  leaderDN
    LDAP-SYNTAX                 dn.&id
    LDAP-NAME                   {"chiefInformationOfficerDN"}
    LDAP-DESC                   "DN of the Chief Information Officer (CIO)"
    ID                          id-at-chiefInformationOfficerDN
}

chiefTechnologyOfficerDN ATTRIBUTE ::= {
    SUBTYPE OF                  leaderDN
    LDAP-SYNTAX                 dn.&id
    LDAP-NAME                   {"chiefTechnologyOfficerDN"}
    LDAP-DESC                   "DN of the Chief Technology Officer (CTO)"
    ID                          id-at-chiefTechnologyOfficerDN
}

chiefMarketingOfficerDN ATTRIBUTE ::= {
    SUBTYPE OF                  leaderDN
    LDAP-SYNTAX                 dn.&id
    LDAP-NAME                   {"chiefMarketingOfficerDN"}
    LDAP-DESC                   "DN of the Chief Marketing Officer (CMO)"
    ID                          id-at-chiefMarketingOfficerDN
}

chiefHumanResourcesOfficerDN ATTRIBUTE ::= {
    SUBTYPE OF                  leaderDN
    LDAP-SYNTAX                 dn.&id
    LDAP-NAME                   {"chiefHumanResourcesOfficerDN"}
    LDAP-DESC                   "DN of the Chief Human Resources Officer (CHRO)"
    ID                          id-at-chiefHumanResourcesOfficerDN
}

chiefInformationSecurityOfficerDN ATTRIBUTE ::= {
    SUBTYPE OF                  leaderDN
    LDAP-SYNTAX                 dn.&id
    LDAP-NAME                   {"chiefInformationSecurityOfficerDN"}
    LDAP-DESC                   "DN of the Chief Information Security Officer (CISO)"
    ID                          id-at-chiefInformationSecurityOfficerDN
}

chiefLegalOfficerDN ATTRIBUTE ::= {
    SUBTYPE OF                  leaderDN
    LDAP-SYNTAX                 dn.&id
    LDAP-NAME                   {"chiefLegalOfficerDN"}
    LDAP-DESC                   "DN of the Chief Legal Officer (CLO)"
    ID                          id-at-chiefLegalOfficerDN
}

chiefDiversityOfficerDN ATTRIBUTE ::= {
    SUBTYPE OF                  leaderDN
    LDAP-SYNTAX                 dn.&id
    LDAP-NAME                   {"chiefDiversityOfficerDN"}
    LDAP-DESC                   "DN of the Chief Diversity Officer (CDO)"
    ID                          id-at-chiefDiversityOfficerDN
}

affiliateDN ATTRIBUTE ::= {
    SUBTYPE OF                  distinguishedName
    LDAP-SYNTAX                 dn.&id
    LDAP-NAME                   {"affiliateDN"}
    LDAP-DESC                   "DN of an affiliate"
    ID                          id-at-affiliateDN
}

subsidiaryDN ATTRIBUTE ::= {
    SUBTYPE OF                  distinguishedName
    LDAP-SYNTAX                 dn.&id
    LDAP-NAME                   {"subsidiaryDN"}
    LDAP-DESC                   "DN of a subsidiary"
    ID                          id-at-subsidiaryDN
}

parentOrganizationDN ATTRIBUTE ::= {
    SUBTYPE OF                  distinguishedName
    LDAP-SYNTAX                 dn.&id
    LDAP-NAME                   {"parentOrganizationDN"}
    LDAP-DESC                   "DN of a parent organization"
    ID                          id-at-parentOrganizationDN
}

contributorDN ATTRIBUTE ::= {
    SUBTYPE OF                  distinguishedName
    LDAP-SYNTAX                 dn.&id
    LDAP-NAME                   {"contributorDN"}
    LDAP-DESC                   "DN of a contributor (in terms of labor) to a project"
    ID                          id-at-contributorDN
}

topContributorDN ATTRIBUTE ::= {
    SUBTYPE OF                  contributorDN
    LDAP-SYNTAX                 dn.&id
    LDAP-NAME                   {"topContributorDN"}
    LDAP-DESC                   "DN of a top contributor (in terms of labor) to a project"
    ID                          id-at-topContributorDN
}

shellCorporationDN ATTRIBUTE ::= {
    SUBTYPE OF                  distinguishedName
    LDAP-SYNTAX                 dn.&id
    LDAP-NAME                   {"shellCorporationDN"}
    LDAP-DESC                   "DN of a shell corporation used by this company or organization"
    ID                          id-at-shellCorporationDN
}

frontOrganizationDN ATTRIBUTE ::= {
    SUBTYPE OF                  distinguishedName
    LDAP-SYNTAX                 dn.&id
    LDAP-NAME                   {"frontOrganizationDN"}
    LDAP-DESC                   "DN of a front organization used by this company or organization"
    ID                          id-at-frontOrganizationDN
}

missionStatement ATTRIBUTE ::= {
    WITH SYNTAX				    UnboundedDirectoryString
    SUBSTRINGS MATCHING RULE    caseIgnoreSubstringsMatch
    LDAP-SYNTAX				    directoryString.&id
    LDAP-NAME				    {"missionStatement"}
    LDAP-DESC				    "Mission Statement"
    ID						    id-at-missionStatement
}

malePopulationPercentage ATTRIBUTE ::= {
    WITH SYNTAX                 BoundedPercentage
    EQUALITY MATCHING RULE      realMatch
    ORDERING MATCHING RULE      realOrderingMatch
    LDAP-SYNTAX				    real.&id
    LDAP-NAME				    {"malePopulationPercentage"}
    LDAP-DESC				    "Male Population as a Percentage of the Total"
    ID						    id-at-malePopulationPercentage
}

admissionRate ATTRIBUTE ::= {
    WITH SYNTAX                 BoundedPercentage
    EQUALITY MATCHING RULE      realMatch
    ORDERING MATCHING RULE      realOrderingMatch
    LDAP-SYNTAX				    real.&id
    LDAP-NAME				    {"admissionRate"}
    LDAP-DESC				    "Admission Rate as a Percentage of Applicants / Candidates"
    ID						    id-at-admissionRate
}

admissionRateForMales ATTRIBUTE ::= {
    WITH SYNTAX                 BoundedPercentage
    EQUALITY MATCHING RULE      realMatch
    ORDERING MATCHING RULE      realOrderingMatch
    LDAP-SYNTAX				    real.&id
    LDAP-NAME				    {"admissionRateForMales"}
    LDAP-DESC				    "Admission Rate as a Percentage of all Male Applicants / Candidates"
    ID						    id-at-admissionRateForMales
}

admissionRateForFemales ATTRIBUTE ::= {
    WITH SYNTAX                 BoundedPercentage
    EQUALITY MATCHING RULE      realMatch
    ORDERING MATCHING RULE      realOrderingMatch
    LDAP-SYNTAX				    real.&id
    LDAP-NAME				    {"admissionRateForFemales"}
    LDAP-DESC				    "Admission Rate as a Percentage of all Female Applicants / Candidates"
    ID						    id-at-admissionRateForFemales
}

admissionRateForCollegeEducated ATTRIBUTE ::= {
    WITH SYNTAX                 BoundedPercentage
    EQUALITY MATCHING RULE      realMatch
    ORDERING MATCHING RULE      realOrderingMatch
    LDAP-SYNTAX				    real.&id
    LDAP-NAME				    {"admissionRateForCollegeEducated"}
    LDAP-DESC				    "Admission Rate as a Percentage of all College-Educated Applicants / Candidates"
    ID						    id-at-admissionRateForCollegeEducated
}

admissionRateForMarried ATTRIBUTE ::= {
    WITH SYNTAX                 BoundedPercentage
    EQUALITY MATCHING RULE      realMatch
    ORDERING MATCHING RULE      realOrderingMatch
    LDAP-SYNTAX				    real.&id
    LDAP-NAME				    {"admissionRateForMarried"}
    LDAP-DESC				    "Admission Rate as a Percentage of all Married Applicants / Candidates"
    ID						    id-at-admissionRateForMarried
}

admissionRateForNonCollegeEducated ATTRIBUTE ::= {
    WITH SYNTAX                 BoundedPercentage
    EQUALITY MATCHING RULE      realMatch
    ORDERING MATCHING RULE      realOrderingMatch
    LDAP-SYNTAX				    real.&id
    LDAP-NAME				    {"admissionRateForNonCollegeEducated"}
    LDAP-DESC				    "Admission Rate as a Percentage of all Non-College-Educated Applicants / Candidates"
    ID						    id-at-admissionRateForNonCollegeEducated
}

admissionRateForNonMarried ATTRIBUTE ::= {
    WITH SYNTAX                 BoundedPercentage
    EQUALITY MATCHING RULE      realMatch
    ORDERING MATCHING RULE      realOrderingMatch
    LDAP-SYNTAX				    real.&id
    LDAP-NAME				    {"admissionRateForNonMarried"}
    LDAP-DESC				    "Admission Rate as a Percentage of all Non-Married Applicants / Candidates"
    ID						    id-at-admissionRateForNonMarried
}

collegeEducatedMembersPercentage ATTRIBUTE ::= {
    WITH SYNTAX                 BoundedPercentage
    EQUALITY MATCHING RULE      realMatch
    ORDERING MATCHING RULE      realOrderingMatch
    LDAP-SYNTAX				    real.&id
    LDAP-NAME				    {"collegeEducatedMembersPercentage"}
    LDAP-DESC				    "Percentage of Membership that is College-Educated"
    ID						    id-at-collegeEducatedMembersPercentage
}

marriedMembersPercentage ATTRIBUTE ::= {
    WITH SYNTAX                 BoundedPercentage
    EQUALITY MATCHING RULE      realMatch
    ORDERING MATCHING RULE      realOrderingMatch
    LDAP-SYNTAX				    real.&id
    LDAP-NAME				    {"marriedMembersPercentage"}
    LDAP-DESC				    "Percentage of Membership that is Married"
    ID						    id-at-marriedMembersPercentage
}

admissionConsiderationAttribute ATTRIBUTE ::= {
    WITH SYNTAX				    AttributeType
    EQUALITY MATCHING RULE	    objectIdentifierMatch
    LDAP-SYNTAX				    oid.&id
    LDAP-NAME				    {"admissionConsiderationAttribute"}
    LDAP-DESC				    "Attribute type OID of an attribute considered when deciding admission"
    ID						    id-at-admissionConsiderationAttribute
}

admissionNonConsiderationAttribute ATTRIBUTE ::= {
    WITH SYNTAX				    AttributeType
    EQUALITY MATCHING RULE	    objectIdentifierMatch
    LDAP-SYNTAX				    oid.&id
    LDAP-NAME				    {"admissionNonConsiderationAttribute"}
    LDAP-DESC				    "Attribute type OID of an attribute NOT considered when deciding admission"
    ID						    id-at-admissionNonConsiderationAttribute
}

applicationFee ATTRIBUTE ::= {
    WITH SYNTAX                 Currency
    EQUALITY MATCHING RULE      currencyMatch
    ORDERING MATCHING RULE      currencyOrderingMatch
    LDAP-SYNTAX				    currencySyntax.&id
    LDAP-NAME				    {"applicationFee"}
    LDAP-DESC				    "Application Fee"
    ID						    id-at-applicationFee
}

meanSalary ATTRIBUTE ::= {
    WITH SYNTAX                 Currency
    EQUALITY MATCHING RULE      currencyMatch
    ORDERING MATCHING RULE      currencyOrderingMatch
    LDAP-SYNTAX				    currencySyntax.&id
    LDAP-NAME				    {"meanSalary"}
    LDAP-DESC				    "Mean Salary"
    ID						    id-at-meanSalary
}

medianSalary ATTRIBUTE ::= {
    WITH SYNTAX                 Currency
    EQUALITY MATCHING RULE      currencyMatch
    ORDERING MATCHING RULE      currencyOrderingMatch
    LDAP-SYNTAX				    currencySyntax.&id
    LDAP-NAME				    {"medianSalary"}
    LDAP-DESC				    "Median Salary"
    ID						    id-at-medianSalary
}

highestSalary ATTRIBUTE ::= {
    WITH SYNTAX                 Currency
    EQUALITY MATCHING RULE      currencyMatch
    ORDERING MATCHING RULE      currencyOrderingMatch
    LDAP-SYNTAX				    currencySyntax.&id
    LDAP-NAME				    {"highestSalary"}
    LDAP-DESC				    "Highest Salary"
    ID						    id-at-highestSalary
}

lowestSalary ATTRIBUTE ::= {
    WITH SYNTAX                 Currency
    EQUALITY MATCHING RULE      currencyMatch
    ORDERING MATCHING RULE      currencyOrderingMatch
    LDAP-SYNTAX				    currencySyntax.&id
    LDAP-NAME				    {"lowestSalary"}
    LDAP-DESC				    "Lowest Salary"
    ID						    id-at-lowestSalary
}

applicantsCount ATTRIBUTE ::= {
    WITH SYNTAX				    INTEGER (0..MAX)
    EQUALITY MATCHING RULE	    integerMatch
    ORDERING MATCHING RULE	    integerOrderingMatch
    LDAP-SYNTAX				    integer.&id
    LDAP-NAME				    {"applicantsCount"}
    LDAP-DESC				    "Cumulative Number of Applicants over all time"
    ID						    id-at-applicantsCount
}

applicantsCountTTM ATTRIBUTE ::= {
    WITH SYNTAX				    INTEGER (0..MAX)
    EQUALITY MATCHING RULE	    integerMatch
    ORDERING MATCHING RULE	    integerOrderingMatch
    LDAP-SYNTAX				    integer.&id
    LDAP-NAME				    {"applicantsCountTTM"}
    LDAP-DESC				    "Number of Applicants over the Last Twelve Months"
    ID						    id-at-applicantsCountTTM
}

meanMemberAge ATTRIBUTE ::= {
    WITH SYNTAX                 REAL (0.0..1.0)
    EQUALITY MATCHING RULE      realMatch
    ORDERING MATCHING RULE      realOrderingMatch
    LDAP-SYNTAX				    real.&id
    LDAP-NAME				    {"meanMemberAge"}
    LDAP-DESC				    "Mean Member Age"
    ID						    id-at-meanMemberAge
}

medianMemberAge ATTRIBUTE ::= {
    WITH SYNTAX                 REAL (0.0..1.0)
    EQUALITY MATCHING RULE      realMatch
    ORDERING MATCHING RULE      realOrderingMatch
    LDAP-SYNTAX				    real.&id
    LDAP-NAME				    {"medianMemberAge"}
    LDAP-DESC				    "Median Member Age"
    ID						    id-at-medianMemberAge
}

highestMemberAge ATTRIBUTE ::= {
    WITH SYNTAX                 REAL (0.0..1.0)
    EQUALITY MATCHING RULE      realMatch
    ORDERING MATCHING RULE      realOrderingMatch
    LDAP-SYNTAX				    real.&id
    LDAP-NAME				    {"highestMemberAge"}
    LDAP-DESC				    "Highest Member Age"
    ID						    id-at-highestMemberAge
}

lowestMemberAge ATTRIBUTE ::= {
    WITH SYNTAX                 REAL (0.0..1.0)
    EQUALITY MATCHING RULE      realMatch
    ORDERING MATCHING RULE      realOrderingMatch
    LDAP-SYNTAX				    real.&id
    LDAP-NAME				    {"lowestMemberAge"}
    LDAP-DESC				    "Lowest Member Age"
    ID						    id-at-lowestMemberAge
}

vettingRequirements ATTRIBUTE ::= {
    WITH SYNTAX				    VettingRequirements
    EQUALITY MATCHING RULE	    objectIdentifierMatch
    LDAP-SYNTAX				    oid.&id
    LDAP-NAME				    {"vettingRequirements"}
    LDAP-DESC				    "The object identifier of a category of vetting procedures required"
    ID						    id-at-vettingRequirements
}

-- Attribute Sets

MembershipStatsAttributes ATTRIBUTE ::= {
    membersCount
    | activeMembersCount
    | dormantMembersCount
    | formerMembersCount
}

MembershipTermsAttributes ATTRIBUTE ::= {
    membershipTerm
    | memberNoun
    | memberSingularNoun
    | memberPluralNoun
    | memberSlangNoun
}

MembershipLifecycleProcedureDescriptions ATTRIBUTE ::= {
    vettingProcedureDescription
    | onboardingProcedureDescription
    | offboardingProcedureDescription
    | renewalProcedureDescription
    | vettingRequirements
}

RacialRequirements ATTRIBUTE ::= {
    requiredContinentalRace
    | requiredCountryRace
    | requiredRegionalRace
}

RacialExclusions ATTRIBUTE ::= {
    forbiddenContinentalRace
    | forbiddenCountryRace
    | forbiddenRegionalRace
}

MembershipRequirementsAttributes ATTRIBUTE ::= {
    minAgeToJoin
    | maxAgeToJoin
    | allowsMen
    | allowsWomen
    | allowsHeterosexuals
    | allowsAltSexuals
    | allowsForeigners
    | requiresReligion
    | forbidsReligion
    | RacialRequirements
    | RacialExclusions
    | drugTestRequired
    | forbidsMembershipWithDN
    | eligibilityFilter
    | eligibilityNoSubtypesFilter
    | ideologicalRequirementsDescription
    | healthRequirementsDescription
    | requiredVaccinationAgainst
}

OrganizationBylawsAttributes ATTRIBUTE ::= {
    hasDrugTestingRequirement
    | hasNonDisclosureRequirement
    | membershipIsSecret
    | ownMembershipIsSecret
    | membershipOath
    | bylawsUrl
    | bylawsText
}

CLevelLeadershipAttributes ATTRIBUTE ::= {
    chiefExecutiveOfficerDN
    | chiefFinancialOfficerDN
    | chiefOperationsOfficerDN
    | chiefInformationOfficerDN
    | chiefTechnologyOfficerDN
    | chiefMarketingOfficerDN
    | chiefHumanResourcesOfficerDN
    | chiefInformationSecurityOfficerDN
    | chiefLegalOfficerDN
    | chiefDiversityOfficerDN
}

LeadershipAttributes ATTRIBUTE ::= {
    leaderDN
    | presidentDN
    | vicePresidentDN
    | treasurerDN
    | secretaryDN
    | historianDN
}

MemberAndSubtypes ATTRIBUTE ::= {
    member
    | publicMemberDN
    | privateMemberDN
}

UniqueMemberAndSubtypes ATTRIBUTE ::= {
    uniqueMember
    | publicUniqueMember
    | privateUniqueMember
}

MemberOfAndSubtypes ATTRIBUTE ::= {
    memberOf
    | publicMemberOf
    | privateMemberOf
}

MembershipRelationAttributes ATTRIBUTE ::= {
    MemberAndSubtypes
    | UniqueMemberAndSubtypes
    | MemberOfAndSubtypes
}

OrganizationalFinanceAttributes ATTRIBUTE ::= {
    BasicBalanceSheetAttributes
    | BasicIncomeStatementAttributes
    | FinanceAttributes
    | AccountingAttributes
    | topDonorDN
}

ContributionAttributes ATTRIBUTE ::= {contributorDN | topContributorDN}

OrganizationalRelationAttributes ATTRIBUTE ::= {
    affiliateDN
    | subsidiaryDN
    | parentOrganizationDN
    | shellCorporationDN
    | frontOrganizationDN
}

AdmissionRateStatAttributes ATTRIBUTE ::= {
    admissionRate
    | admissionRateForMales
    | admissionRateForFemales
    | admissionRateForCollegeEducated
    | admissionRateForMarried
    | admissionRateForNonCollegeEducated
    | admissionRateForNonMarried,
    ...
}

MembershipStatAttributes ATTRIBUTE ::= {
    AdmissionRateStatAttributes
    | applicantsCount
    | applicantsCountTTM
    | malePopulationPercentage
    | meanSalary
    | medianSalary
    | highestSalary
    | lowestSalary
    | collegeEducatedMembersPercentage
    | marriedMembersPercentage
    | meanMemberAge
    | medianMemberAge
    | highestMemberAge
    | lowestMemberAge,
    ...
}

ExtOrganizationOrGroupAttributes ATTRIBUTE ::= {
    MembershipStatsAttributes
    | MembershipTermsAttributes
    | MembershipLifecycleProcedureDescriptions
    | MembershipRequirementsAttributes
    | OrganizationBylawsAttributes
    | MembershipRelationAttributes
    | OrganizationalDescriptionAttributes
    | FundingAttributes
    | OrganizationalFinanceAttributes
    | PositiveComplianceAttributes
    | CreationAttributes
    | BusinessCategoryTypes
    | ThemeColorAttributes
    | VerbalContentAttributes
    | ContributionAttributes
    | MembershipStatAttributes
    | missionStatement
    | faviconPNG
    | symbolUrl
    | symbolDescription
    | anthemName
    | timeToLiveDuration -- Controls client caching of the group membership
    | associatedDomain
    | dnsName
    | category
    | rules
    | keyword
    | url
}

-- Attributes for organizations, but not groups / roles
ExtOrganizationalAttributes ATTRIBUTE ::= {
    ExtOrganizationOrGroupAttributes
    | OrganizationIdentifierTypes
    | BillingPostalAttributeSet
    | HeadquartersPostalAttributeSet
    | MailingPostalAttributeSet
    | PrincipalPostalAttributeSet
    | OrganizationalPhoneAttributeSet
    | OrganizationalFaxAttributeSet
    | OrganizationalEmailAttributeSet
    | OrganizationalUrls
    | LeadershipAttributes
    | TaxpayerAttributes
    | CLevelLeadershipAttributes
    | OrganizationalRelationAttributes
    | owner
    | organizationIdentifier
    | taxIdentifier
    | stakeholderDN
    | beneficiaryDN
    | directorDN
}

-- Object Classes

organizationExt OBJECT-CLASS ::= {
    SUBCLASS OF			{organization}
    KIND				structural
    MAY CONTAIN			{ExtOrganizationalAttributes}
    LDAP-NAME			{"organizationExt"}
    LDAP-DESC			"An organization"
    ID					id-oc-organizationExt
}

organizationalUnitExt OBJECT-CLASS ::= {
    SUBCLASS OF         {organizationalUnit}
    KIND                structural
    MAY CONTAIN         {ExtOrganizationalAttributes}
    LDAP-NAME           {"organizationalUnitExt"}
    LDAP-DESC           "An organizational unit"
    ID                  id-oc-organizationalUnitExt
}

organizationalRoleExt OBJECT-CLASS ::= {
    SUBCLASS OF         {organizationalRole}
    KIND                structural
    MAY CONTAIN         {ExtOrganizationOrGroupAttributes}
    LDAP-NAME           {"organizationalRoleExt"}
    LDAP-DESC           "An organizational role"
    ID                  id-oc-organizationalRoleExt
}

groupOfNamesExt OBJECT-CLASS ::= {
    SUBCLASS OF         {groupOfNames}
    KIND                structural
    MAY CONTAIN         {ExtOrganizationOrGroupAttributes}
    LDAP-NAME           {"groupOfNamesExt"}
    LDAP-DESC           "A group of names"
    ID                  id-oc-groupOfNamesExt
}

groupOfUniqueNamesExt OBJECT-CLASS ::= {
    SUBCLASS OF         {groupOfUniqueNames}
    KIND                structural
    MAY CONTAIN         {ExtOrganizationOrGroupAttributes}
    LDAP-NAME           {"groupOfUniqueNamesExt"}
    LDAP-DESC           "A group of unique names"
    ID                  id-oc-groupOfUniqueNamesExt
}

-- // TODO: Fill these in

boardOfDirectors OBJECT-CLASS ::= {
    SUBCLASS OF			{top}
    KIND				auxiliary
    MUST CONTAIN		{}
    MAY CONTAIN			{}
    LDAP-NAME			{"boardOfDirectors"}
    LDAP-DESC			"Board of Directors"
    ID					id-oc-boardOfDirectors
}

vorstand OBJECT-CLASS ::= {
    SUBCLASS OF			{top}
    KIND				auxiliary
    MUST CONTAIN		{}
    MAY CONTAIN			{}
    LDAP-NAME			{"vorstand"}
    LDAP-DESC			"Vorstand"
    ID					id-oc-vorstand
}

committee OBJECT-CLASS ::= {
    SUBCLASS OF			{top}
    KIND				auxiliary
    MUST CONTAIN		{}
    MAY CONTAIN			{
        committeeType -- executive, conference, standing, nominating, steering, special
    }
    LDAP-NAME			{"committee"}
    LDAP-DESC			"Committee"
    ID					id-oc-committee
}

caucus OBJECT-CLASS ::= {
    SUBCLASS OF			{top}
    KIND				auxiliary
    MUST CONTAIN		{}
    MAY CONTAIN			{}
    LDAP-NAME			{"caucus"}
    LDAP-DESC			"Caucus"
    ID					id-oc-caucus
}

-- // TODO: cryptocurrencyExchange

-- Name Forms

organizationExtNameForm NAME-FORM ::= {
    NAMES			    organizationExt
    WITH ATTRIBUTES	    orgNameForm.&MandatoryAttributes -- organizationName
    LDAP-NAME		    {"organizationExtNameForm"}
    ID				    id-nf-organizationExtNameForm
}

organizationalRoleExtNameForm NAME-FORM ::= {
    NAMES			    organizationalRoleExt
    WITH ATTRIBUTES	    orgRoleNameForm.&MandatoryAttributes -- commonName
    LDAP-NAME		    {"organizationalRoleExtNameForm"}
    ID				    id-nf-organizationalRoleExtNameFo
}

groupOfNamesExtNameForm NAME-FORM ::= {
    NAMES			    groupOfNamesExt
    WITH ATTRIBUTES	    gONNameForm.&MandatoryAttributes -- commonName
    LDAP-NAME		    {"groupOfNamesExtNameForm"}
    ID				    id-nf-groupOfNamesExtNameForm
}

groupOfUniqueNamesExtNameForm NAME-FORM ::= {
    NAMES			    groupOfUniqueNamesExt
    WITH ATTRIBUTES	    {commonName}
    LDAP-NAME		    {"groupOfUniqueNamesExtNameForm"}
    ID				    id-nf-groupOfUniqueNamesExtNameFo
}

organizationalUnitExtNameForm NAME-FORM ::= {
    NAMES			    organizationalUnitExt
    WITH ATTRIBUTES	    orgUnitNameForm.&MandatoryAttributes -- organizationalUnitName
    LDAP-NAME		    {"organizationalUnitExtNameForm"}
    ID				    id-nf-organizationalUnitExtNameFo
}

END
