-- Derived from data/ldap-schema/schema2ldif/core.schema
-- Upstream: http://www.openldap.org/
-- This module is a container for LDAP schema. It has no module identifier.
-- X- extension fields from the LDAP schema are comments. USAGE userApplications and structural KIND are omitted because they are the defaults.
-- 78 elements were omitted because their OIDs are already defined. See CONVERSION-REPORT.txt.
-- LDAP {length} bounds on directory strings are DirectoryString{n}. Bounds on IA5String, PrintableString, NumericString, and OCTET STRING are SIZE (1..n). Other bounds stay comments because the LDAP figure is an encoded-length hint.
LdapSchema2ldifCore DEFINITIONS ::=
BEGIN

IMPORTS

  ATTRIBUTE
    FROM InformationFramework
      {joint-iso-itu-t ds(5) module(1) informationFramework(1) 9} WITH SUCCESSORS

  caseIgnoreIA5Match, caseIgnoreIA5SubstringsMatch, ia5String
    FROM SelectedAttributeTypes
      {joint-iso-itu-t ds(5) module(1) selectedAttributeTypes(5) 9} WITH SUCCESSORS ;

-- Object identifiers

id-at-teletexTerminalIdentifier OBJECT IDENTIFIER ::= { 2 5 4 22 }
id-at-mail OBJECT IDENTIFIER ::= { 0 9 2342 19200300 100 1 3 }
id-at-associatedDomain OBJECT IDENTIFIER ::= { 0 9 2342 19200300 100 1 37 }

-- Attribute types

-- LDAP syntax 1.3.6.1.4.1.1466.115.121.1.51 is a Teletex Terminal Identifier (RFC 4517). X.520 has removed that type. Represented as OCTET STRING.
teletexTerminalIdentifier ATTRIBUTE ::= {
  WITH SYNTAX               OCTET STRING
  LDAP-SYNTAX               { 1 3 6 1 4 1 1466 115 121 1 51 }
  LDAP-NAME                 {"teletexTerminalIdentifier"}
  LDAP-DESC                 "RFC2256: Teletex Terminal Identifier"
  ID                        id-at-teletexTerminalIdentifier }

mail ATTRIBUTE ::= {
  WITH SYNTAX               IA5String(SIZE (1..256))
  EQUALITY MATCHING RULE    caseIgnoreIA5Match
  SUBSTRINGS MATCHING RULE  caseIgnoreIA5SubstringsMatch
  LDAP-SYNTAX               ia5String.&id
  LDAP-NAME                 {"mail", "rfc822Mailbox"}
  LDAP-DESC                 "RFC1274: RFC822 Mailbox"
  ID                        id-at-mail }

associatedDomain ATTRIBUTE ::= {
  WITH SYNTAX               IA5String
  EQUALITY MATCHING RULE    caseIgnoreIA5Match
  SUBSTRINGS MATCHING RULE  caseIgnoreIA5SubstringsMatch
  LDAP-SYNTAX               ia5String.&id
  LDAP-NAME                 {"associatedDomain"}
  LDAP-DESC                 "RFC1274: domain associated with object"
  ID                        id-at-associatedDomain }
END
