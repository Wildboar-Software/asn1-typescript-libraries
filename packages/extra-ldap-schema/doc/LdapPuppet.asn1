-- Derived from data/ldap-schema/puppet.ldif
-- Upstream: https://github.com/wikimedia-incubator/operations-puppet/blob/392301bc570b5b61f48eda0cbaa62b8b8ff52f92/files/ldap/puppet.ldif#L3
-- This module is a container for LDAP schema. It has no module identifier.
-- X- extension fields from the LDAP schema are comments. USAGE userApplications and structural KIND are omitted because they are the defaults.
LdapPuppet DEFINITIONS ::=
BEGIN

IMPORTS

  ATTRIBUTE, OBJECT-CLASS, top
    FROM InformationFramework
      {joint-iso-itu-t ds(5) module(1) informationFramework(1) 9} WITH SUCCESSORS

  caseIgnoreIA5Match, ia5String
    FROM SelectedAttributeTypes
      {joint-iso-itu-t ds(5) module(1) selectedAttributeTypes(5) 9} WITH SUCCESSORS ;

-- Object identifiers

id-at-puppetClass OBJECT IDENTIFIER ::= { 1 3 6 1 4 1 34380 1 1 3 10 }
id-at-parentNode OBJECT IDENTIFIER ::= { 1 3 6 1 4 1 34380 1 1 3 9 }
id-at-environment OBJECT IDENTIFIER ::= { 1 3 6 1 4 1 34380 1 1 3 11 }
id-at-puppetVar OBJECT IDENTIFIER ::= { 1 3 6 1 4 1 34380 1 1 3 12 }
id-oc-puppetClient OBJECT IDENTIFIER ::= { 1 3 6 1 4 1 34380 1 1 1 2 }

-- Attribute types

puppetClass ATTRIBUTE ::= {
  WITH SYNTAX               IA5String
  EQUALITY MATCHING RULE    caseIgnoreIA5Match
  LDAP-SYNTAX               ia5String.&id
  LDAP-NAME                 {"puppetClass"}
  LDAP-DESC                 "Puppet Node Class"
  ID                        id-at-puppetClass }

parentNode ATTRIBUTE ::= {
  WITH SYNTAX               IA5String
  EQUALITY MATCHING RULE    caseIgnoreIA5Match
  SINGLE VALUE              TRUE
  LDAP-SYNTAX               ia5String.&id
  LDAP-NAME                 {"parentNode"}
  LDAP-DESC                 "Puppet Parent Node"
  ID                        id-at-parentNode }

environment ATTRIBUTE ::= {
  WITH SYNTAX               IA5String
  EQUALITY MATCHING RULE    caseIgnoreIA5Match
  LDAP-SYNTAX               ia5String.&id
  LDAP-NAME                 {"environment"}
  LDAP-DESC                 "Puppet Node Environment"
  ID                        id-at-environment }

puppetVar ATTRIBUTE ::= {
  WITH SYNTAX               IA5String
  EQUALITY MATCHING RULE    caseIgnoreIA5Match
  LDAP-SYNTAX               ia5String.&id
  LDAP-NAME                 {"puppetVar"}
  LDAP-DESC                 "A variable setting for puppet"
  ID                        id-at-puppetVar }

-- Object classes

puppetClient OBJECT-CLASS ::= {
  SUBCLASS OF               { top }
  KIND                      auxiliary
  MAY CONTAIN               { puppetClass
                              | parentNode
                              | environment
                              | puppetVar }
  LDAP-NAME                 {"puppetClient"}
  LDAP-DESC                 "Puppet Client objectclass"
  ID                        id-oc-puppetClient }
END
