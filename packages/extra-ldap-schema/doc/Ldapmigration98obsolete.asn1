-- Derived from data/ldap-schema/ldapmigration/98obsolete.ldif
-- This module is a container for LDAP schema. It has no module identifier.
-- X- extension fields from the LDAP schema are comments. USAGE userApplications and structural KIND are omitted because they are the defaults.
-- 1 elements were omitted because their OIDs are already defined. See CONVERSION-REPORT.txt.
Ldapmigration98obsolete DEFINITIONS ::=
BEGIN

IMPORTS

  ATTRIBUTE, DistinguishedName
    FROM InformationFramework
      {joint-iso-itu-t ds(5) module(1) informationFramework(1) 9} WITH SUCCESSORS

  dn
    FROM SelectedAttributeTypes
      {joint-iso-itu-t ds(5) module(1) selectedAttributeTypes(5) 9} WITH SUCCESSORS ;

-- Object identifiers

id-at-passwordPolicySubentry OBJECT IDENTIFIER ::= { 1 3 6 1 4 1 42 2 27 9 1 30 }

-- Attribute types

-- X-DS-USE: "internal"
-- X-ORIGIN: "Password Policy for LDAP Directories Internet Draft"
passwordPolicySubentry ATTRIBUTE ::= {
  WITH SYNTAX               DistinguishedName
  SINGLE VALUE              TRUE
  USAGE                     directoryOperation
  LDAP-SYNTAX               dn.&id
  LDAP-NAME                 {"passwordPolicySubentry", "pwdPolicySubentry"}
  LDAP-DESC                 "Directory Server defined password policy attribute type"
  ID                        id-at-passwordPolicySubentry }
END
