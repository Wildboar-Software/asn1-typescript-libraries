-- These definitions are from Microsoft's Active Directory.
-- They were first gathered using the subschemaSubentry object of
-- Windows 2000 Advanced Server Release Candidate 2.
-- Additional definitions were gathered from Windows Server 2012
-- and adjusted to ease compatibility issues.
-- These object classes and attributes are rooted at OID
-- 1.2.840.113556.1, Microsoft's Directory Enabled networks
-- OID. OID Macros are used throughout, to make mapping of
-- incompatible OIDs easier.
-- A number of custom syntaxes have been replaced with generic
-- syntaxes. The original syntax OIDs are commented out below.
-- NO USER MODIFICATION is set on every attribute whose LDAP schema
-- specified NO-USER-MODIFICATION. The OpenLDAP source recorded that
-- keyword as a comment above the attribute.
-- Only the subset of Windows 2012 attributes needed to make the
-- user and group objectclasses work has been added to the previously
-- retrieved definitions.
-- If an AD definition clashes with existing standardized schema,
-- the AD definition has been commented out.
-- Converted from the OpenLDAP schema embedded in this module.
-- Commented-out attribute types and the container object class were not emitted. They clash with standardized schema, and references to those names import the existing attribute.
-- LDAP {length} bounds follow the ldap-schema conversion: directory strings use DirectoryString{n}; IA5String, PrintableString, NumericString, and OCTET STRING use SIZE (1..n).
-- 5 elements were kept even though an existing module uses their numeric OID under a different name.
MSUser {
    iso(1) identified-organization(3) dod(6) internet(1) private(4) enterprise(1) wildboar(56490) module(1) msuser(26)
}
DEFINITIONS
EXPLICIT TAGS
EXTENSIBILITY IMPLIED
::=
BEGIN

EXPORTS ALL;

IMPORTS

  ATTRIBUTE, DistinguishedName, OBJECT-CLASS, objectClass, top
    FROM InformationFramework
      {joint-iso-itu-t ds(5) module(1) informationFramework(1) 9} WITH SUCCESSORS

  boolean, businessCategory, commonName, description, directoryString,
    distinguishedName, dn, generalizedTime, givenName, ia5String, initials,
    integer, member, name, octetString, oid, organizationName, printableString,
    uid, UnboundedDirectoryString, uniqueIdentifier
    FROM SelectedAttributeTypes
      {joint-iso-itu-t ds(5) module(1) selectedAttributeTypes(5) 9} WITH SUCCESSORS

  organizationalPerson
    FROM SelectedObjectClasses
      {joint-iso-itu-t ds(5) module(1) selectedObjectClasses(6) 9} WITH SUCCESSORS

  userCertificate
    FROM AuthenticationFramework
      {joint-iso-itu-t ds(5) module(1) authenticationFramework(7) 9} WITH SUCCESSORS

  userSMIMECertificate
    FROM H323-X500-Schema
      {iso(1) identified-organization(3) dod(6) internet(1) private(4) enterprise(1) wildboar(56490) module(1) h323-x500-schema(1000)} WITH SUCCESSORS

  carLicense, departmentNumber, displayName, employeeNumber, employeeType,
    preferredLanguage
    FROM InetOrgPerson
      {iso(1) identified-organization(3) dod(6) internet(1) private(4) enterprise(1) wildboar(56490) module(1) inetorgperson(5)} WITH SUCCESSORS

  homeDirectory, nisMapName
    FROM NIS
      {iso(1) identified-organization(3) dod(6) internet(1) private(4) enterprise(1) wildboar(56490) module(1) nis(7)} WITH SUCCESSORS

  labeledURI
    FROM OpenLDAPCoreSchema
      {iso(1) identified-organization(3) dod(6) internet(1) private(4) enterprise(1) wildboar(56490) module(1) openldap-core(6)} WITH SUCCESSORS

  userPKCS12
    FROM PKCS-9
      {iso(1) member-body(2) us(840) rsadsi(113549) pkcs(1) pkcs-9(9) modules(0) pkcs-9(1)} WITH SUCCESSORS

  mail
    FROM LdapSchema2ldifCore

  audio, homePhone, homePostalAddress, manager, mobile, pager, photo,
    roomNumber, secretary
    FROM LdapSchema2ldifCosine

  jpegPhoto
    FROM LdapSchema2ldifInetorgperson ;

-- objectidentifier macros from the OpenLDAP schema

-- MicrosoftRoot = 1.2.840.113556
-- MSAD = 1.2.840.113556.1
-- MSADat2 = 1.2.840.113556.1.2
-- MSADat4 = 1.2.840.113556.1.4
-- MSADat6 = 1.2.840.113556.1.6
-- MSADcis = 1.3.6.1.4.1.1466.115.121.1.44
-- MSADdnWithOctetString = 1.3.6.1.4.1.1466.115.121.1.40
-- MSADdnWithString = 1.3.6.1.4.1.1466.115.121.1.40
-- MSADlargeInteger = 1.3.6.1.4.1.1466.115.121.1.27
-- MSADoc3 = 1.2.840.113556.1.3
-- MSADoc5 = 1.2.840.113556.1.5
-- MSADsecDesc = 1.3.6.1.4.1.1466.115.121.1.40
-- MSADtelex = 1.3.6.1.4.1.1466.115.121.1.44

-- Object identifiers

id-at-ownerBL OBJECT IDENTIFIER ::= { 1 2 840 113556 1 2 104 }
id-at-msCOM-PartitionSetLink OBJECT IDENTIFIER ::= { 1 2 840 113556 1 4 1424 }
id-at-msCOM-UserLink OBJECT IDENTIFIER ::= { 1 2 840 113556 1 4 1425 }
id-at-msDS-Approx-Immed-Subordinates OBJECT IDENTIFIER ::= { 1 2 840 113556 1 4 1669 }
id-at-msDS-NCReplCursors OBJECT IDENTIFIER ::= { 1 2 840 113556 1 4 1704 }
id-at-msDS-NCReplInboundNeighbors OBJECT IDENTIFIER ::= { 1 2 840 113556 1 4 1705 }
id-at-msDS-NCReplOutboundNeighbors OBJECT IDENTIFIER ::= { 1 2 840 113556 1 4 1706 }
id-at-msDS-ReplAttributeMetaData OBJECT IDENTIFIER ::= { 1 2 840 113556 1 4 1707 }
id-at-msDS-ReplValueMetaData OBJECT IDENTIFIER ::= { 1 2 840 113556 1 4 1708 }
id-at-msDS-NonMembers OBJECT IDENTIFIER ::= { 1 2 840 113556 1 4 1793 }
id-at-msDS-NonMembersBL OBJECT IDENTIFIER ::= { 1 2 840 113556 1 4 1794 }
id-at-msDS-MembersForAzRole OBJECT IDENTIFIER ::= { 1 2 840 113556 1 4 1806 }
id-at-msDS-MembersForAzRoleBL OBJECT IDENTIFIER ::= { 1 2 840 113556 1 4 1807 }
id-at-msDS-OperationsForAzTask OBJECT IDENTIFIER ::= { 1 2 840 113556 1 4 1808 }
id-at-msDS-OperationsForAzTaskBL OBJECT IDENTIFIER ::= { 1 2 840 113556 1 4 1809 }
id-at-msDS-TasksForAzTask OBJECT IDENTIFIER ::= { 1 2 840 113556 1 4 1810 }
id-at-msDS-TasksForAzTaskBL OBJECT IDENTIFIER ::= { 1 2 840 113556 1 4 1811 }
id-at-msDS-OperationsForAzRole OBJECT IDENTIFIER ::= { 1 2 840 113556 1 4 1812 }
id-at-msDS-OperationsForAzRoleBL OBJECT IDENTIFIER ::= { 1 2 840 113556 1 4 1813 }
id-at-msDS-TasksForAzRole OBJECT IDENTIFIER ::= { 1 2 840 113556 1 4 1814 }
id-at-msDS-TasksForAzRoleBL OBJECT IDENTIFIER ::= { 1 2 840 113556 1 4 1815 }
id-at-msDs-masteredBy OBJECT IDENTIFIER ::= { 1 2 840 113556 1 4 1837 }
id-at-msDS-ObjectReference OBJECT IDENTIFIER ::= { 1 2 840 113556 1 4 1840 }
id-at-msDS-ObjectReferenceBL OBJECT IDENTIFIER ::= { 1 2 840 113556 1 4 1841 }
id-at-msDS-PrincipalName OBJECT IDENTIFIER ::= { 1 2 840 113556 1 4 1865 }
id-at-msDS-RevealedDSAs OBJECT IDENTIFIER ::= { 1 2 840 113556 1 4 1930 }
id-at-msDS-KrbTgtLinkBl OBJECT IDENTIFIER ::= { 1 2 840 113556 1 4 1931 }
id-at-msDS-IsFullReplicaFor OBJECT IDENTIFIER ::= { 1 2 840 113556 1 4 1932 }
id-at-msDS-IsDomainFor OBJECT IDENTIFIER ::= { 1 2 840 113556 1 4 1933 }
id-at-msDS-IsPartialReplicaFor OBJECT IDENTIFIER ::= { 1 2 840 113556 1 4 1934 }
id-at-msDS-AuthenticatedToAccountlist OBJECT IDENTIFIER ::= { 1 2 840 113556 1 4 1957 }
id-at-msDS-AuthenticatedAtDC OBJECT IDENTIFIER ::= { 1 2 840 113556 1 4 1958 }
id-at-msDS-RevealedListBL OBJECT IDENTIFIER ::= { 1 2 840 113556 1 4 1975 }
id-at-msDS-NC-RO-Replica-Locations-BL OBJECT IDENTIFIER ::= { 1 2 840 113556 1 4 1968 }
id-at-msDS-PSOApplied OBJECT IDENTIFIER ::= { 1 2 840 113556 1 4 2021 }
id-at-msDS-NcType OBJECT IDENTIFIER ::= { 1 2 840 113556 1 4 2024 }
id-at-msDS-OIDToGroupLinkBl OBJECT IDENTIFIER ::= { 1 2 840 113556 1 4 2052 }
id-at-msDS-HostServiceAccountBL OBJECT IDENTIFIER ::= { 1 2 840 113556 1 4 2057 }
id-at-isRecycled OBJECT IDENTIFIER ::= { 1 2 840 113556 1 4 2058 }
id-at-msDS-LocalEffectiveDeletionTime OBJECT IDENTIFIER ::= { 1 2 840 113556 1 4 2059 }
id-at-msDS-LocalEffectiveRecycleTime OBJECT IDENTIFIER ::= { 1 2 840 113556 1 4 2060 }
id-at-msDS-LastKnownRDN OBJECT IDENTIFIER ::= { 1 2 840 113556 1 4 2067 }
id-at-msDS-EnabledFeatureBL OBJECT IDENTIFIER ::= { 1 2 840 113556 1 4 2069 }
id-at-msDS-ClaimSharesPossibleValuesWithBL OBJECT IDENTIFIER ::= { 1 2 840 113556 1 4 2102 }
id-at-msDS-MembersOfResourcePropertyListBL OBJECT IDENTIFIER ::= { 1 2 840 113556 1 4 2104 }
id-at-msDS-IsPrimaryComputerFor OBJECT IDENTIFIER ::= { 1 2 840 113556 1 4 2168 }
id-at-msDS-ValueTypeReferenceBL OBJECT IDENTIFIER ::= { 1 2 840 113556 1 4 2188 }
id-at-msDS-TDOIngressBL OBJECT IDENTIFIER ::= { 1 2 840 113556 1 4 2193 }
id-at-msDS-TDOEgressBL OBJECT IDENTIFIER ::= { 1 2 840 113556 1 4 2194 }
id-at-msDS-parentdistname OBJECT IDENTIFIER ::= { 1 2 840 113556 1 4 2203 }
id-at-msDS-ReplValueMetaDataExt OBJECT IDENTIFIER ::= { 1 2 840 113556 1 4 2235 }
id-at-msds-memberOfTransitive OBJECT IDENTIFIER ::= { 1 2 840 113556 1 4 2236 }
id-at-msds-memberTransitive OBJECT IDENTIFIER ::= { 1 2 840 113556 1 4 2238 }
id-at-msSFU30PosixMemberOf OBJECT IDENTIFIER ::= { 1 2 840 113556 1 6 18 1 347 }
id-at-msDFSR-MemberReferenceBL OBJECT IDENTIFIER ::= { 1 2 840 113556 1 6 13 3 102 }
id-at-msDFSR-ComputerReferenceBL OBJECT IDENTIFIER ::= { 1 2 840 113556 1 6 13 3 103 }
id-at-msDS-AzLDAPQuery OBJECT IDENTIFIER ::= { 1 2 840 113556 1 4 1792 }
id-at-msDS-AzBizRule OBJECT IDENTIFIER ::= { 1 2 840 113556 1 4 1801 }
id-at-msDS-AzBizRuleLanguage OBJECT IDENTIFIER ::= { 1 2 840 113556 1 4 1802 }
id-at-msDS-AzLastImportedBizRulePath OBJECT IDENTIFIER ::= { 1 2 840 113556 1 4 1803 }
id-at-msDS-AzApplicationData OBJECT IDENTIFIER ::= { 1 2 840 113556 1 4 1819 }
id-at-msDS-AzObjectGuid OBJECT IDENTIFIER ::= { 1 2 840 113556 1 4 1949 }
id-at-msDS-AzGenericData OBJECT IDENTIFIER ::= { 1 2 840 113556 1 4 1950 }
id-at-msDS-PrimaryComputer OBJECT IDENTIFIER ::= { 1 2 840 113556 1 4 2167 }
id-at-msSFU30Name OBJECT IDENTIFIER ::= { 1 2 840 113556 1 6 18 1 309 }
id-at-msSFU30NisDomain OBJECT IDENTIFIER ::= { 1 2 840 113556 1 6 18 1 339 }
id-at-msSFU30PosixMember OBJECT IDENTIFIER ::= { 1 2 840 113556 1 6 18 1 346 }
id-at-msCOM-UserPartitionSetLink OBJECT IDENTIFIER ::= { 1 2 840 113556 1 4 1426 }
id-at-msDS-Cached-Membership OBJECT IDENTIFIER ::= { 1 2 840 113556 1 4 1441 }
id-at-msDS-Cached-Membership-Time-Stamp OBJECT IDENTIFIER ::= { 1 2 840 113556 1 4 1442 }
id-at-msDS-Site-Affinity OBJECT IDENTIFIER ::= { 1 2 840 113556 1 4 1443 }
id-at-msDS-User-Account-Control-Computed OBJECT IDENTIFIER ::= { 1 2 840 113556 1 4 1460 }
id-at-lastLogonTimestamp OBJECT IDENTIFIER ::= { 1 2 840 113556 1 4 1696 }
id-at-msIIS-FTPRoot OBJECT IDENTIFIER ::= { 1 2 840 113556 1 4 1785 }
id-at-msIIS-FTPDir OBJECT IDENTIFIER ::= { 1 2 840 113556 1 4 1786 }
id-at-msDRM-IdentityCertificate OBJECT IDENTIFIER ::= { 1 2 840 113556 1 4 1843 }
id-at-msDS-SourceObjectDN OBJECT IDENTIFIER ::= { 1 2 840 113556 1 4 1879 }
id-at-msPKIRoamingTimeStamp OBJECT IDENTIFIER ::= { 1 2 840 113556 1 4 1892 }
id-at-msPKIDPAPIMasterKeys OBJECT IDENTIFIER ::= { 1 2 840 113556 1 4 1893 }
id-at-msPKIAccountCredentials OBJECT IDENTIFIER ::= { 1 2 840 113556 1 4 1894 }
id-at-msRADIUS-FramedInterfaceId OBJECT IDENTIFIER ::= { 1 2 840 113556 1 4 1913 }
id-at-msRADIUS-SavedFramedInterfaceId OBJECT IDENTIFIER ::= { 1 2 840 113556 1 4 1914 }
id-at-msRADIUS-FramedIpv6Prefix OBJECT IDENTIFIER ::= { 1 2 840 113556 1 4 1915 }
id-at-msRADIUS-SavedFramedIpv6Prefix OBJECT IDENTIFIER ::= { 1 2 840 113556 1 4 1916 }
id-at-msRADIUS-FramedIpv6Route OBJECT IDENTIFIER ::= { 1 2 840 113556 1 4 1917 }
id-at-msRADIUS-SavedFramedIpv6Route OBJECT IDENTIFIER ::= { 1 2 840 113556 1 4 1918 }
id-at-msDS-SecondaryKrbTgtNumber OBJECT IDENTIFIER ::= { 1 2 840 113556 1 4 1929 }
id-at-msDS-SupportedEncryptionTypes OBJECT IDENTIFIER ::= { 1 2 840 113556 1 4 1963 }
id-at-msDS-LastSuccessfulInteractiveLogonTime OBJECT IDENTIFIER ::= { 1 2 840 113556 1 4 1970 }
id-at-msDS-LastFailedInteractiveLogonTime OBJECT IDENTIFIER ::= { 1 2 840 113556 1 4 1971 }
id-at-msDS-FailedInteractiveLogonCount OBJECT IDENTIFIER ::= { 1 2 840 113556 1 4 1972 }
id-at-msDS-FailedInteractiveLogonCountAtLastSuccessfulLogon OBJECT IDENTIFIER ::= { 1 2 840 113556 1 4 1973 }
id-at-msTSProfilePath OBJECT IDENTIFIER ::= { 1 2 840 113556 1 4 1976 }
id-at-msTSHomeDirectory OBJECT IDENTIFIER ::= { 1 2 840 113556 1 4 1977 }
id-at-msTSHomeDrive OBJECT IDENTIFIER ::= { 1 2 840 113556 1 4 1978 }
id-at-msTSAllowLogon OBJECT IDENTIFIER ::= { 1 2 840 113556 1 4 1979 }
id-at-msTSRemoteControl OBJECT IDENTIFIER ::= { 1 2 840 113556 1 4 1980 }
id-at-msTSMaxDisconnectionTime OBJECT IDENTIFIER ::= { 1 2 840 113556 1 4 1981 }
id-at-msTSMaxConnectionTime OBJECT IDENTIFIER ::= { 1 2 840 113556 1 4 1982 }
id-at-msTSMaxIdleTime OBJECT IDENTIFIER ::= { 1 2 840 113556 1 4 1983 }
id-at-msTSReconnectionAction OBJECT IDENTIFIER ::= { 1 2 840 113556 1 4 1984 }
id-at-msTSBrokenConnectionAction OBJECT IDENTIFIER ::= { 1 2 840 113556 1 4 1985 }
id-at-msTSConnectClientDrives OBJECT IDENTIFIER ::= { 1 2 840 113556 1 4 1986 }
id-at-msTSConnectPrinterDrives OBJECT IDENTIFIER ::= { 1 2 840 113556 1 4 1987 }
id-at-msTSDefaultToMainPrinter OBJECT IDENTIFIER ::= { 1 2 840 113556 1 4 1988 }
id-at-msTSWorkDirectory OBJECT IDENTIFIER ::= { 1 2 840 113556 1 4 1989 }
id-at-msTSInitialProgram OBJECT IDENTIFIER ::= { 1 2 840 113556 1 4 1990 }
id-at-msTSProperty01 OBJECT IDENTIFIER ::= { 1 2 840 113556 1 4 1991 }
id-at-msTSProperty02 OBJECT IDENTIFIER ::= { 1 2 840 113556 1 4 1992 }
id-at-msTSExpireDate OBJECT IDENTIFIER ::= { 1 2 840 113556 1 4 1993 }
id-at-msTSLicenseVersion OBJECT IDENTIFIER ::= { 1 2 840 113556 1 4 1994 }
id-at-msTSManagingLS OBJECT IDENTIFIER ::= { 1 2 840 113556 1 4 1995 }
id-at-msDS-UserPasswordExpiryTimeComputed OBJECT IDENTIFIER ::= { 1 2 840 113556 1 4 1996 }
id-at-msTSManagingLS4 OBJECT IDENTIFIER ::= { 1 2 840 113556 1 4 2008 }
id-at-msTSManagingLS3 OBJECT IDENTIFIER ::= { 1 2 840 113556 1 4 2005 }
id-at-msTSManagingLS2 OBJECT IDENTIFIER ::= { 1 2 840 113556 1 4 2002 }
id-at-msTSExpireDate4 OBJECT IDENTIFIER ::= { 1 2 840 113556 1 4 2006 }
id-at-msTSExpireDate3 OBJECT IDENTIFIER ::= { 1 2 840 113556 1 4 2003 }
id-at-msTSExpireDate2 OBJECT IDENTIFIER ::= { 1 2 840 113556 1 4 2000 }
id-at-msTSLicenseVersion3 OBJECT IDENTIFIER ::= { 1 2 840 113556 1 4 2004 }
id-at-msTSLicenseVersion2 OBJECT IDENTIFIER ::= { 1 2 840 113556 1 4 2001 }
id-at-msTSLicenseVersion4 OBJECT IDENTIFIER ::= { 1 2 840 113556 1 4 2007 }
id-at-msTSLSProperty01 OBJECT IDENTIFIER ::= { 1 2 840 113556 1 4 2009 }
id-at-msTSLSProperty02 OBJECT IDENTIFIER ::= { 1 2 840 113556 1 4 2010 }
id-at-msDS-ResultantPSO OBJECT IDENTIFIER ::= { 1 2 840 113556 1 4 2022 }
id-at-msPKI-CredentialRoamingTokens OBJECT IDENTIFIER ::= { 1 2 840 113556 1 4 2050 }
id-at-msTSPrimaryDesktop OBJECT IDENTIFIER ::= { 1 2 840 113556 1 4 2073 }
id-at-msTSSecondaryDesktops OBJECT IDENTIFIER ::= { 1 2 840 113556 1 4 2075 }
id-at-msDS-SyncServerUrl OBJECT IDENTIFIER ::= { 1 2 840 113556 1 4 2276 }
id-at-msDS-AssignedAuthNPolicySilo OBJECT IDENTIFIER ::= { 1 2 840 113556 1 4 2285 }
id-at-msDS-AuthNPolicySiloMembersBL OBJECT IDENTIFIER ::= { 1 2 840 113556 1 4 2288 }
id-at-msDS-AssignedAuthNPolicy OBJECT IDENTIFIER ::= { 1 2 840 113556 1 4 2295 }
id-at-msDS-AdditionalDnsHostName OBJECT IDENTIFIER ::= { 1 2 840 113556 1 4 1717 }
id-at-msDS-AdditionalSamAccountName OBJECT IDENTIFIER ::= { 1 2 840 113556 1 4 1718 }
id-at-msDS-ExecuteScriptPassword OBJECT IDENTIFIER ::= { 1 2 840 113556 1 4 1783 }
id-at-msDS-KrbTgtLink OBJECT IDENTIFIER ::= { 1 2 840 113556 1 4 1923 }
id-at-msDS-RevealedUsers OBJECT IDENTIFIER ::= { 1 2 840 113556 1 4 1924 }
id-at-msDS-NeverRevealGroup OBJECT IDENTIFIER ::= { 1 2 840 113556 1 4 1926 }
id-at-msDS-RevealOnDemandGroup OBJECT IDENTIFIER ::= { 1 2 840 113556 1 4 1928 }
id-at-msDS-RevealedList OBJECT IDENTIFIER ::= { 1 2 840 113556 1 4 1940 }
id-at-msDS-isGC OBJECT IDENTIFIER ::= { 1 2 840 113556 1 4 1959 }
id-at-msDS-isRODC OBJECT IDENTIFIER ::= { 1 2 840 113556 1 4 1960 }
id-at-msDS-SiteName OBJECT IDENTIFIER ::= { 1 2 840 113556 1 4 1961 }
id-at-msDS-PromotionSettings OBJECT IDENTIFIER ::= { 1 2 840 113556 1 4 1962 }
id-at-msTPM-OwnerInformation OBJECT IDENTIFIER ::= { 1 2 840 113556 1 4 1966 }
id-at-msDS-IsUserCachableAtRodc OBJECT IDENTIFIER ::= { 1 2 840 113556 1 4 2025 }
id-at-msDS-HostServiceAccount OBJECT IDENTIFIER ::= { 1 2 840 113556 1 4 2056 }
id-at-msTSEndpointData OBJECT IDENTIFIER ::= { 1 2 840 113556 1 4 2070 }
id-at-msTSEndpointType OBJECT IDENTIFIER ::= { 1 2 840 113556 1 4 2071 }
id-at-msTSEndpointPlugin OBJECT IDENTIFIER ::= { 1 2 840 113556 1 4 2072 }
id-at-msTSPrimaryDesktopBL OBJECT IDENTIFIER ::= { 1 2 840 113556 1 4 2074 }
id-at-msTSSecondaryDesktopBL OBJECT IDENTIFIER ::= { 1 2 840 113556 1 4 2078 }
id-at-msTPM-TpmInformationForComputer OBJECT IDENTIFIER ::= { 1 2 840 113556 1 4 2109 }
id-at-msDS-GenerationId OBJECT IDENTIFIER ::= { 1 2 840 113556 1 4 2166 }
id-at-msImaging-ThumbprintHash OBJECT IDENTIFIER ::= { 1 2 840 113556 1 4 2180 }
id-at-msImaging-HashAlgorithm OBJECT IDENTIFIER ::= { 1 2 840 113556 1 4 2181 }
id-at-netbootDUID OBJECT IDENTIFIER ::= { 1 2 840 113556 1 4 2234 }
id-at-msSFU30Aliases OBJECT IDENTIFIER ::= { 1 2 840 113556 1 6 18 1 323 }
id-at-netbootNewMachineOU OBJECT IDENTIFIER ::= { 1 2 840 113556 1 4 856 }
id-at-builtinCreationTime OBJECT IDENTIFIER ::= { 1 2 840 113556 1 4 13 }
id-at-pKIEnrollmentAccess OBJECT IDENTIFIER ::= { 1 2 840 113556 1 4 1335 }
id-at-pKIExtendedKeyUsage OBJECT IDENTIFIER ::= { 1 2 840 113556 1 4 1333 }
id-at-msNPCalledStationID OBJECT IDENTIFIER ::= { 1 2 840 113556 1 4 1123 }
id-at-initialAuthIncoming OBJECT IDENTIFIER ::= { 1 2 840 113556 1 4 539 }
id-at-objectClassCategory OBJECT IDENTIFIER ::= { 1 2 840 113556 1 2 370 }
id-at-generatedConnection OBJECT IDENTIFIER ::= { 1 2 840 113556 1 4 41 }
id-at-allowedChildClasses OBJECT IDENTIFIER ::= { 1 2 840 113556 1 4 911 }
id-at-machineArchitecture OBJECT IDENTIFIER ::= { 1 2 840 113556 1 4 68 }
id-at-aCSMaxPeakBandwidth OBJECT IDENTIFIER ::= { 1 2 840 113556 1 4 767 }
id-at-marshalledInterface OBJECT IDENTIFIER ::= { 1 2 840 113556 1 4 72 }
id-at-rIDManagerReference OBJECT IDENTIFIER ::= { 1 2 840 113556 1 4 368 }
id-at-aCSEnableACSService OBJECT IDENTIFIER ::= { 1 2 840 113556 1 4 770 }
id-at-mSMQRoutingService OBJECT IDENTIFIER ::= { 1 2 840 113556 1 4 1237 }
id-at-mS-SQL-AllowQueuedUpdatingSubscription OBJECT IDENTIFIER ::= { 1 2 840 113556 1 4 1405 }
id-at-primaryTelexNumber OBJECT IDENTIFIER ::= { 1 2 840 113556 1 4 648 }
id-at-userAccountControl OBJECT IDENTIFIER ::= { 1 2 840 113556 1 4 8 }
id-at-shellPropertyPages OBJECT IDENTIFIER ::= { 1 2 840 113556 1 4 563 }
id-at-replUpToDateVector OBJECT IDENTIFIER ::= { 1 2 840 113556 1 4 4 }
-- OID 1.2.840.113556.1.4.484 is also used by calOtherCAPURIs in RFC2739Calendar. The LDAP names differ, so this definition was kept.
id-at-fRSDirectoryFilter OBJECT IDENTIFIER ::= { 1 2 840 113556 1 4 484 }
id-at-printSeparatorFile OBJECT IDENTIFIER ::= { 1 2 840 113556 1 4 230 }
id-at-pKIMaxIssuingDepth OBJECT IDENTIFIER ::= { 1 2 840 113556 1 4 1329 }
id-at-accountNameHistory OBJECT IDENTIFIER ::= { 1 2 840 113556 1 4 1307 }
id-at-mS-SQL-GPSLongitude OBJECT IDENTIFIER ::= { 1 2 840 113556 1 4 1386 }
id-at-adminPropertyPages OBJECT IDENTIFIER ::= { 1 2 840 113556 1 4 562 }
id-at-securityIdentifier OBJECT IDENTIFIER ::= { 1 2 840 113556 1 4 121 }
id-at-groupMembershipSAM OBJECT IDENTIFIER ::= { 1 2 840 113556 1 4 166 }
id-at-serviceDNSNameType OBJECT IDENTIFIER ::= { 1 2 840 113556 1 4 659 }
id-at-meetingIsEncrypted OBJECT IDENTIFIER ::= { 1 2 840 113556 1 4 585 }
id-at-mS-SQL-Applications OBJECT IDENTIFIER ::= { 1 2 840 113556 1 4 1400 }
id-at-lastUpdateSequence OBJECT IDENTIFIER ::= { 1 2 840 113556 1 4 330 }
id-at-lastContentIndexed OBJECT IDENTIFIER ::= { 1 2 840 113556 1 4 50 }
id-at-meetingDescription OBJECT IDENTIFIER ::= { 1 2 840 113556 1 4 567 }
id-at-monikerDisplayName OBJECT IDENTIFIER ::= { 1 2 840 113556 1 4 83 }
id-at-requiredCategories OBJECT IDENTIFIER ::= { 1 2 840 113556 1 4 321 }
id-at-upgradeProductCode OBJECT IDENTIFIER ::= { 1 2 840 113556 1 4 813 }
id-at-aCSMaxNoOfLogFiles OBJECT IDENTIFIER ::= { 1 2 840 113556 1 4 774 }
id-at-mS-SQL-CharacterSet OBJECT IDENTIFIER ::= { 1 2 840 113556 1 4 1370 }
id-at-meetingContactInfo OBJECT IDENTIFIER ::= { 1 2 840 113556 1 4 578 }
id-at-mS-SQL-CreationDate OBJECT IDENTIFIER ::= { 1 2 840 113556 1 4 1397 }
id-at-domainPolicyObject OBJECT IDENTIFIER ::= { 1 2 840 113556 1 4 32 }
id-at-dhcpObjDescription OBJECT IDENTIFIER ::= { 1 2 840 113556 1 4 703 }
id-at-meetingApplication OBJECT IDENTIFIER ::= { 1 2 840 113556 1 4 573 }
id-at-defaultHidingValue OBJECT IDENTIFIER ::= { 1 2 840 113556 1 4 518 }
id-at-fRSMemberReference OBJECT IDENTIFIER ::= { 1 2 840 113556 1 4 875 }
id-at-dhcpIdentification OBJECT IDENTIFIER ::= { 1 2 840 113556 1 4 701 }
id-at-trustAuthOutgoing OBJECT IDENTIFIER ::= { 1 2 840 113556 1 4 135 }
id-at-systemMustContain OBJECT IDENTIFIER ::= { 1 2 840 113556 1 4 197 }
id-at-primaryGroupToken OBJECT IDENTIFIER ::= { 1 2 840 113556 1 4 1412 }
id-at-rpcNsProfileEntry OBJECT IDENTIFIER ::= { 1 2 840 113556 1 4 118 }
id-at-trustAuthIncoming OBJECT IDENTIFIER ::= { 1 2 840 113556 1 4 129 }
id-at-mSMQPrevSiteGates OBJECT IDENTIFIER ::= { 1 2 840 113556 1 4 1225 }
id-at-queryPolicyObject OBJECT IDENTIFIER ::= { 1 2 840 113556 1 4 607 }
id-at-optionDescription OBJECT IDENTIFIER ::= { 1 2 840 113556 1 4 712 }
id-at-aCSMaximumSDUSize OBJECT IDENTIFIER ::= { 1 2 840 113556 1 4 1314 }
id-at-nonSecurityMember OBJECT IDENTIFIER ::= { 1 2 840 113556 1 4 530 }
id-at-fRSReplicaSetType OBJECT IDENTIFIER ::= { 1 2 840 113556 1 4 31 }
id-at-aCSTotalNoOfFlows OBJECT IDENTIFIER ::= { 1 2 840 113556 1 4 763 }
id-at-possibleInferiors OBJECT IDENTIFIER ::= { 1 2 840 113556 1 4 915 }
id-at-netbootMaxClients OBJECT IDENTIFIER ::= { 1 2 840 113556 1 4 851 }
id-at-mS-SQL-GPSLatitude OBJECT IDENTIFIER ::= { 1 2 840 113556 1 4 1385 }
id-at-aCSPermissionBits OBJECT IDENTIFIER ::= { 1 2 840 113556 1 4 765 }
id-at-mSMQTransactional OBJECT IDENTIFIER ::= { 1 2 840 113556 1 4 926 }
id-at-mS-SQL-Description OBJECT IDENTIFIER ::= { 1 2 840 113556 1 4 1390 }
id-at-allowedAttributes OBJECT IDENTIFIER ::= { 1 2 840 113556 1 4 913 }
id-at-fRSFaultCondition OBJECT IDENTIFIER ::= { 1 2 840 113556 1 4 491 }
id-at-tombstoneLifetime OBJECT IDENTIFIER ::= { 1 2 840 113556 1 2 54 }
id-at-remoteStorageGUID OBJECT IDENTIFIER ::= { 1 2 840 113556 1 4 809 }
id-at-showInAddressBook OBJECT IDENTIFIER ::= { 1 2 840 113556 1 4 644 }
id-at-defaultClassStore OBJECT IDENTIFIER ::= { 1 2 840 113556 1 4 213 }
id-at-meetingOriginator OBJECT IDENTIFIER ::= { 1 2 840 113556 1 4 577 }
id-at-userPrincipalName OBJECT IDENTIFIER ::= { 1 2 840 113556 1 4 656 }
id-at-aCSMinimumLatency OBJECT IDENTIFIER ::= { 1 2 840 113556 1 4 1316 }
id-at-isPrivilegeHolder OBJECT IDENTIFIER ::= { 1 2 840 113556 1 4 638 }
id-at-fRSReplicaSetGUID OBJECT IDENTIFIER ::= { 1 2 840 113556 1 4 533 }
id-at-rIDAllocationPool OBJECT IDENTIFIER ::= { 1 2 840 113556 1 4 371 }
id-at-pKIDefaultKeySpec OBJECT IDENTIFIER ::= { 1 2 840 113556 1 4 1327 }
id-at-dynamicLDAPServer OBJECT IDENTIFIER ::= { 1 2 840 113556 1 4 537 }
id-at-serverReferenceBL OBJECT IDENTIFIER ::= { 1 2 840 113556 1 4 516 }
id-at-fRSServiceCommand OBJECT IDENTIFIER ::= { 1 2 840 113556 1 4 500 }
id-at-sDRightsEffective OBJECT IDENTIFIER ::= { 1 2 840 113556 1 4 1304 }
id-at-proxiedObjectName OBJECT IDENTIFIER ::= { 1 2 840 113556 1 4 1249 }
id-at-meetingRecurrence OBJECT IDENTIFIER ::= { 1 2 840 113556 1 4 586 }
id-at-cOMTreatAsClassId OBJECT IDENTIFIER ::= { 1 2 840 113556 1 4 251 }
id-at-globalAddressList OBJECT IDENTIFIER ::= { 1 2 840 113556 1 4 1245 }
id-at-extendedClassInfo OBJECT IDENTIFIER ::= { 1 2 840 113556 1 4 908 }
id-at-machineWidePolicy OBJECT IDENTIFIER ::= { 1 2 840 113556 1 4 459 }
id-at-foreignIdentifier OBJECT IDENTIFIER ::= { 1 2 840 113556 1 4 356 }
id-at-dNReferenceUpdate OBJECT IDENTIFIER ::= { 1 2 840 113556 1 4 1242 }
id-at-trustPosixOffset OBJECT IDENTIFIER ::= { 1 2 840 113556 1 4 134 }
id-at-enabledConnection OBJECT IDENTIFIER ::= { 1 2 840 113556 1 4 36 }
id-at-ipsecNFAReference OBJECT IDENTIFIER ::= { 1 2 840 113556 1 4 627 }
id-at-userWorkstations OBJECT IDENTIFIER ::= { 1 2 840 113556 1 4 86 }
id-at-garbageCollPeriod OBJECT IDENTIFIER ::= { 1 2 840 113556 1 2 301 }
id-at-mSMQComputerType OBJECT IDENTIFIER ::= { 1 2 840 113556 1 4 933 }
id-at-logonWorkstation OBJECT IDENTIFIER ::= { 1 2 840 113556 1 4 65 }
id-at-mSMQJournalQuota OBJECT IDENTIFIER ::= { 1 2 840 113556 1 4 921 }
id-at-remoteSourceType OBJECT IDENTIFIER ::= { 1 2 840 113556 1 4 108 }
id-at-pwdHistoryLength OBJECT IDENTIFIER ::= { 1 2 840 113556 1 4 95 }
id-at-mSMQBasePriority OBJECT IDENTIFIER ::= { 1 2 840 113556 1 4 920 }
id-at-systemMayContain OBJECT IDENTIFIER ::= { 1 2 840 113556 1 4 196 }
id-at-mS-SQL-ThirdParty OBJECT IDENTIFIER ::= { 1 2 840 113556 1 4 1407 }
id-at-mSMQQueueNameExt OBJECT IDENTIFIER ::= { 1 2 840 113556 1 4 1243 }
-- OID 1.2.840.113556.1.4.485 is also used by calOtherCalAdrURIs in RFC2739Calendar. The LDAP names differ, so this definition was kept.
id-at-fRSUpdateTimeout OBJECT IDENTIFIER ::= { 1 2 840 113556 1 4 485 }
id-at-mSMQPrivacyLevel OBJECT IDENTIFIER ::= { 1 2 840 113556 1 4 924 }
id-at-shellContextMenu OBJECT IDENTIFIER ::= { 1 2 840 113556 1 4 615 }
id-at-wellKnownObjects OBJECT IDENTIFIER ::= { 1 2 840 113556 1 4 618 }
id-at-transportDLLName OBJECT IDENTIFIER ::= { 1 2 840 113556 1 4 789 }
id-at-qualityOfService OBJECT IDENTIFIER ::= { 1 2 840 113556 1 4 458 }
id-at-lockoutThreshold OBJECT IDENTIFIER ::= { 1 2 840 113556 1 4 73 }
id-at-remoteServerName OBJECT IDENTIFIER ::= { 1 2 840 113556 1 4 105 }
id-at-previousParentCA OBJECT IDENTIFIER ::= { 1 2 840 113556 1 4 694 }
id-at-dSUIShellMaximum OBJECT IDENTIFIER ::= { 1 2 840 113556 1 4 1345 }
id-at-notificationList OBJECT IDENTIFIER ::= { 1 2 840 113556 1 4 303 }
id-at-addressBookRoots OBJECT IDENTIFIER ::= { 1 2 840 113556 1 4 1244 }
id-at-fRSPrimaryMember OBJECT IDENTIFIER ::= { 1 2 840 113556 1 4 878 }
id-at-mSMQSiteGatesMig OBJECT IDENTIFIER ::= { 1 2 840 113556 1 4 1310 }
id-at-dhcpReservations OBJECT IDENTIFIER ::= { 1 2 840 113556 1 4 709 }
id-at-adminContextMenu OBJECT IDENTIFIER ::= { 1 2 840 113556 1 4 614 }
id-at-pKIOverlapPeriod OBJECT IDENTIFIER ::= { 1 2 840 113556 1 4 1332 }
id-at-winsockAddresses OBJECT IDENTIFIER ::= { 1 2 840 113556 1 4 142 }
id-at-mSMQAuthenticate OBJECT IDENTIFIER ::= { 1 2 840 113556 1 4 923 }
id-at-dSUIAdminMaximum OBJECT IDENTIFIER ::= { 1 2 840 113556 1 4 1344 }
id-at-appSchemaVersion OBJECT IDENTIFIER ::= { 1 2 840 113556 1 4 848 }
id-at-serviceClassInfo OBJECT IDENTIFIER ::= { 1 2 840 113556 1 4 123 }
id-at-aCSEventLogLevel OBJECT IDENTIFIER ::= { 1 2 840 113556 1 4 769 }
id-at-userSharedFolder OBJECT IDENTIFIER ::= { 1 2 840 113556 1 4 751 }
id-at-domainWidePolicy OBJECT IDENTIFIER ::= { 1 2 840 113556 1 4 421 }
id-at-rIDSetReferences OBJECT IDENTIFIER ::= { 1 2 840 113556 1 4 669 }
id-at-canUpgradeScript OBJECT IDENTIFIER ::= { 1 2 840 113556 1 4 815 }
id-at-classDisplayName OBJECT IDENTIFIER ::= { 1 2 840 113556 1 4 610 }
id-at-adminDescription OBJECT IDENTIFIER ::= { 1 2 840 113556 1 2 226 }
id-at-lSAModifiedCount OBJECT IDENTIFIER ::= { 1 2 840 113556 1 4 67 }
id-at-serviceClassName OBJECT IDENTIFIER ::= { 1 2 840 113556 1 4 509 }
id-at-localPolicyFlags OBJECT IDENTIFIER ::= { 1 2 840 113556 1 4 56 }
id-at-rpcNsInterfaceID OBJECT IDENTIFIER ::= { 1 2 840 113556 1 4 115 }
id-at-adminDisplayName OBJECT IDENTIFIER ::= { 1 2 840 113556 1 2 194 }
id-at-nameServiceFlags OBJECT IDENTIFIER ::= { 1 2 840 113556 1 4 753 }
id-at-meetingBandwidth OBJECT IDENTIFIER ::= { 1 2 840 113556 1 4 589 }
id-at-domainIdentifier OBJECT IDENTIFIER ::= { 1 2 840 113556 1 4 755 }
id-at-rIDAvailablePool OBJECT IDENTIFIER ::= { 1 2 840 113556 1 4 370 }
id-at-legacyExchangeDN OBJECT IDENTIFIER ::= { 1 2 840 113556 1 4 655 }
id-at-trustAttributes OBJECT IDENTIFIER ::= { 1 2 840 113556 1 4 470 }
id-at-fRSRootSecurity OBJECT IDENTIFIER ::= { 1 2 840 113556 1 4 535 }
id-at-superiorDNSRoot OBJECT IDENTIFIER ::= { 1 2 840 113556 1 4 532 }
id-at-printMaxYExtent OBJECT IDENTIFIER ::= { 1 2 840 113556 1 4 278 }
id-at-printMaxXExtent OBJECT IDENTIFIER ::= { 1 2 840 113556 1 4 277 }
id-at-printMinYExtent OBJECT IDENTIFIER ::= { 1 2 840 113556 1 4 280 }
id-at-printMinXExtent OBJECT IDENTIFIER ::= { 1 2 840 113556 1 4 279 }
id-at-attributeSyntax OBJECT IDENTIFIER ::= { 1 2 840 113556 1 2 32 }
id-at-printAttributes OBJECT IDENTIFIER ::= { 1 2 840 113556 1 4 247 }
id-at-groupAttributes OBJECT IDENTIFIER ::= { 1 2 840 113556 1 4 152 }
id-at-fileExtPriority OBJECT IDENTIFIER ::= { 1 2 840 113556 1 4 816 }
id-at-mSMQServiceType OBJECT IDENTIFIER ::= { 1 2 840 113556 1 4 930 }
id-at-operatingSystem OBJECT IDENTIFIER ::= { 1 2 840 113556 1 4 363 }
id-at-mS-SQL-SortOrder OBJECT IDENTIFIER ::= { 1 2 840 113556 1 4 1371 }
id-at-versionNumberLo OBJECT IDENTIFIER ::= { 1 2 840 113556 1 4 329 }
id-at-msRRASAttribute OBJECT IDENTIFIER ::= { 1 2 840 113556 1 4 884 }
id-at-lastKnownParent OBJECT IDENTIFIER ::= { 1 2 840 113556 1 4 781 }
id-at-shortServerName OBJECT IDENTIFIER ::= { 1 2 840 113556 1 4 1209 }
id-at-lockoutDuration OBJECT IDENTIFIER ::= { 1 2 840 113556 1 4 60 }
id-at-defaultPriority OBJECT IDENTIFIER ::= { 1 2 840 113556 1 4 232 }
id-at-rpcNsEntryFlags OBJECT IDENTIFIER ::= { 1 2 840 113556 1 4 754 }
id-at-optionsLocation OBJECT IDENTIFIER ::= { 1 2 840 113556 1 4 713 }
id-at-versionNumberHi OBJECT IDENTIFIER ::= { 1 2 840 113556 1 4 328 }
id-at-rpcNsAnnotation OBJECT IDENTIFIER ::= { 1 2 840 113556 1 4 366 }
id-at-purportedSearch OBJECT IDENTIFIER ::= { 1 2 840 113556 1 4 886 }
id-at-aCSDSBMPriority OBJECT IDENTIFIER ::= { 1 2 840 113556 1 4 776 }
id-at-mSMQSiteForeign OBJECT IDENTIFIER ::= { 1 2 840 113556 1 4 961 }
id-at-currentLocation OBJECT IDENTIFIER ::= { 1 2 840 113556 1 4 335 }
id-at-meetingProtocol OBJECT IDENTIFIER ::= { 1 2 840 113556 1 4 570 }
id-at-publicKeyPolicy OBJECT IDENTIFIER ::= { 1 2 840 113556 1 4 420 }
id-at-mS-SQL-Publisher OBJECT IDENTIFIER ::= { 1 2 840 113556 1 4 1402 }
id-at-createWizardExt OBJECT IDENTIFIER ::= { 1 2 840 113556 1 4 812 }
id-at-mS-SQL-Clustered OBJECT IDENTIFIER ::= { 1 2 840 113556 1 4 1373 }
id-at-volTableIdxGUID OBJECT IDENTIFIER ::= { 1 2 840 113556 1 4 334 }
id-at-currentParentCA OBJECT IDENTIFIER ::= { 1 2 840 113556 1 4 696 }
id-at-seqNotification OBJECT IDENTIFIER ::= { 1 2 840 113556 1 4 504 }
id-at-serverReference OBJECT IDENTIFIER ::= { 1 2 840 113556 1 4 515 }
id-at-msNPAllowDialin OBJECT IDENTIFIER ::= { 1 2 840 113556 1 4 1119 }
id-at-mS-SQL-GPSHeight OBJECT IDENTIFIER ::= { 1 2 840 113556 1 4 1387 }
id-at-mS-SQL-AppleTalk OBJECT IDENTIFIER ::= { 1 2 840 113556 1 4 1378 }
id-at-linkTrackSecret OBJECT IDENTIFIER ::= { 1 2 840 113556 1 4 269 }
id-at-dnsAllowDynamic OBJECT IDENTIFIER ::= { 1 2 840 113556 1 4 378 }
id-at-badPasswordTime OBJECT IDENTIFIER ::= { 1 2 840 113556 1 4 49 }
id-at-privilegeHolder OBJECT IDENTIFIER ::= { 1 2 840 113556 1 4 637 }
id-at-printMediaReady OBJECT IDENTIFIER ::= { 1 2 840 113556 1 4 289 }
id-at-printMACAddress OBJECT IDENTIFIER ::= { 1 2 840 113556 1 4 288 }
id-at-lSACreationTime OBJECT IDENTIFIER ::= { 1 2 840 113556 1 4 66 }
id-at-meetingLocation OBJECT IDENTIFIER ::= { 1 2 840 113556 1 4 569 }
id-at-aCSIdentityName OBJECT IDENTIFIER ::= { 1 2 840 113556 1 4 784 }
id-at-mS-DS-CreatorSID OBJECT IDENTIFIER ::= { 1 2 840 113556 1 4 1410 }
id-at-mS-SQL-NamedPipe OBJECT IDENTIFIER ::= { 1 2 840 113556 1 4 1374 }
id-at-lDAPAdminLimits OBJECT IDENTIFIER ::= { 1 2 840 113556 1 4 843 }
id-at-lDAPDisplayName OBJECT IDENTIFIER ::= { 1 2 840 113556 1 2 460 }
id-at-applicationName OBJECT IDENTIFIER ::= { 1 2 840 113556 1 4 218 }
id-at-pendingParentCA OBJECT IDENTIFIER ::= { 1 2 840 113556 1 4 695 }
id-at-aCSCacheTimeout OBJECT IDENTIFIER ::= { 1 2 840 113556 1 4 779 }
id-at-meetingLanguage OBJECT IDENTIFIER ::= { 1 2 840 113556 1 4 574 }
id-at-aCSDSBMDeadTime OBJECT IDENTIFIER ::= { 1 2 840 113556 1 4 778 }
id-at-cACertificateDN OBJECT IDENTIFIER ::= { 1 2 840 113556 1 4 697 }
id-at-userParameters OBJECT IDENTIFIER ::= { 1 2 840 113556 1 4 138 }
id-at-trustDirection OBJECT IDENTIFIER ::= { 1 2 840 113556 1 4 132 }
id-at-mSMQQueueQuota OBJECT IDENTIFIER ::= { 1 2 840 113556 1 4 962 }
id-at-mSMQEncryptKey OBJECT IDENTIFIER ::= { 1 2 840 113556 1 4 936 }
id-at-terminalServer OBJECT IDENTIFIER ::= { 1 2 840 113556 1 4 885 }
id-at-printStartTime OBJECT IDENTIFIER ::= { 1 2 840 113556 1 4 233 }
id-at-syncWithObject OBJECT IDENTIFIER ::= { 1 2 840 113556 1 4 664 }
id-at-groupsToIgnore OBJECT IDENTIFIER ::= { 1 2 840 113556 1 4 344 }
id-at-syncMembership OBJECT IDENTIFIER ::= { 1 2 840 113556 1 4 665 }
id-at-syncAttributes OBJECT IDENTIFIER ::= { 1 2 840 113556 1 4 666 }
id-at-nextLevelStore OBJECT IDENTIFIER ::= { 1 2 840 113556 1 4 214 }
id-at-sAMAccountType OBJECT IDENTIFIER ::= { 1 2 840 113556 1 4 302 }
id-at-mS-SQL-Keywords OBJECT IDENTIFIER ::= { 1 2 840 113556 1 4 1401 }
id-at-proxyAddresses OBJECT IDENTIFIER ::= { 1 2 840 113556 1 2 210 }
id-at-bytesPerMinute OBJECT IDENTIFIER ::= { 1 2 840 113556 1 4 284 }
id-at-printMaxCopies OBJECT IDENTIFIER ::= { 1 2 840 113556 1 4 241 }
id-at-primaryGroupID OBJECT IDENTIFIER ::= { 1 2 840 113556 1 4 98 }
id-at-nTGroupMembers OBJECT IDENTIFIER ::= { 1 2 840 113556 1 4 89 }
id-at-mSMQDsServices OBJECT IDENTIFIER ::= { 1 2 840 113556 1 4 1228 }
id-at-fRSVersionGUID OBJECT IDENTIFIER ::= { 1 2 840 113556 1 4 43 }
id-at-fRSWorkingPath OBJECT IDENTIFIER ::= { 1 2 840 113556 1 4 486 }
id-at-otherTelephone OBJECT IDENTIFIER ::= { 1 2 840 113556 1 2 18 }
id-at-otherHomePhone OBJECT IDENTIFIER ::= { 1 2 840 113556 1 2 277 }
id-at-oEMInformation OBJECT IDENTIFIER ::= { 1 2 840 113556 1 4 151 }
id-at-networkAddress OBJECT IDENTIFIER ::= { 1 2 840 113556 1 2 459 }
id-at-mSMQDigestsMig OBJECT IDENTIFIER ::= { 1 2 840 113556 1 4 966 }
id-at-meetingKeyword OBJECT IDENTIFIER ::= { 1 2 840 113556 1 4 568 }
id-at-lDAPIPDenyList OBJECT IDENTIFIER ::= { 1 2 840 113556 1 4 844 }
id-at-installUiLevel OBJECT IDENTIFIER ::= { 1 2 840 113556 1 4 847 }
id-at-gPCFileSysPath OBJECT IDENTIFIER ::= { 1 2 840 113556 1 4 894 }
id-at-fRSStagingPath OBJECT IDENTIFIER ::= { 1 2 840 113556 1 4 488 }
id-at-auxiliaryClass OBJECT IDENTIFIER ::= { 1 2 840 113556 1 2 351 }
id-at-accountExpires OBJECT IDENTIFIER ::= { 1 2 840 113556 1 4 159 }
id-at-dhcpProperties OBJECT IDENTIFIER ::= { 1 2 840 113556 1 4 718 }
id-at-desktopProfile OBJECT IDENTIFIER ::= { 1 2 840 113556 1 4 346 }
id-at-aCSServiceType OBJECT IDENTIFIER ::= { 1 2 840 113556 1 4 762 }
id-at-assocNTAccount OBJECT IDENTIFIER ::= { 1 2 840 113556 1 4 1213 }
id-at-creationWizard OBJECT IDENTIFIER ::= { 1 2 840 113556 1 4 498 }
id-at-cOMOtherProgId OBJECT IDENTIFIER ::= { 1 2 840 113556 1 4 253 }
id-at-auditingPolicy OBJECT IDENTIFIER ::= { 1 2 840 113556 1 4 202 }
id-at-privilegeValue OBJECT IDENTIFIER ::= { 1 2 840 113556 1 4 635 }
id-at-mS-SQL-Location OBJECT IDENTIFIER ::= { 1 2 840 113556 1 4 1366 }
id-at-pKIDefaultCSPs OBJECT IDENTIFIER ::= { 1 2 840 113556 1 4 1334 }
id-at-printShareName OBJECT IDENTIFIER ::= { 1 2 840 113556 1 4 270 }
id-at-isSingleValued OBJECT IDENTIFIER ::= { 1 2 840 113556 1 2 33 }
id-at-domainCrossRef OBJECT IDENTIFIER ::= { 1 2 840 113556 1 4 472 }
id-at-netbootSIFFile OBJECT IDENTIFIER ::= { 1 2 840 113556 1 4 1240 }
id-at-cOMUniqueLIBID OBJECT IDENTIFIER ::= { 1 2 840 113556 1 4 250 }
id-at-serviceDNSName OBJECT IDENTIFIER ::= { 1 2 840 113556 1 4 657 }
id-at-objectCategory OBJECT IDENTIFIER ::= { 1 2 840 113556 1 4 782 }
id-at-serviceClassID OBJECT IDENTIFIER ::= { 1 2 840 113556 1 4 122 }
id-at-dhcpUpdateTime OBJECT IDENTIFIER ::= { 1 2 840 113556 1 4 720 }
id-at-sAMAccountName OBJECT IDENTIFIER ::= { 1 2 840 113556 1 4 221 }
id-at-mS-SQL-Language OBJECT IDENTIFIER ::= { 1 2 840 113556 1 4 1389 }
id-at-aCSDSBMRefresh OBJECT IDENTIFIER ::= { 1 2 840 113556 1 4 777 }
id-at-mS-SQL-Database OBJECT IDENTIFIER ::= { 1 2 840 113556 1 4 1393 }
id-at-cOMInterfaceID OBJECT IDENTIFIER ::= { 1 2 840 113556 1 4 20 }
id-at-mS-SQL-AllowKnownPullSubscription OBJECT IDENTIFIER ::= { 1 2 840 113556 1 4 1403 }
id-at-mS-SQL-AllowAnonymousSubscription OBJECT IDENTIFIER ::= { 1 2 840 113556 1 4 1394 }
id-at-managedObjects OBJECT IDENTIFIER ::= { 1 2 840 113556 1 4 654 }
id-at-possSuperiors OBJECT IDENTIFIER ::= { 1 2 840 113556 1 2 8 }
id-at-transportType OBJECT IDENTIFIER ::= { 1 2 840 113556 1 4 791 }
id-at-groupPriority OBJECT IDENTIFIER ::= { 1 2 840 113556 1 4 345 }
id-at-rpcNsPriority OBJECT IDENTIFIER ::= { 1 2 840 113556 1 4 117 }
id-at-mSMQQueueType OBJECT IDENTIFIER ::= { 1 2 840 113556 1 4 917 }
id-at-versionNumber OBJECT IDENTIFIER ::= { 1 2 840 113556 1 4 141 }
id-at-uSNLastObjRem OBJECT IDENTIFIER ::= { 1 2 840 113556 1 2 121 }
id-at-templateRoots OBJECT IDENTIFIER ::= { 1 2 840 113556 1 4 1346 }
id-at-pwdProperties OBJECT IDENTIFIER ::= { 1 2 840 113556 1 4 93 }
id-at-printNumberUp OBJECT IDENTIFIER ::= { 1 2 840 113556 1 4 290 }
id-at-fRSExtensions OBJECT IDENTIFIER ::= { 1 2 840 113556 1 4 536 }
id-at-printRateUnit OBJECT IDENTIFIER ::= { 1 2 840 113556 1 4 286 }
id-at-msiScriptSize OBJECT IDENTIFIER ::= { 1 2 840 113556 1 4 846 }
id-at-printSpooling OBJECT IDENTIFIER ::= { 1 2 840 113556 1 4 274 }
id-at-queryPolicyBL OBJECT IDENTIFIER ::= { 1 2 840 113556 1 4 608 }
id-at-proxyLifetime OBJECT IDENTIFIER ::= { 1 2 840 113556 1 4 103 }
id-at-operatorCount OBJECT IDENTIFIER ::= { 1 2 840 113556 1 4 144 }
id-at-netbootServer OBJECT IDENTIFIER ::= { 1 2 840 113556 1 4 860 }
id-at-fSMORoleOwner OBJECT IDENTIFIER ::= { 1 2 840 113556 1 4 369 }
id-at-driverVersion OBJECT IDENTIFIER ::= { 1 2 840 113556 1 4 276 }
id-at-mS-SQL-Version OBJECT IDENTIFIER ::= { 1 2 840 113556 1 4 1388 }
id-at-mSMQNameStyle OBJECT IDENTIFIER ::= { 1 2 840 113556 1 4 939 }
id-at-schemaVersion OBJECT IDENTIFIER ::= { 1 2 840 113556 1 2 471 }
id-at-directReports OBJECT IDENTIFIER ::= { 1 2 840 113556 1 2 436 }
id-at-addressSyntax OBJECT IDENTIFIER ::= { 1 2 840 113556 1 2 255 }
id-at-printFormName OBJECT IDENTIFIER ::= { 1 2 840 113556 1 4 235 }
id-at-msiScriptPath OBJECT IDENTIFIER ::= { 1 2 840 113556 1 4 15 }
id-at-aCSServerList OBJECT IDENTIFIER ::= { 1 2 840 113556 1 4 1312 }
id-at-moveTreeState OBJECT IDENTIFIER ::= { 1 2 840 113556 1 4 1305 }
id-at-mSMQSiteGates OBJECT IDENTIFIER ::= { 1 2 840 113556 1 4 945 }
id-at-mSMQDsService OBJECT IDENTIFIER ::= { 1 2 840 113556 1 4 1238 }
id-at-objectVersion OBJECT IDENTIFIER ::= { 1 2 840 113556 1 2 76 }
id-at-dNSTombstoned OBJECT IDENTIFIER ::= { 1 2 840 113556 1 4 1414 }
id-at-mSMQLongLived OBJECT IDENTIFIER ::= { 1 2 840 113556 1 4 941 }
id-at-fRSLevelLimit OBJECT IDENTIFIER ::= { 1 2 840 113556 1 4 534 }
id-at-msiScriptName OBJECT IDENTIFIER ::= { 1 2 840 113556 1 4 845 }
id-at-dhcpUniqueKey OBJECT IDENTIFIER ::= { 1 2 840 113556 1 4 698 }
id-at-extensionName OBJECT IDENTIFIER ::= { 1 2 840 113556 1 2 227 }
id-at-rpcNsBindings OBJECT IDENTIFIER ::= { 1 2 840 113556 1 4 113 }
id-at-printBinNames OBJECT IDENTIFIER ::= { 1 2 840 113556 1 4 237 }
id-at-replicaSource OBJECT IDENTIFIER ::= { 1 2 840 113556 1 4 109 }
id-at-printLanguage OBJECT IDENTIFIER ::= { 1 2 840 113556 1 4 246 }
id-at-mS-SQL-Contact OBJECT IDENTIFIER ::= { 1 2 840 113556 1 4 1365 }
id-at-nTMixedDomain OBJECT IDENTIFIER ::= { 1 2 840 113556 1 4 357 }
-- OID 1.2.840.113556.1.4.483 is also used by calOtherFBURLs in RFC2739Calendar. The LDAP names differ, so this definition was kept.
id-at-fRSFileFilter OBJECT IDENTIFIER ::= { 1 2 840 113556 1 4 483 }
id-at-birthLocation OBJECT IDENTIFIER ::= { 1 2 840 113556 1 4 332 }
id-at-friendlyNames OBJECT IDENTIFIER ::= { 1 2 840 113556 1 4 682 }
id-at-ipsecDataType OBJECT IDENTIFIER ::= { 1 2 840 113556 1 4 622 }
id-at-meetingRating OBJECT IDENTIFIER ::= { 1 2 840 113556 1 4 584 }
id-at-indexedScopes OBJECT IDENTIFIER ::= { 1 2 840 113556 1 4 681 }
id-at-rpcNsObjectID OBJECT IDENTIFIER ::= { 1 2 840 113556 1 4 312 }
id-at-modifiedCount OBJECT IDENTIFIER ::= { 1 2 840 113556 1 4 168 }
id-at-oMObjectClass OBJECT IDENTIFIER ::= { 1 2 840 113556 1 2 218 }
id-at-aCSPolicyName OBJECT IDENTIFIER ::= { 1 2 840 113556 1 4 772 }
id-at-timeVolChange OBJECT IDENTIFIER ::= { 1 2 840 113556 1 4 502 }
id-at-currMachineId OBJECT IDENTIFIER ::= { 1 2 840 113556 1 4 337 }
id-at-schemaFlagsEx OBJECT IDENTIFIER ::= { 1 2 840 113556 1 4 120 }
id-at-validAccesses OBJECT IDENTIFIER ::= { 1 2 840 113556 1 4 1356 }
id-at-domainReplica OBJECT IDENTIFIER ::= { 1 2 840 113556 1 4 158 }
id-at-mSMQInterval2 OBJECT IDENTIFIER ::= { 1 2 840 113556 1 4 1309 }
id-at-mSMQInterval1 OBJECT IDENTIFIER ::= { 1 2 840 113556 1 4 1308 }
id-at-canonicalName OBJECT IDENTIFIER ::= { 1 2 840 113556 1 4 916 }
id-at-ntPwdHistory OBJECT IDENTIFIER ::= { 1 2 840 113556 1 4 94 }
id-at-trustPartner OBJECT IDENTIFIER ::= { 1 2 840 113556 1 4 133 }
id-at-lmPwdHistory OBJECT IDENTIFIER ::= { 1 2 840 113556 1 4 160 }
id-at-mS-SQL-Status OBJECT IDENTIFIER ::= { 1 2 840 113556 1 4 1380 }
id-at-uSNIntersite OBJECT IDENTIFIER ::= { 1 2 840 113556 1 2 469 }
id-at-netbootTools OBJECT IDENTIFIER ::= { 1 2 840 113556 1 4 858 }
id-at-priorSetTime OBJECT IDENTIFIER ::= { 1 2 840 113556 1 4 99 }
id-at-mS-SQL-Memory OBJECT IDENTIFIER ::= { 1 2 840 113556 1 4 1367 }
id-at-mSMQServices OBJECT IDENTIFIER ::= { 1 2 840 113556 1 4 950 }
id-at-currentValue OBJECT IDENTIFIER ::= { 1 2 840 113556 1 4 27 }
id-at-siteLinkList OBJECT IDENTIFIER ::= { 1 2 840 113556 1 4 822 }
id-at-remoteSource OBJECT IDENTIFIER ::= { 1 2 840 113556 1 4 107 }
id-at-setupCommand OBJECT IDENTIFIER ::= { 1 2 840 113556 1 4 325 }
id-at-dSHeuristics OBJECT IDENTIFIER ::= { 1 2 840 113556 1 2 212 }
id-at-replInterval OBJECT IDENTIFIER ::= { 1 2 840 113556 1 4 1336 }
id-at-printEndTime OBJECT IDENTIFIER ::= { 1 2 840 113556 1 4 234 }
id-at-instanceType OBJECT IDENTIFIER ::= { 1 2 840 113556 1 2 1 }
id-at-otherIpPhone OBJECT IDENTIFIER ::= { 1 2 840 113556 1 4 722 }
id-at-mSMQSiteName OBJECT IDENTIFIER ::= { 1 2 840 113556 1 4 965 }
id-at-meetingOwner OBJECT IDENTIFIER ::= { 1 2 840 113556 1 4 579 }
id-at-printCollate OBJECT IDENTIFIER ::= { 1 2 840 113556 1 4 242 }
-- OID 1.2.840.113556.1.4.480 is also used by calCAPURI in RFC2739Calendar. The LDAP names differ, so this definition was kept.
id-at-defaultGroup OBJECT IDENTIFIER ::= { 1 2 840 113556 1 4 480 }
id-at-minPwdLength OBJECT IDENTIFIER ::= { 1 2 840 113556 1 4 79 }
id-at-netbootSCPBL OBJECT IDENTIFIER ::= { 1 2 840 113556 1 4 864 }
id-at-mhsORAddress OBJECT IDENTIFIER ::= { 1 2 840 113556 1 4 650 }
id-at-rpcNsCodeset OBJECT IDENTIFIER ::= { 1 2 840 113556 1 4 367 }
id-at-hasMasterNCs OBJECT IDENTIFIER ::= { 1 2 840 113556 1 2 14 }
id-at-mSMQMigrated OBJECT IDENTIFIER ::= { 1 2 840 113556 1 4 952 }
id-at-dSASignature OBJECT IDENTIFIER ::= { 1 2 840 113556 1 2 74 }
id-at-invocationId OBJECT IDENTIFIER ::= { 1 2 840 113556 1 2 115 }
id-at-cOMTypelibId OBJECT IDENTIFIER ::= { 1 2 840 113556 1 4 254 }
id-at-creationTime OBJECT IDENTIFIER ::= { 1 2 840 113556 1 4 26 }
id-at-meetingScope OBJECT IDENTIFIER ::= { 1 2 840 113556 1 4 581 }
id-at-volTableGUID OBJECT IDENTIFIER ::= { 1 2 840 113556 1 4 336 }
id-at-siteObjectBL OBJECT IDENTIFIER ::= { 1 2 840 113556 1 4 513 }
id-at-aCSTimeOfDay OBJECT IDENTIFIER ::= { 1 2 840 113556 1 4 756 }
id-at-aCSDirection OBJECT IDENTIFIER ::= { 1 2 840 113556 1 4 757 }
id-at-maxTicketAge OBJECT IDENTIFIER ::= { 1 2 840 113556 1 4 77 }
-- OID 1.2.840.113556.1.4.481 is also used by calCalAdrURI in RFC2739Calendar. The LDAP names differ, so this definition was kept.
id-at-schemaUpdate OBJECT IDENTIFIER ::= { 1 2 840 113556 1 4 481 }
id-at-minTicketAge OBJECT IDENTIFIER ::= { 1 2 840 113556 1 4 80 }
id-at-ipsecNegotiationPolicyReference OBJECT IDENTIFIER ::= { 1 2 840 113556 1 4 628 }
id-at-helpFileName OBJECT IDENTIFIER ::= { 1 2 840 113556 1 2 327 }
id-at-schemaIDGUID OBJECT IDENTIFIER ::= { 1 2 840 113556 1 4 148 }
id-at-createDialog OBJECT IDENTIFIER ::= { 1 2 840 113556 1 4 810 }
id-at-mSMQNt4Flags OBJECT IDENTIFIER ::= { 1 2 840 113556 1 4 964 }
id-at-packageFlags OBJECT IDENTIFIER ::= { 1 2 840 113556 1 4 327 }
id-at-wWWHomePage OBJECT IDENTIFIER ::= { 1 2 840 113556 1 2 464 }
id-at-volumeCount OBJECT IDENTIFIER ::= { 1 2 840 113556 1 4 507 }
id-at-printStatus OBJECT IDENTIFIER ::= { 1 2 840 113556 1 4 273 }
id-at-uPNSuffixes OBJECT IDENTIFIER ::= { 1 2 840 113556 1 4 890 }
id-at-trustParent OBJECT IDENTIFIER ::= { 1 2 840 113556 1 4 471 }
id-at-tokenGroups OBJECT IDENTIFIER ::= { 1 2 840 113556 1 4 1301 }
id-at-systemFlags OBJECT IDENTIFIER ::= { 1 2 840 113556 1 4 375 }
id-at-syncWithSID OBJECT IDENTIFIER ::= { 1 2 840 113556 1 4 667 }
id-at-dNSProperty OBJECT IDENTIFIER ::= { 1 2 840 113556 1 4 1306 }
id-at-superScopes OBJECT IDENTIFIER ::= { 1 2 840 113556 1 4 710 }
id-at-sPNMappings OBJECT IDENTIFIER ::= { 1 2 840 113556 1 4 1347 }
id-at-printNotify OBJECT IDENTIFIER ::= { 1 2 840 113556 1 4 272 }
id-at-printMemory OBJECT IDENTIFIER ::= { 1 2 840 113556 1 4 282 }
id-at-serverState OBJECT IDENTIFIER ::= { 1 2 840 113556 1 4 154 }
id-at-mSMQVersion OBJECT IDENTIFIER ::= { 1 2 840 113556 1 4 942 }
id-at-rIDUsedPool OBJECT IDENTIFIER ::= { 1 2 840 113556 1 4 373 }
id-at-queryFilter OBJECT IDENTIFIER ::= { 1 2 840 113556 1 4 1355 }
id-at-printerName OBJECT IDENTIFIER ::= { 1 2 840 113556 1 4 300 }
id-at-preferredOU OBJECT IDENTIFIER ::= { 1 2 840 113556 1 4 97 }
id-at-primaryInternationalISDNNumber OBJECT IDENTIFIER ::= { 1 2 840 113556 1 4 649 }
id-at-oMTIndxGuid OBJECT IDENTIFIER ::= { 1 2 840 113556 1 4 333 }
id-at-mSMQUserSid OBJECT IDENTIFIER ::= { 1 2 840 113556 1 4 1337 }
id-at-fRSRootPath OBJECT IDENTIFIER ::= { 1 2 840 113556 1 4 487 }
id-at-mSMQJournal OBJECT IDENTIFIER ::= { 1 2 840 113556 1 4 918 }
id-at-contextMenu OBJECT IDENTIFIER ::= { 1 2 840 113556 1 4 499 }
id-at-aCSPriority OBJECT IDENTIFIER ::= { 1 2 840 113556 1 4 764 }
id-at-mSMQSignKey OBJECT IDENTIFIER ::= { 1 2 840 113556 1 4 937 }
id-at-netbootGUID OBJECT IDENTIFIER ::= { 1 2 840 113556 1 4 359 }
id-at-mSMQOwnerID OBJECT IDENTIFIER ::= { 1 2 840 113556 1 4 925 }
id-at-mustContain OBJECT IDENTIFIER ::= { 1 2 840 113556 1 2 24 }
id-at-dnsAllowXFR OBJECT IDENTIFIER ::= { 1 2 840 113556 1 4 379 }
id-at-mS-SQL-Vines OBJECT IDENTIFIER ::= { 1 2 840 113556 1 4 1379 }
id-at-mSMQDigests OBJECT IDENTIFIER ::= { 1 2 840 113556 1 4 948 }
id-at-lockoutTime OBJECT IDENTIFIER ::= { 1 2 840 113556 1 4 662 }
id-at-lastSetTime OBJECT IDENTIFIER ::= { 1 2 840 113556 1 4 53 }
id-at-countryCode OBJECT IDENTIFIER ::= { 1 2 840 113556 1 4 25 }
id-at-mS-SQL-TCPIP OBJECT IDENTIFIER ::= { 1 2 840 113556 1 4 1377 }
id-at-mSMQForeign OBJECT IDENTIFIER ::= { 1 2 840 113556 1 4 934 }
id-at-meetingType OBJECT IDENTIFIER ::= { 1 2 840 113556 1 4 571 }
id-at-dhcpOptions OBJECT IDENTIFIER ::= { 1 2 840 113556 1 4 714 }
id-at-dhcpServers OBJECT IDENTIFIER ::= { 1 2 840 113556 1 4 704 }
id-at-assetNumber OBJECT IDENTIFIER ::= { 1 2 840 113556 1 4 283 }
id-at-addressType OBJECT IDENTIFIER ::= { 1 2 840 113556 1 2 350 }
id-at-mSMQCSPName OBJECT IDENTIFIER ::= { 1 2 840 113556 1 4 940 }
id-at-msiFileList OBJECT IDENTIFIER ::= { 1 2 840 113556 1 4 671 }
id-at-dNSHostName OBJECT IDENTIFIER ::= { 1 2 840 113556 1 4 619 }
id-at-dhcpSubnets OBJECT IDENTIFIER ::= { 1 2 840 113556 1 4 705 }
id-at-pKIKeyUsage OBJECT IDENTIFIER ::= { 1 2 840 113556 1 4 1328 }
id-at-attributeID OBJECT IDENTIFIER ::= { 1 2 840 113556 1 2 30 }
id-at-objectCount OBJECT IDENTIFIER ::= { 1 2 840 113556 1 4 506 }
id-at-timeRefresh OBJECT IDENTIFIER ::= { 1 2 840 113556 1 4 503 }
id-at-profilePath OBJECT IDENTIFIER ::= { 1 2 840 113556 1 4 139 }
id-at-productCode OBJECT IDENTIFIER ::= { 1 2 840 113556 1 4 818 }
id-at-otherMobile OBJECT IDENTIFIER ::= { 1 2 840 113556 1 4 647 }
id-at-badPwdCount OBJECT IDENTIFIER ::= { 1 2 840 113556 1 4 12 }
id-at-mS-SQL-Build OBJECT IDENTIFIER ::= { 1 2 840 113556 1 4 1368 }
id-at-nETBIOSName OBJECT IDENTIFIER ::= { 1 2 840 113556 1 4 87 }
id-at-mS-SQL-Alias OBJECT IDENTIFIER ::= { 1 2 840 113556 1 4 1395 }
id-at-maxRenewAge OBJECT IDENTIFIER ::= { 1 2 840 113556 1 4 75 }
id-at-treatAsLeaf OBJECT IDENTIFIER ::= { 1 2 840 113556 1 4 806 }
id-at-mSMQNt4Stub OBJECT IDENTIFIER ::= { 1 2 840 113556 1 4 960 }
id-at-packageType OBJECT IDENTIFIER ::= { 1 2 840 113556 1 4 324 }
id-at-isEphemeral OBJECT IDENTIFIER ::= { 1 2 840 113556 1 4 1212 }
id-at-dMDLocation OBJECT IDENTIFIER ::= { 1 2 840 113556 1 2 36 }
id-at-dhcpClasses OBJECT IDENTIFIER ::= { 1 2 840 113556 1 4 715 }
id-at-forceLogoff OBJECT IDENTIFIER ::= { 1 2 840 113556 1 4 39 }
id-at-whenCreated OBJECT IDENTIFIER ::= { 1 2 840 113556 1 2 2 }
id-at-meetingName OBJECT IDENTIFIER ::= { 1 2 840 113556 1 4 566 }
id-at-mailAddress OBJECT IDENTIFIER ::= { 1 2 840 113556 1 4 786 }
id-at-meetingBlob OBJECT IDENTIFIER ::= { 1 2 840 113556 1 4 590 }
id-at-machineRole OBJECT IDENTIFIER ::= { 1 2 840 113556 1 4 71 }
id-at-searchFlags OBJECT IDENTIFIER ::= { 1 2 840 113556 1 2 334 }
id-at-whenChanged OBJECT IDENTIFIER ::= { 1 2 840 113556 1 2 3 }
id-at-dhcpObjName OBJECT IDENTIFIER ::= { 1 2 840 113556 1 4 702 }
id-at-aCSMaxAggregatePeakRatePerUser OBJECT IDENTIFIER ::= { 1 2 840 113556 1 4 897 }
id-at-packageName OBJECT IDENTIFIER ::= { 1 2 840 113556 1 4 326 }
id-at-systemOnly OBJECT IDENTIFIER ::= { 1 2 840 113556 1 4 170 }
id-at-mSMQOSType OBJECT IDENTIFIER ::= { 1 2 840 113556 1 4 935 }
id-at-queryPoint OBJECT IDENTIFIER ::= { 1 2 840 113556 1 4 680 }
id-at-printOwner OBJECT IDENTIFIER ::= { 1 2 840 113556 1 4 271 }
id-at-uSNCreated OBJECT IDENTIFIER ::= { 1 2 840 113556 1 2 19 }
id-at-siteServer OBJECT IDENTIFIER ::= { 1 2 840 113556 1 4 494 }
id-at-rpcNsGroup OBJECT IDENTIFIER ::= { 1 2 840 113556 1 4 114 }
id-at-sIDHistory OBJECT IDENTIFIER ::= { 1 2 840 113556 1 4 609 }
id-at-fRSVersion OBJECT IDENTIFIER ::= { 1 2 840 113556 1 4 882 }
id-at-logonHours OBJECT IDENTIFIER ::= { 1 2 840 113556 1 4 64 }
id-at-netbootAnswerOnlyValidClients OBJECT IDENTIFIER ::= { 1 2 840 113556 1 4 854 }
id-at-pwdLastSet OBJECT IDENTIFIER ::= { 1 2 840 113556 1 4 96 }
id-at-printColor OBJECT IDENTIFIER ::= { 1 2 840 113556 1 4 243 }
id-at-mS-SQL-Type OBJECT IDENTIFIER ::= { 1 2 840 113556 1 4 1391 }
id-at-fromServer OBJECT IDENTIFIER ::= { 1 2 840 113556 1 4 40 }
id-at-serverRole OBJECT IDENTIFIER ::= { 1 2 840 113556 1 4 157 }
id-at-priorValue OBJECT IDENTIFIER ::= { 1 2 840 113556 1 4 100 }
id-at-logonCount OBJECT IDENTIFIER ::= { 1 2 840 113556 1 4 169 }
id-at-unicodePwd OBJECT IDENTIFIER ::= { 1 2 840 113556 1 4 90 }
id-at-subClassOf OBJECT IDENTIFIER ::= { 1 2 840 113556 1 2 21 }
id-at-mS-SQL-Size OBJECT IDENTIFIER ::= { 1 2 840 113556 1 4 1396 }
id-at-privateKey OBJECT IDENTIFIER ::= { 1 2 840 113556 1 4 101 }
id-at-siteObject OBJECT IDENTIFIER ::= { 1 2 840 113556 1 4 512 }
id-at-scriptPath OBJECT IDENTIFIER ::= { 1 2 840 113556 1 4 62 }
id-at-serverName OBJECT IDENTIFIER ::= { 1 2 840 113556 1 4 223 }
id-at-mSMQSiteID OBJECT IDENTIFIER ::= { 1 2 840 113556 1 4 953 }
id-at-rightsGuid OBJECT IDENTIFIER ::= { 1 2 840 113556 1 4 340 }
id-at-rIDNextRID OBJECT IDENTIFIER ::= { 1 2 840 113556 1 4 374 }
id-at-meetingURL OBJECT IDENTIFIER ::= { 1 2 840 113556 1 4 583 }
id-at-addressEntryDisplayTableMSDOS OBJECT IDENTIFIER ::= { 1 2 840 113556 1 2 400 }
id-at-maxStorage OBJECT IDENTIFIER ::= { 1 2 840 113556 1 4 76 }
id-at-rangeUpper OBJECT IDENTIFIER ::= { 1 2 840 113556 1 2 35 }
id-at-rangeLower OBJECT IDENTIFIER ::= { 1 2 840 113556 1 2 34 }
id-at-otherPager OBJECT IDENTIFIER ::= { 1 2 840 113556 1 2 118 }
id-at-isMemberOfPartialAttributeSet OBJECT IDENTIFIER ::= { 1 2 840 113556 1 4 639 }
id-at-parentGUID OBJECT IDENTIFIER ::= { 1 2 840 113556 1 4 1224 }
id-at-department OBJECT IDENTIFIER ::= { 1 2 840 113556 1 2 141 }
id-at-mayContain OBJECT IDENTIFIER ::= { 1 2 840 113556 1 2 25 }
id-at-adminCount OBJECT IDENTIFIER ::= { 1 2 840 113556 1 4 150 }
id-at-lastLogoff OBJECT IDENTIFIER ::= { 1 2 840 113556 1 4 51 }
id-at-masteredBy OBJECT IDENTIFIER ::= { 1 2 840 113556 1 4 1409 }
id-at-employeeID OBJECT IDENTIFIER ::= { 1 2 840 113556 1 4 35 }
id-at-dhcpMaxKey OBJECT IDENTIFIER ::= { 1 2 840 113556 1 4 719 }
id-at-driverName OBJECT IDENTIFIER ::= { 1 2 840 113556 1 4 229 }
id-at-mS-SQL-Name OBJECT IDENTIFIER ::= { 1 2 840 113556 1 4 1363 }
id-at-categoryId OBJECT IDENTIFIER ::= { 1 2 840 113556 1 4 322 }
id-at-additionalTrustedServiceNames OBJECT IDENTIFIER ::= { 1 2 840 113556 1 4 889 }
id-at-scopeFlags OBJECT IDENTIFIER ::= { 1 2 840 113556 1 4 1354 }
id-at-categories OBJECT IDENTIFIER ::= { 1 2 840 113556 1 4 672 }
id-at-netbootNewMachineNamingPolicy OBJECT IDENTIFIER ::= { 1 2 840 113556 1 4 855 }
id-at-cOMClassID OBJECT IDENTIFIER ::= { 1 2 840 113556 1 4 19 }
id-at-uSNChanged OBJECT IDENTIFIER ::= { 1 2 840 113556 1 2 120 }
id-at-objectGUID OBJECT IDENTIFIER ::= { 1 2 840 113556 1 4 2 }
id-at-dhcpRanges OBJECT IDENTIFIER ::= { 1 2 840 113556 1 4 707 }
id-at-schemaInfo OBJECT IDENTIFIER ::= { 1 2 840 113556 1 4 1358 }
id-at-otherFacsimileTelephoneNumber OBJECT IDENTIFIER ::= { 1 2 840 113556 1 4 646 }
id-at-machinePasswordChangeInterval OBJECT IDENTIFIER ::= { 1 2 840 113556 1 4 520 }
id-at-rootTrust OBJECT IDENTIFIER ::= { 1 2 840 113556 1 4 674 }
id-at-trustType OBJECT IDENTIFIER ::= { 1 2 840 113556 1 4 136 }
id-at-groupType OBJECT IDENTIFIER ::= { 1 2 840 113556 1 4 750 }
id-at-uSNSource OBJECT IDENTIFIER ::= { 1 2 840 113556 1 4 896 }
id-at-mSMQQuota OBJECT IDENTIFIER ::= { 1 2 840 113556 1 4 919 }
id-at-mSMQSites OBJECT IDENTIFIER ::= { 1 2 840 113556 1 4 927 }
id-at-fromEntry OBJECT IDENTIFIER ::= { 1 2 840 113556 1 4 910 }
id-at-mS-SQL-SPX OBJECT IDENTIFIER ::= { 1 2 840 113556 1 4 1376 }
id-at-gPOptions OBJECT IDENTIFIER ::= { 1 2 840 113556 1 4 892 }
id-at-msiScript OBJECT IDENTIFIER ::= { 1 2 840 113556 1 4 814 }
id-at-printRate OBJECT IDENTIFIER ::= { 1 2 840 113556 1 4 285 }
id-at-cRLPartitionedRevocationList OBJECT IDENTIFIER ::= { 1 2 840 113556 1 4 683 }
id-at-assistant OBJECT IDENTIFIER ::= { 1 2 840 113556 1 4 652 }
id-at-fRSDSPoll OBJECT IDENTIFIER ::= { 1 2 840 113556 1 4 490 }
id-at-partialAttributeDeletionList OBJECT IDENTIFIER ::= { 1 2 840 113556 1 4 663 }
id-at-lastLogon OBJECT IDENTIFIER ::= { 1 2 840 113556 1 4 52 }
id-at-governsID OBJECT IDENTIFIER ::= { 1 2 840 113556 1 2 22 }
id-at-appliesTo OBJECT IDENTIFIER ::= { 1 2 840 113556 1 4 341 }
id-at-eFSPolicy OBJECT IDENTIFIER ::= { 1 2 840 113556 1 4 268 }
id-at-uASCompat OBJECT IDENTIFIER ::= { 1 2 840 113556 1 4 155 }
id-at-prefixMap OBJECT IDENTIFIER ::= { 1 2 840 113556 1 4 538 }
id-at-isDefunct OBJECT IDENTIFIER ::= { 1 2 840 113556 1 4 661 }
id-at-dhcpSites OBJECT IDENTIFIER ::= { 1 2 840 113556 1 4 708 }
id-at-iPSECNegotiationPolicyAction OBJECT IDENTIFIER ::= { 1 2 840 113556 1 4 888 }
id-at-dnsRecord OBJECT IDENTIFIER ::= { 1 2 840 113556 1 4 382 }
id-at-cOMProgID OBJECT IDENTIFIER ::= { 1 2 840 113556 1 4 21 }
id-at-homeDrive OBJECT IDENTIFIER ::= { 1 2 840 113556 1 4 45 }
id-at-meetingIP OBJECT IDENTIFIER ::= { 1 2 840 113556 1 4 580 }
id-at-aCSNonReservedMinPolicedSize OBJECT IDENTIFIER ::= { 1 2 840 113556 1 4 1321 }
id-at-dhcpState OBJECT IDENTIFIER ::= { 1 2 840 113556 1 4 717 }
id-at-mSMQLabel OBJECT IDENTIFIER ::= { 1 2 840 113556 1 4 922 }
id-at-maxPwdAge OBJECT IDENTIFIER ::= { 1 2 840 113556 1 4 74 }
id-at-minPwdAge OBJECT IDENTIFIER ::= { 1 2 840 113556 1 4 78 }
id-at-cRLObject OBJECT IDENTIFIER ::= { 1 2 840 113556 1 4 689 }
id-at-objectSid OBJECT IDENTIFIER ::= { 1 2 840 113556 1 4 146 }
id-at-meetingID OBJECT IDENTIFIER ::= { 1 2 840 113556 1 4 565 }
id-at-ipsecName OBJECT IDENTIFIER ::= { 1 2 840 113556 1 4 620 }
id-at-isDeleted OBJECT IDENTIFIER ::= { 1 2 840 113556 1 2 48 }
id-at-aCSAggregateTokenRatePerUser OBJECT IDENTIFIER ::= { 1 2 840 113556 1 4 760 }
id-at-ipsecData OBJECT IDENTIFIER ::= { 1 2 840 113556 1 4 623 }
id-at-domainCAs OBJECT IDENTIFIER ::= { 1 2 840 113556 1 4 668 }
id-at-cAConnect OBJECT IDENTIFIER ::= { 1 2 840 113556 1 4 687 }
id-at-printMaxResolutionSupported OBJECT IDENTIFIER ::= { 1 2 840 113556 1 4 238 }
id-at-dhcpFlags OBJECT IDENTIFIER ::= { 1 2 840 113556 1 4 700 }
id-at-helpData16 OBJECT IDENTIFIER ::= { 1 2 840 113556 1 2 402 }
id-at-managedBy OBJECT IDENTIFIER ::= { 1 2 840 113556 1 4 653 }
id-at-helpData32 OBJECT IDENTIFIER ::= { 1 2 840 113556 1 2 9 }
id-at-mSMQSite2 OBJECT IDENTIFIER ::= { 1 2 840 113556 1 4 944 }
id-at-mSMQSite1 OBJECT IDENTIFIER ::= { 1 2 840 113556 1 4 943 }
id-at-replTopologyStayOfExecution OBJECT IDENTIFIER ::= { 1 2 840 113556 1 4 677 }
id-at-allowedChildClassesEffective OBJECT IDENTIFIER ::= { 1 2 840 113556 1 4 912 }
id-at-oMSyntax OBJECT IDENTIFIER ::= { 1 2 840 113556 1 2 231 }
id-at-priority OBJECT IDENTIFIER ::= { 1 2 840 113556 1 4 231 }
id-at-keywords OBJECT IDENTIFIER ::= { 1 2 840 113556 1 4 48 }
id-at-mSMQCost OBJECT IDENTIFIER ::= { 1 2 840 113556 1 4 946 }
id-at-siteList OBJECT IDENTIFIER ::= { 1 2 840 113556 1 4 821 }
id-at-revision OBJECT IDENTIFIER ::= { 1 2 840 113556 1 4 145 }
id-at-repsFrom OBJECT IDENTIFIER ::= { 1 2 840 113556 1 2 91 }
id-at-userCert OBJECT IDENTIFIER ::= { 1 2 840 113556 1 4 645 }
id-at-mSMQQMID OBJECT IDENTIFIER ::= { 1 2 840 113556 1 4 951 }
id-at-portName OBJECT IDENTIFIER ::= { 1 2 840 113556 1 4 228 }
id-at-netbootLocallyInstalledOSes OBJECT IDENTIFIER ::= { 1 2 840 113556 1 4 859 }
id-at-division OBJECT IDENTIFIER ::= { 1 2 840 113556 1 4 261 }
id-at-aCSMaxSizeOfRSVPAccountFile OBJECT IDENTIFIER ::= { 1 2 840 113556 1 4 902 }
id-at-dhcpType OBJECT IDENTIFIER ::= { 1 2 840 113556 1 4 699 }
id-at-wbemPath OBJECT IDENTIFIER ::= { 1 2 840 113556 1 4 301 }
id-at-siteGUID OBJECT IDENTIFIER ::= { 1 2 840 113556 1 4 362 }
id-at-rDNAttID OBJECT IDENTIFIER ::= { 1 2 840 113556 1 2 26 }
id-at-aCSRSVPAccountFilesLocation OBJECT IDENTIFIER ::= { 1 2 840 113556 1 4 900 }
id-at-mSMQDependentClientServices OBJECT IDENTIFIER ::= { 1 2 840 113556 1 4 1226 }
id-at-location OBJECT IDENTIFIER ::= { 1 2 840 113556 1 4 222 }
id-at-fRSFlags OBJECT IDENTIFIER ::= { 1 2 840 113556 1 4 874 }
id-at-iconPath OBJECT IDENTIFIER ::= { 1 2 840 113556 1 4 219 }
id-at-cAWEBURL OBJECT IDENTIFIER ::= { 1 2 840 113556 1 4 688 }
id-at-mscopeId OBJECT IDENTIFIER ::= { 1 2 840 113556 1 4 716 }
id-at-treeName OBJECT IDENTIFIER ::= { 1 2 840 113556 1 4 660 }
id-at-schedule OBJECT IDENTIFIER ::= { 1 2 840 113556 1 4 211 }
id-at-parentCA OBJECT IDENTIFIER ::= { 1 2 840 113556 1 4 557 }
id-at-cOMCLSID OBJECT IDENTIFIER ::= { 1 2 840 113556 1 4 249 }
id-at-catalogs OBJECT IDENTIFIER ::= { 1 2 840 113556 1 4 675 }
id-at-memberOf OBJECT IDENTIFIER ::= { 1 2 840 113556 1 2 102 }
id-at-cAUsages OBJECT IDENTIFIER ::= { 1 2 840 113556 1 4 690 }
id-at-dhcpMask OBJECT IDENTIFIER ::= { 1 2 840 113556 1 4 706 }
id-at-flatName OBJECT IDENTIFIER ::= { 1 2 840 113556 1 4 511 }
id-at-domainID OBJECT IDENTIFIER ::= { 1 2 840 113556 1 4 686 }
id-at-localeID OBJECT IDENTIFIER ::= { 1 2 840 113556 1 4 58 }
id-at-codePage OBJECT IDENTIFIER ::= { 1 2 840 113556 1 4 16 }
id-at-aCSEnableRSVPMessageLogging OBJECT IDENTIFIER ::= { 1 2 840 113556 1 4 768 }
id-at-printOrientationsSupported OBJECT IDENTIFIER ::= { 1 2 840 113556 1 4 240 }
id-at-msRRASVendorAttributeEntry OBJECT IDENTIFIER ::= { 1 2 840 113556 1 4 883 }
id-at-interSiteTopologyGenerator OBJECT IDENTIFIER ::= { 1 2 840 113556 1 4 1246 }
id-at-options OBJECT IDENTIFIER ::= { 1 2 840 113556 1 4 307 }
id-at-dnsRoot OBJECT IDENTIFIER ::= { 1 2 840 113556 1 4 28 }
id-at-iPSECNegotiationPolicyType OBJECT IDENTIFIER ::= { 1 2 840 113556 1 4 887 }
id-at-mS-SQL-InformationDirectory OBJECT IDENTIFIER ::= { 1 2 840 113556 1 4 1392 }
id-at-operatingSystemServicePack OBJECT IDENTIFIER ::= { 1 2 840 113556 1 4 365 }
id-at-nextRid OBJECT IDENTIFIER ::= { 1 2 840 113556 1 4 88 }
id-at-pekList OBJECT IDENTIFIER ::= { 1 2 840 113556 1 4 865 }
id-at-subRefs OBJECT IDENTIFIER ::= { 1 2 840 113556 1 2 7 }
id-at-oMTGuid OBJECT IDENTIFIER ::= { 1 2 840 113556 1 4 505 }
id-at-pKTGuid OBJECT IDENTIFIER ::= { 1 2 840 113556 1 4 205 }
id-at-company OBJECT IDENTIFIER ::= { 1 2 840 113556 1 2 146 }
id-at-moniker OBJECT IDENTIFIER ::= { 1 2 840 113556 1 4 82 }
id-at-comment OBJECT IDENTIFIER ::= { 1 2 840 113556 1 4 156 }
id-at-ipPhone OBJECT IDENTIFIER ::= { 1 2 840 113556 1 4 721 }
id-at-mS-DS-ConsistencyChildCount OBJECT IDENTIFIER ::= { 1 2 840 113556 1 4 1361 }
id-at-creator OBJECT IDENTIFIER ::= { 1 2 840 113556 1 4 679 }
id-at-uNCName OBJECT IDENTIFIER ::= { 1 2 840 113556 1 4 137 }
id-at-dBCSPwd OBJECT IDENTIFIER ::= { 1 2 840 113556 1 4 55 }
id-at-mSMQDependentClientService OBJECT IDENTIFIER ::= { 1 2 840 113556 1 4 1239 }
id-at-certificateAuthorityObject OBJECT IDENTIFIER ::= { 1 2 840 113556 1 4 684 }
id-at-ipsecID OBJECT IDENTIFIER ::= { 1 2 840 113556 1 4 621 }
id-at-allowedAttributesEffective OBJECT IDENTIFIER ::= { 1 2 840 113556 1 4 914 }
id-at-aCSMaxPeakBandwidthPerFlow OBJECT IDENTIFIER ::= { 1 2 840 113556 1 4 759 }
id-at-enabled OBJECT IDENTIFIER ::= { 1 2 840 113556 1 2 557 }
id-at-perRecipDialogDisplayTable OBJECT IDENTIFIER ::= { 1 2 840 113556 1 2 326 }
id-at-interSiteTopologyFailover OBJECT IDENTIFIER ::= { 1 2 840 113556 1 4 1248 }
id-at-transportAddressAttribute OBJECT IDENTIFIER ::= { 1 2 840 113556 1 4 895 }
id-at-netbootCurrentClientCount OBJECT IDENTIFIER ::= { 1 2 840 113556 1 4 852 }
id-at-rIDPreviousAllocationPool OBJECT IDENTIFIER ::= { 1 2 840 113556 1 4 372 }
id-at-repsTo OBJECT IDENTIFIER ::= { 1 2 840 113556 1 2 83 }
id-at-defaultSecurityDescriptor OBJECT IDENTIFIER ::= { 1 2 840 113556 1 4 224 }
id-at-lastBackupRestorationTime OBJECT IDENTIFIER ::= { 1 2 840 113556 1 4 519 }
id-at-fRSControlOutboundBacklog OBJECT IDENTIFIER ::= { 1 2 840 113556 1 4 873 }
id-at-vendor OBJECT IDENTIFIER ::= { 1 2 840 113556 1 4 255 }
id-at-gPLink OBJECT IDENTIFIER ::= { 1 2 840 113556 1 4 891 }
id-at-originalDisplayTableMSDOS OBJECT IDENTIFIER ::= { 1 2 840 113556 1 2 214 }
id-at-linkID OBJECT IDENTIFIER ::= { 1 2 840 113556 1 2 50 }
id-at-msNPSavedCallingStationID OBJECT IDENTIFIER ::= { 1 2 840 113556 1 4 1130 }
id-at-mAPIID OBJECT IDENTIFIER ::= { 1 2 840 113556 1 2 49 }
id-at-serviceBindingInformation OBJECT IDENTIFIER ::= { 1 2 840 113556 1 4 510 }
id-at-nCName OBJECT IDENTIFIER ::= { 1 2 840 113556 1 2 16 }
id-at-tokenGroupsNoGCAcceptable OBJECT IDENTIFIER ::= { 1 2 840 113556 1 4 1303 }
id-at-tokenGroupsGlobalAndUniversal OBJECT IDENTIFIER ::= { 1 2 840 113556 1 4 1418 }
id-at-msRASSavedFramedIPAddress OBJECT IDENTIFIER ::= { 1 2 840 113556 1 4 1190 }
id-at-aCSAllocableRSVPBandwidth OBJECT IDENTIFIER ::= { 1 2 840 113556 1 4 766 }
id-at-lockOutObservationWindow OBJECT IDENTIFIER ::= { 1 2 840 113556 1 4 61 }
id-at-netbootIntelliMirrorOSes OBJECT IDENTIFIER ::= { 1 2 840 113556 1 4 857 }
id-at-aCSNonReservedMaxSDUSize OBJECT IDENTIFIER ::= { 1 2 840 113556 1 4 1320 }
id-at-notes OBJECT IDENTIFIER ::= { 1 2 840 113556 1 4 265 }
id-at-retiredReplDSASignatures OBJECT IDENTIFIER ::= { 1 2 840 113556 1 4 673 }
id-at-aCSMaxTokenBucketPerFlow OBJECT IDENTIFIER ::= { 1 2 840 113556 1 4 1313 }
id-at-addressEntryDisplayTable OBJECT IDENTIFIER ::= { 1 2 840 113556 1 2 324 }
id-at-aCSMinimumDelayVariation OBJECT IDENTIFIER ::= { 1 2 840 113556 1 4 1317 }
id-at-fRSControlInboundBacklog OBJECT IDENTIFIER ::= { 1 2 840 113556 1 4 872 }
id-at-flags OBJECT IDENTIFIER ::= { 1 2 840 113556 1 4 38 }
id-at-mS-SQL-LastDiagnosticDate OBJECT IDENTIFIER ::= { 1 2 840 113556 1 4 1399 }
id-at-gPCMachineExtensionNames OBJECT IDENTIFIER ::= { 1 2 840 113556 1 4 1348 }
id-at-ms-DS-MachineAccountQuota OBJECT IDENTIFIER ::= { 1 2 840 113556 1 4 1411 }
id-at-perMsgDialogDisplayTable OBJECT IDENTIFIER ::= { 1 2 840 113556 1 2 325 }
id-at-defaultLocalPolicyObject OBJECT IDENTIFIER ::= { 1 2 840 113556 1 4 57 }
id-at-msRASSavedCallbackNumber OBJECT IDENTIFIER ::= { 1 2 840 113556 1 4 1189 }
id-at-parentCACertificateChain OBJECT IDENTIFIER ::= { 1 2 840 113556 1 4 685 }
id-at-gPCFunctionalityVersion OBJECT IDENTIFIER ::= { 1 2 840 113556 1 4 893 }
id-at-fRSServiceCommandStatus OBJECT IDENTIFIER ::= { 1 2 840 113556 1 4 879 }
id-at-aCSNonReservedTokenSize OBJECT IDENTIFIER ::= { 1 2 840 113556 1 4 1319 }
id-at-aCSMaxSizeOfRSVPLogFile OBJECT IDENTIFIER ::= { 1 2 840 113556 1 4 775 }
id-at-cost OBJECT IDENTIFIER ::= { 1 2 840 113556 1 2 135 }
id-at-modifiedCountAtLastProm OBJECT IDENTIFIER ::= { 1 2 840 113556 1 4 81 }
id-at-aCSRSVPLogFilesLocation OBJECT IDENTIFIER ::= { 1 2 840 113556 1 4 773 }
id-at-supplementalCredentials OBJECT IDENTIFIER ::= { 1 2 840 113556 1 4 125 }
id-at-bridgeheadTransportList OBJECT IDENTIFIER ::= { 1 2 840 113556 1 4 819 }
id-at-mSMQSignCertificatesMig OBJECT IDENTIFIER ::= { 1 2 840 113556 1 4 967 }
id-at-msRADIUSFramedIPAddress OBJECT IDENTIFIER ::= { 1 2 840 113556 1 4 1153 }
id-at-mS-DS-ReplicatesNCReason OBJECT IDENTIFIER ::= { 1 2 840 113556 1 4 1408 }
id-at-aCSEnableRSVPAccounting OBJECT IDENTIFIER ::= { 1 2 840 113556 1 4 899 }
id-at-printStaplingSupported OBJECT IDENTIFIER ::= { 1 2 840 113556 1 4 281 }
id-at-interSiteTopologyRenew OBJECT IDENTIFIER ::= { 1 2 840 113556 1 4 1247 }
id-at-operatingSystemVersion OBJECT IDENTIFIER ::= { 1 2 840 113556 1 4 364 }
id-at-otherLoginWorkstations OBJECT IDENTIFIER ::= { 1 2 840 113556 1 4 91 }
id-at-netbootAllowNewClients OBJECT IDENTIFIER ::= { 1 2 840 113556 1 4 849 }
id-at-mS-SQL-UnicodeSortOrder OBJECT IDENTIFIER ::= { 1 2 840 113556 1 4 1372 }
id-at-url OBJECT IDENTIFIER ::= { 1 2 840 113556 1 4 749 }
id-at-pKT OBJECT IDENTIFIER ::= { 1 2 840 113556 1 4 206 }
id-at-serviceInstanceVersion OBJECT IDENTIFIER ::= { 1 2 840 113556 1 4 199 }
id-at-showInAdvancedViewOnly OBJECT IDENTIFIER ::= { 1 2 840 113556 1 2 169 }
id-at-aCSMaxTokenRatePerFlow OBJECT IDENTIFIER ::= { 1 2 840 113556 1 4 758 }
id-at-isCriticalSystemObject OBJECT IDENTIFIER ::= { 1 2 840 113556 1 4 868 }
id-at-meetingMaxParticipants OBJECT IDENTIFIER ::= { 1 2 840 113556 1 4 576 }
id-at-aNR OBJECT IDENTIFIER ::= { 1 2 840 113556 1 4 1208 }
id-at-rid OBJECT IDENTIFIER ::= { 1 2 840 113556 1 4 153 }
id-at-proxyGenerationEnabled OBJECT IDENTIFIER ::= { 1 2 840 113556 1 2 523 }
id-at-fRSControlDataCreation OBJECT IDENTIFIER ::= { 1 2 840 113556 1 4 871 }
id-at-previousCACertificates OBJECT IDENTIFIER ::= { 1 2 840 113556 1 4 692 }
id-at-contentIndexingAllowed OBJECT IDENTIFIER ::= { 1 2 840 113556 1 4 24 }
id-at-policyReplicationFlags OBJECT IDENTIFIER ::= { 1 2 840 113556 1 4 633 }
id-at-frsComputerReferenceBL OBJECT IDENTIFIER ::= { 1 2 840 113556 1 4 870 }
id-at-aCSNonReservedPeakRate OBJECT IDENTIFIER ::= { 1 2 840 113556 1 4 1318 }
id-at-aCSMaxNoOfAccountFiles OBJECT IDENTIFIER ::= { 1 2 840 113556 1 4 901 }
id-at-physicalLocationObject OBJECT IDENTIFIER ::= { 1 2 840 113556 1 4 514 }
id-at-mSMQOutRoutingServers OBJECT IDENTIFIER ::= { 1 2 840 113556 1 4 928 }
id-at-bridgeheadServerListBL OBJECT IDENTIFIER ::= { 1 2 840 113556 1 4 820 }
id-at-msRADIUSCallbackNumber OBJECT IDENTIFIER ::= { 1 2 840 113556 1 4 1145 }
id-at-netbootMachineFilePath OBJECT IDENTIFIER ::= { 1 2 840 113556 1 4 361 }
id-at-mSMQQueueJournalQuota OBJECT IDENTIFIER ::= { 1 2 840 113556 1 4 963 }
id-at-netbootAnswerRequests OBJECT IDENTIFIER ::= { 1 2 840 113556 1 4 853 }
id-at-operatingSystemHotfix OBJECT IDENTIFIER ::= { 1 2 840 113556 1 4 415 }
id-at-attributeSecurityGUID OBJECT IDENTIFIER ::= { 1 2 840 113556 1 4 149 }
id-at-superScopeDescription OBJECT IDENTIFIER ::= { 1 2 840 113556 1 4 711 }
id-at-otherWellKnownObjects OBJECT IDENTIFIER ::= { 1 2 840 113556 1 4 1359 }
id-at-aCSNonReservedTxLimit OBJECT IDENTIFIER ::= { 1 2 840 113556 1 4 780 }
id-at-authenticationOptions OBJECT IDENTIFIER ::= { 1 2 840 113556 1 4 11 }
id-at-altSecurityIdentities OBJECT IDENTIFIER ::= { 1 2 840 113556 1 4 867 }
id-at-gPCUserExtensionNames OBJECT IDENTIFIER ::= { 1 2 840 113556 1 4 1349 }
id-at-netbootInitialization OBJECT IDENTIFIER ::= { 1 2 840 113556 1 4 358 }
id-at-mS-SQL-RegisteredOwner OBJECT IDENTIFIER ::= { 1 2 840 113556 1 4 1364 }
id-at-aCSMaxDurationPerFlow OBJECT IDENTIFIER ::= { 1 2 840 113556 1 4 761 }
id-at-pKICriticalExtensions OBJECT IDENTIFIER ::= { 1 2 840 113556 1 4 1330 }
id-at-attributeDisplayNames OBJECT IDENTIFIER ::= { 1 2 840 113556 1 4 748 }
id-at-mS-SQL-AllowImmediateUpdatingSubscription OBJECT IDENTIFIER ::= { 1 2 840 113556 1 4 1404 }
id-at-msRASSavedFramedRoute OBJECT IDENTIFIER ::= { 1 2 840 113556 1 4 1191 }
id-at-userSharedFolderOther OBJECT IDENTIFIER ::= { 1 2 840 113556 1 4 752 }
id-at-extendedAttributeInfo OBJECT IDENTIFIER ::= { 1 2 840 113556 1 4 909 }
id-at-netbootMirrorDataFile OBJECT IDENTIFIER ::= { 1 2 840 113556 1 4 1241 }
id-at-aCSMinimumPolicedSize OBJECT IDENTIFIER ::= { 1 2 840 113556 1 4 1315 }
id-at-localizationDisplayId OBJECT IDENTIFIER ::= { 1 2 840 113556 1 4 1353 }
id-at-meetingAdvertiseScope OBJECT IDENTIFIER ::= { 1 2 840 113556 1 4 582 }
id-at-dSUIAdminNotification OBJECT IDENTIFIER ::= { 1 2 840 113556 1 4 1343 }
id-at-mS-SQL-LastUpdatedDate OBJECT IDENTIFIER ::= { 1 2 840 113556 1 4 1381 }
id-at-dSCorePropagationData OBJECT IDENTIFIER ::= { 1 2 840 113556 1 4 1357 }
id-at-implementedCategories OBJECT IDENTIFIER ::= { 1 2 840 113556 1 4 320 }
id-at-defaultObjectCategory OBJECT IDENTIFIER ::= { 1 2 840 113556 1 4 783 }
id-at-domainPolicyReference OBJECT IDENTIFIER ::= { 1 2 840 113556 1 4 422 }
id-at-mSMQInRoutingServers OBJECT IDENTIFIER ::= { 1 2 840 113556 1 4 929 }
id-at-printDuplexSupported OBJECT IDENTIFIER ::= { 1 2 840 113556 1 4 1311 }
id-at-pendingCACertificates OBJECT IDENTIFIER ::= { 1 2 840 113556 1 4 693 }
id-at-nTSecurityDescriptor OBJECT IDENTIFIER ::= { 1 2 840 113556 1 2 281 }
id-at-systemAuxiliaryClass OBJECT IDENTIFIER ::= { 1 2 840 113556 1 4 198 }
id-at-aCSNonReservedTxSize OBJECT IDENTIFIER ::= { 1 2 840 113556 1 4 898 }
id-at-mS-SQL-InformationURL OBJECT IDENTIFIER ::= { 1 2 840 113556 1 4 1382 }
id-at-replPropertyMetaData OBJECT IDENTIFIER ::= { 1 2 840 113556 1 4 3 }
id-at-mS-SQL-PublicationURL OBJECT IDENTIFIER ::= { 1 2 840 113556 1 4 1384 }
id-at-printKeepPrintedJobs OBJECT IDENTIFIER ::= { 1 2 840 113556 1 4 275 }
id-at-uSNDSALastObjRemoved OBJECT IDENTIFIER ::= { 1 2 840 113556 1 2 267 }
id-at-dnsNotifySecondaries OBJECT IDENTIFIER ::= { 1 2 840 113556 1 4 381 }
id-at-mS-DS-ConsistencyGuid OBJECT IDENTIFIER ::= { 1 2 840 113556 1 4 1360 }
id-at-frsComputerReference OBJECT IDENTIFIER ::= { 1 2 840 113556 1 4 869 }
id-at-mS-SQL-ServiceAccount OBJECT IDENTIFIER ::= { 1 2 840 113556 1 4 1369 }
id-at-msNPCallingStationID OBJECT IDENTIFIER ::= { 1 2 840 113556 1 4 1124 }
id-at-mSMQSignCertificates OBJECT IDENTIFIER ::= { 1 2 840 113556 1 4 947 }
id-at-ipsecOwnersReference OBJECT IDENTIFIER ::= { 1 2 840 113556 1 4 624 }
id-at-builtinModifiedCount OBJECT IDENTIFIER ::= { 1 2 840 113556 1 4 14 }
id-at-privilegeDisplayName OBJECT IDENTIFIER ::= { 1 2 840 113556 1 4 634 }
id-at-dnsSecureSecondaries OBJECT IDENTIFIER ::= { 1 2 840 113556 1 4 380 }
id-at-localizedDescription OBJECT IDENTIFIER ::= { 1 2 840 113556 1 4 817 }
id-at-systemPossSuperiors OBJECT IDENTIFIER ::= { 1 2 840 113556 1 4 195 }
id-at-displayNamePrintable OBJECT IDENTIFIER ::= { 1 2 840 113556 1 2 353 }
id-at-servicePrincipalName OBJECT IDENTIFIER ::= { 1 2 840 113556 1 4 771 }
id-at-pekKeyChangeInterval OBJECT IDENTIFIER ::= { 1 2 840 113556 1 4 866 }
id-at-originalDisplayTable OBJECT IDENTIFIER ::= { 1 2 840 113556 1 2 445 }
id-at-mS-SQL-LastBackupDate OBJECT IDENTIFIER ::= { 1 2 840 113556 1 4 1398 }
id-at-ipsecPolicyReference OBJECT IDENTIFIER ::= { 1 2 840 113556 1 4 517 }
id-at-certificateTemplates OBJECT IDENTIFIER ::= { 1 2 840 113556 1 4 823 }
id-at-hasPartialReplicaNCs OBJECT IDENTIFIER ::= { 1 2 840 113556 1 2 15 }
id-at-localPolicyReference OBJECT IDENTIFIER ::= { 1 2 840 113556 1 4 457 }
id-at-extendedCharsAllowed OBJECT IDENTIFIER ::= { 1 2 840 113556 1 2 380 }
id-at-ipsecFilterReference OBJECT IDENTIFIER ::= { 1 2 840 113556 1 4 629 }
id-at-ipsecISAKMPReference OBJECT IDENTIFIER ::= { 1 2 840 113556 1 4 626 }
id-at-fRSMemberReferenceBL OBJECT IDENTIFIER ::= { 1 2 840 113556 1 4 876 }
id-at-rpcNsTransferSyntax OBJECT IDENTIFIER ::= { 1 2 840 113556 1 4 314 }
id-at-mSMQRoutingServices OBJECT IDENTIFIER ::= { 1 2 840 113556 1 4 1227 }
id-at-mS-SQL-MultiProtocol OBJECT IDENTIFIER ::= { 1 2 840 113556 1 4 1375 }
id-at-enrollmentProviders OBJECT IDENTIFIER ::= { 1 2 840 113556 1 4 825 }
id-at-printNetworkAddress OBJECT IDENTIFIER ::= { 1 2 840 113556 1 4 287 }
id-at-msRADIUSServiceType OBJECT IDENTIFIER ::= { 1 2 840 113556 1 4 1171 }
id-at-printPagesPerMinute OBJECT IDENTIFIER ::= { 1 2 840 113556 1 4 631 }
id-at-printMediaSupported OBJECT IDENTIFIER ::= { 1 2 840 113556 1 4 299 }
id-at-signatureAlgorithms OBJECT IDENTIFIER ::= { 1 2 840 113556 1 4 824 }
id-at-fRSPartnerAuthLevel OBJECT IDENTIFIER ::= { 1 2 840 113556 1 4 877 }
id-at-privilegeAttributes OBJECT IDENTIFIER ::= { 1 2 840 113556 1 4 636 }
id-at-partialAttributeSet OBJECT IDENTIFIER ::= { 1 2 840 113556 1 4 640 }
id-at-netbootLimitClients OBJECT IDENTIFIER ::= { 1 2 840 113556 1 4 850 }
id-at-mS-SQL-ConnectionURL OBJECT IDENTIFIER ::= { 1 2 840 113556 1 4 1383 }
id-at-mS-SQL-AllowSnapshotFilesFTPDownloading OBJECT IDENTIFIER ::= { 1 2 840 113556 1 4 1406 }
id-at-pKIExpirationPeriod OBJECT IDENTIFIER ::= { 1 2 840 113556 1 4 1331 }
id-at-nonSecurityMemberBL OBJECT IDENTIFIER ::= { 1 2 840 113556 1 4 531 }
id-at-initialAuthOutgoing OBJECT IDENTIFIER ::= { 1 2 840 113556 1 4 540 }
id-at-msRADIUSFramedRoute OBJECT IDENTIFIER ::= { 1 2 840 113556 1 4 1158 }
id-at-controlAccessRights OBJECT IDENTIFIER ::= { 1 2 840 113556 1 4 200 }
id-oc-mstop OBJECT IDENTIFIER ::= { 1 2 840 113556 1 5 0 }
id-oc-group OBJECT IDENTIFIER ::= { 1 2 840 113556 1 5 8 }
id-oc-user OBJECT IDENTIFIER ::= { 1 2 840 113556 1 5 9 }
id-oc-computer OBJECT IDENTIFIER ::= { 1 2 840 113556 1 3 30 }

-- Attribute types

-- OID written as MSADat2:104 and expanded with this file's objectidentifier macros.
ownerBL ATTRIBUTE ::= {
  WITH SYNTAX               DistinguishedName
  NO USER MODIFICATION      TRUE
  LDAP-SYNTAX               dn.&id
  LDAP-NAME                 {"ownerBL"}
  ID                        id-at-ownerBL }

-- OID written as MSADat4:1424 and expanded with this file's objectidentifier macros.
msCOM-PartitionSetLink ATTRIBUTE ::= {
  WITH SYNTAX               DistinguishedName
  NO USER MODIFICATION      TRUE
  LDAP-SYNTAX               dn.&id
  LDAP-NAME                 {"msCOM-PartitionSetLink"}
  ID                        id-at-msCOM-PartitionSetLink }

-- OID written as MSADat4:1425 and expanded with this file's objectidentifier macros.
msCOM-UserLink ATTRIBUTE ::= {
  WITH SYNTAX               DistinguishedName
  NO USER MODIFICATION      TRUE
  LDAP-SYNTAX               dn.&id
  LDAP-NAME                 {"msCOM-UserLink"}
  ID                        id-at-msCOM-UserLink }

-- OID written as MSADat4:1669 and expanded with this file's objectidentifier macros.
msDS-Approx-Immed-Subordinates ATTRIBUTE ::= {
  WITH SYNTAX               INTEGER
  SINGLE VALUE              TRUE
  NO USER MODIFICATION      TRUE
  LDAP-SYNTAX               integer.&id
  LDAP-NAME                 {"msDS-Approx-Immed-Subordinates"}
  ID                        id-at-msDS-Approx-Immed-Subordinates }

-- OID written as MSADat4:1704 and expanded with this file's objectidentifier macros.
msDS-NCReplCursors ATTRIBUTE ::= {
  WITH SYNTAX               UnboundedDirectoryString
  LDAP-SYNTAX               directoryString.&id
  LDAP-NAME                 {"msDS-NCReplCursors"}
  ID                        id-at-msDS-NCReplCursors }

-- OID written as MSADat4:1705 and expanded with this file's objectidentifier macros.
msDS-NCReplInboundNeighbors ATTRIBUTE ::= {
  WITH SYNTAX               UnboundedDirectoryString
  LDAP-SYNTAX               directoryString.&id
  LDAP-NAME                 {"msDS-NCReplInboundNeighbors"}
  ID                        id-at-msDS-NCReplInboundNeighbors }

-- OID written as MSADat4:1706 and expanded with this file's objectidentifier macros.
msDS-NCReplOutboundNeighbors ATTRIBUTE ::= {
  WITH SYNTAX               UnboundedDirectoryString
  LDAP-SYNTAX               directoryString.&id
  LDAP-NAME                 {"msDS-NCReplOutboundNeighbors"}
  ID                        id-at-msDS-NCReplOutboundNeighbors }

-- OID written as MSADat4:1707 and expanded with this file's objectidentifier macros.
msDS-ReplAttributeMetaData ATTRIBUTE ::= {
  WITH SYNTAX               UnboundedDirectoryString
  LDAP-SYNTAX               directoryString.&id
  LDAP-NAME                 {"msDS-ReplAttributeMetaData"}
  ID                        id-at-msDS-ReplAttributeMetaData }

-- OID written as MSADat4:1708 and expanded with this file's objectidentifier macros.
msDS-ReplValueMetaData ATTRIBUTE ::= {
  WITH SYNTAX               UnboundedDirectoryString
  LDAP-SYNTAX               directoryString.&id
  LDAP-NAME                 {"msDS-ReplValueMetaData"}
  ID                        id-at-msDS-ReplValueMetaData }

-- OID written as MSADat4:1793 and expanded with this file's objectidentifier macros.
msDS-NonMembers ATTRIBUTE ::= {
  WITH SYNTAX               DistinguishedName
  LDAP-SYNTAX               dn.&id
  LDAP-NAME                 {"msDS-NonMembers"}
  ID                        id-at-msDS-NonMembers }

-- OID written as MSADat4:1794 and expanded with this file's objectidentifier macros.
msDS-NonMembersBL ATTRIBUTE ::= {
  WITH SYNTAX               DistinguishedName
  NO USER MODIFICATION      TRUE
  LDAP-SYNTAX               dn.&id
  LDAP-NAME                 {"msDS-NonMembersBL"}
  ID                        id-at-msDS-NonMembersBL }

-- OID written as MSADat4:1806 and expanded with this file's objectidentifier macros.
msDS-MembersForAzRole ATTRIBUTE ::= {
  WITH SYNTAX               DistinguishedName
  LDAP-SYNTAX               dn.&id
  LDAP-NAME                 {"msDS-MembersForAzRole"}
  ID                        id-at-msDS-MembersForAzRole }

-- OID written as MSADat4:1807 and expanded with this file's objectidentifier macros.
msDS-MembersForAzRoleBL ATTRIBUTE ::= {
  WITH SYNTAX               DistinguishedName
  NO USER MODIFICATION      TRUE
  LDAP-SYNTAX               dn.&id
  LDAP-NAME                 {"msDS-MembersForAzRoleBL"}
  ID                        id-at-msDS-MembersForAzRoleBL }

-- OID written as MSADat4:1808 and expanded with this file's objectidentifier macros.
msDS-OperationsForAzTask ATTRIBUTE ::= {
  WITH SYNTAX               DistinguishedName
  LDAP-SYNTAX               dn.&id
  LDAP-NAME                 {"msDS-OperationsForAzTask"}
  ID                        id-at-msDS-OperationsForAzTask }

-- OID written as MSADat4:1809 and expanded with this file's objectidentifier macros.
msDS-OperationsForAzTaskBL ATTRIBUTE ::= {
  WITH SYNTAX               DistinguishedName
  NO USER MODIFICATION      TRUE
  LDAP-SYNTAX               dn.&id
  LDAP-NAME                 {"msDS-OperationsForAzTaskBL"}
  ID                        id-at-msDS-OperationsForAzTaskBL }

-- OID written as MSADat4:1810 and expanded with this file's objectidentifier macros.
msDS-TasksForAzTask ATTRIBUTE ::= {
  WITH SYNTAX               DistinguishedName
  LDAP-SYNTAX               dn.&id
  LDAP-NAME                 {"msDS-TasksForAzTask"}
  ID                        id-at-msDS-TasksForAzTask }

-- OID written as MSADat4:1811 and expanded with this file's objectidentifier macros.
msDS-TasksForAzTaskBL ATTRIBUTE ::= {
  WITH SYNTAX               DistinguishedName
  NO USER MODIFICATION      TRUE
  LDAP-SYNTAX               dn.&id
  LDAP-NAME                 {"msDS-TasksForAzTaskBL"}
  ID                        id-at-msDS-TasksForAzTaskBL }

-- OID written as MSADat4:1812 and expanded with this file's objectidentifier macros.
msDS-OperationsForAzRole ATTRIBUTE ::= {
  WITH SYNTAX               DistinguishedName
  LDAP-SYNTAX               dn.&id
  LDAP-NAME                 {"msDS-OperationsForAzRole"}
  ID                        id-at-msDS-OperationsForAzRole }

-- OID written as MSADat4:1813 and expanded with this file's objectidentifier macros.
msDS-OperationsForAzRoleBL ATTRIBUTE ::= {
  WITH SYNTAX               DistinguishedName
  NO USER MODIFICATION      TRUE
  LDAP-SYNTAX               dn.&id
  LDAP-NAME                 {"msDS-OperationsForAzRoleBL"}
  ID                        id-at-msDS-OperationsForAzRoleBL }

-- OID written as MSADat4:1814 and expanded with this file's objectidentifier macros.
msDS-TasksForAzRole ATTRIBUTE ::= {
  WITH SYNTAX               DistinguishedName
  LDAP-SYNTAX               dn.&id
  LDAP-NAME                 {"msDS-TasksForAzRole"}
  ID                        id-at-msDS-TasksForAzRole }

-- OID written as MSADat4:1815 and expanded with this file's objectidentifier macros.
msDS-TasksForAzRoleBL ATTRIBUTE ::= {
  WITH SYNTAX               DistinguishedName
  NO USER MODIFICATION      TRUE
  LDAP-SYNTAX               dn.&id
  LDAP-NAME                 {"msDS-TasksForAzRoleBL"}
  ID                        id-at-msDS-TasksForAzRoleBL }

-- OID written as MSADat4:1837 and expanded with this file's objectidentifier macros.
msDs-masteredBy ATTRIBUTE ::= {
  WITH SYNTAX               DistinguishedName
  NO USER MODIFICATION      TRUE
  LDAP-SYNTAX               dn.&id
  LDAP-NAME                 {"msDs-masteredBy"}
  ID                        id-at-msDs-masteredBy }

-- OID written as MSADat4:1840 and expanded with this file's objectidentifier macros.
msDS-ObjectReference ATTRIBUTE ::= {
  WITH SYNTAX               DistinguishedName
  LDAP-SYNTAX               dn.&id
  LDAP-NAME                 {"msDS-ObjectReference"}
  ID                        id-at-msDS-ObjectReference }

-- OID written as MSADat4:1841 and expanded with this file's objectidentifier macros.
msDS-ObjectReferenceBL ATTRIBUTE ::= {
  WITH SYNTAX               DistinguishedName
  NO USER MODIFICATION      TRUE
  LDAP-SYNTAX               dn.&id
  LDAP-NAME                 {"msDS-ObjectReferenceBL"}
  ID                        id-at-msDS-ObjectReferenceBL }

-- OID written as MSADat4:1865 and expanded with this file's objectidentifier macros.
msDS-PrincipalName ATTRIBUTE ::= {
  WITH SYNTAX               UnboundedDirectoryString
  SINGLE VALUE              TRUE
  LDAP-SYNTAX               directoryString.&id
  LDAP-NAME                 {"msDS-PrincipalName"}
  ID                        id-at-msDS-PrincipalName }

-- OID written as MSADat4:1930 and expanded with this file's objectidentifier macros.
msDS-RevealedDSAs ATTRIBUTE ::= {
  WITH SYNTAX               DistinguishedName
  NO USER MODIFICATION      TRUE
  LDAP-SYNTAX               dn.&id
  LDAP-NAME                 {"msDS-RevealedDSAs"}
  ID                        id-at-msDS-RevealedDSAs }

-- OID written as MSADat4:1931 and expanded with this file's objectidentifier macros.
msDS-KrbTgtLinkBl ATTRIBUTE ::= {
  WITH SYNTAX               DistinguishedName
  NO USER MODIFICATION      TRUE
  LDAP-SYNTAX               dn.&id
  LDAP-NAME                 {"msDS-KrbTgtLinkBl"}
  ID                        id-at-msDS-KrbTgtLinkBl }

-- OID written as MSADat4:1932 and expanded with this file's objectidentifier macros.
msDS-IsFullReplicaFor ATTRIBUTE ::= {
  WITH SYNTAX               DistinguishedName
  NO USER MODIFICATION      TRUE
  LDAP-SYNTAX               dn.&id
  LDAP-NAME                 {"msDS-IsFullReplicaFor"}
  ID                        id-at-msDS-IsFullReplicaFor }

-- OID written as MSADat4:1933 and expanded with this file's objectidentifier macros.
msDS-IsDomainFor ATTRIBUTE ::= {
  WITH SYNTAX               DistinguishedName
  NO USER MODIFICATION      TRUE
  LDAP-SYNTAX               dn.&id
  LDAP-NAME                 {"msDS-IsDomainFor"}
  ID                        id-at-msDS-IsDomainFor }

-- OID written as MSADat4:1934 and expanded with this file's objectidentifier macros.
msDS-IsPartialReplicaFor ATTRIBUTE ::= {
  WITH SYNTAX               DistinguishedName
  NO USER MODIFICATION      TRUE
  LDAP-SYNTAX               dn.&id
  LDAP-NAME                 {"msDS-IsPartialReplicaFor"}
  ID                        id-at-msDS-IsPartialReplicaFor }

-- OID written as MSADat4:1957 and expanded with this file's objectidentifier macros.
msDS-AuthenticatedToAccountlist ATTRIBUTE ::= {
  WITH SYNTAX               DistinguishedName
  NO USER MODIFICATION      TRUE
  LDAP-SYNTAX               dn.&id
  LDAP-NAME                 {"msDS-AuthenticatedToAccountlist"}
  ID                        id-at-msDS-AuthenticatedToAccountlist }

-- OID written as MSADat4:1958 and expanded with this file's objectidentifier macros.
msDS-AuthenticatedAtDC ATTRIBUTE ::= {
  WITH SYNTAX               DistinguishedName
  LDAP-SYNTAX               dn.&id
  LDAP-NAME                 {"msDS-AuthenticatedAtDC"}
  ID                        id-at-msDS-AuthenticatedAtDC }

-- OID written as MSADat4:1975 and expanded with this file's objectidentifier macros.
msDS-RevealedListBL ATTRIBUTE ::= {
  WITH SYNTAX               DistinguishedName
  NO USER MODIFICATION      TRUE
  LDAP-SYNTAX               dn.&id
  LDAP-NAME                 {"msDS-RevealedListBL"}
  ID                        id-at-msDS-RevealedListBL }

-- OID written as MSADat4:1968 and expanded with this file's objectidentifier macros.
msDS-NC-RO-Replica-Locations-BL ATTRIBUTE ::= {
  WITH SYNTAX               DistinguishedName
  LDAP-SYNTAX               dn.&id
  LDAP-NAME                 {"msDS-NC-RO-Replica-Locations-BL"}
  ID                        id-at-msDS-NC-RO-Replica-Locations-BL }

-- OID written as MSADat4:2021 and expanded with this file's objectidentifier macros.
msDS-PSOApplied ATTRIBUTE ::= {
  WITH SYNTAX               DistinguishedName
  NO USER MODIFICATION      TRUE
  LDAP-SYNTAX               dn.&id
  LDAP-NAME                 {"msDS-PSOApplied"}
  ID                        id-at-msDS-PSOApplied }

-- OID written as MSADat4:2024 and expanded with this file's objectidentifier macros.
msDS-NcType ATTRIBUTE ::= {
  WITH SYNTAX               INTEGER
  SINGLE VALUE              TRUE
  NO USER MODIFICATION      TRUE
  LDAP-SYNTAX               integer.&id
  LDAP-NAME                 {"msDS-NcType"}
  ID                        id-at-msDS-NcType }

-- OID written as MSADat4:2052 and expanded with this file's objectidentifier macros.
msDS-OIDToGroupLinkBl ATTRIBUTE ::= {
  WITH SYNTAX               DistinguishedName
  NO USER MODIFICATION      TRUE
  LDAP-SYNTAX               dn.&id
  LDAP-NAME                 {"msDS-OIDToGroupLinkBl"}
  ID                        id-at-msDS-OIDToGroupLinkBl }

-- OID written as MSADat4:2057 and expanded with this file's objectidentifier macros.
msDS-HostServiceAccountBL ATTRIBUTE ::= {
  WITH SYNTAX               DistinguishedName
  LDAP-SYNTAX               dn.&id
  LDAP-NAME                 {"msDS-HostServiceAccountBL"}
  ID                        id-at-msDS-HostServiceAccountBL }

-- OID written as MSADat4:2058 and expanded with this file's objectidentifier macros.
isRecycled ATTRIBUTE ::= {
  WITH SYNTAX               BOOLEAN
  SINGLE VALUE              TRUE
  NO USER MODIFICATION      TRUE
  LDAP-SYNTAX               boolean.&id
  LDAP-NAME                 {"isRecycled"}
  ID                        id-at-isRecycled }

-- OID written as MSADat4:2059 and expanded with this file's objectidentifier macros.
msDS-LocalEffectiveDeletionTime ATTRIBUTE ::= {
  WITH SYNTAX               GeneralizedTime
  SINGLE VALUE              TRUE
  NO USER MODIFICATION      TRUE
  LDAP-SYNTAX               generalizedTime.&id
  LDAP-NAME                 {"msDS-LocalEffectiveDeletionTime"}
  ID                        id-at-msDS-LocalEffectiveDeletionTime }

-- OID written as MSADat4:2060 and expanded with this file's objectidentifier macros.
msDS-LocalEffectiveRecycleTime ATTRIBUTE ::= {
  WITH SYNTAX               GeneralizedTime
  SINGLE VALUE              TRUE
  NO USER MODIFICATION      TRUE
  LDAP-SYNTAX               generalizedTime.&id
  LDAP-NAME                 {"msDS-LocalEffectiveRecycleTime"}
  ID                        id-at-msDS-LocalEffectiveRecycleTime }

-- OID written as MSADat4:2067 and expanded with this file's objectidentifier macros.
msDS-LastKnownRDN ATTRIBUTE ::= {
  WITH SYNTAX               UnboundedDirectoryString
  SINGLE VALUE              TRUE
  NO USER MODIFICATION      TRUE
  LDAP-SYNTAX               directoryString.&id
  LDAP-NAME                 {"msDS-LastKnownRDN"}
  ID                        id-at-msDS-LastKnownRDN }

-- OID written as MSADat4:2069 and expanded with this file's objectidentifier macros.
msDS-EnabledFeatureBL ATTRIBUTE ::= {
  WITH SYNTAX               DistinguishedName
  NO USER MODIFICATION      TRUE
  LDAP-SYNTAX               dn.&id
  LDAP-NAME                 {"msDS-EnabledFeatureBL"}
  ID                        id-at-msDS-EnabledFeatureBL }

-- OID written as MSADat4:2102 and expanded with this file's objectidentifier macros.
msDS-ClaimSharesPossibleValuesWithBL ATTRIBUTE ::= {
  WITH SYNTAX               DistinguishedName
  LDAP-SYNTAX               dn.&id
  LDAP-NAME                 {"msDS-ClaimSharesPossibleValuesWithBL"}
  ID                        id-at-msDS-ClaimSharesPossibleValuesWithBL }

-- OID written as MSADat4:2104 and expanded with this file's objectidentifier macros.
msDS-MembersOfResourcePropertyListBL ATTRIBUTE ::= {
  WITH SYNTAX               DistinguishedName
  LDAP-SYNTAX               dn.&id
  LDAP-NAME                 {"msDS-MembersOfResourcePropertyListBL"}
  ID                        id-at-msDS-MembersOfResourcePropertyListBL }

-- OID written as MSADat4:2168 and expanded with this file's objectidentifier macros.
msDS-IsPrimaryComputerFor ATTRIBUTE ::= {
  WITH SYNTAX               DistinguishedName
  LDAP-SYNTAX               dn.&id
  LDAP-NAME                 {"msDS-IsPrimaryComputerFor"}
  ID                        id-at-msDS-IsPrimaryComputerFor }

-- OID written as MSADat4:2188 and expanded with this file's objectidentifier macros.
msDS-ValueTypeReferenceBL ATTRIBUTE ::= {
  WITH SYNTAX               DistinguishedName
  NO USER MODIFICATION      TRUE
  LDAP-SYNTAX               dn.&id
  LDAP-NAME                 {"msDS-ValueTypeReferenceBL"}
  ID                        id-at-msDS-ValueTypeReferenceBL }

-- OID written as MSADat4:2193 and expanded with this file's objectidentifier macros.
msDS-TDOIngressBL ATTRIBUTE ::= {
  WITH SYNTAX               DistinguishedName
  NO USER MODIFICATION      TRUE
  LDAP-SYNTAX               dn.&id
  LDAP-NAME                 {"msDS-TDOIngressBL"}
  ID                        id-at-msDS-TDOIngressBL }

-- OID written as MSADat4:2194 and expanded with this file's objectidentifier macros.
msDS-TDOEgressBL ATTRIBUTE ::= {
  WITH SYNTAX               DistinguishedName
  NO USER MODIFICATION      TRUE
  LDAP-SYNTAX               dn.&id
  LDAP-NAME                 {"msDS-TDOEgressBL"}
  ID                        id-at-msDS-TDOEgressBL }

-- OID written as MSADat4:2203 and expanded with this file's objectidentifier macros.
msDS-parentdistname ATTRIBUTE ::= {
  WITH SYNTAX               DistinguishedName
  SINGLE VALUE              TRUE
  NO USER MODIFICATION      TRUE
  LDAP-SYNTAX               dn.&id
  LDAP-NAME                 {"msDS-parentdistname"}
  ID                        id-at-msDS-parentdistname }

-- OID written as MSADat4:2235 and expanded with this file's objectidentifier macros.
msDS-ReplValueMetaDataExt ATTRIBUTE ::= {
  WITH SYNTAX               UnboundedDirectoryString
  LDAP-SYNTAX               directoryString.&id
  LDAP-NAME                 {"msDS-ReplValueMetaDataExt"}
  ID                        id-at-msDS-ReplValueMetaDataExt }

-- OID written as MSADat4:2236 and expanded with this file's objectidentifier macros.
msds-memberOfTransitive ATTRIBUTE ::= {
  WITH SYNTAX               DistinguishedName
  NO USER MODIFICATION      TRUE
  LDAP-SYNTAX               dn.&id
  LDAP-NAME                 {"msds-memberOfTransitive"}
  ID                        id-at-msds-memberOfTransitive }

-- OID written as MSADat4:2238 and expanded with this file's objectidentifier macros.
msds-memberTransitive ATTRIBUTE ::= {
  WITH SYNTAX               DistinguishedName
  NO USER MODIFICATION      TRUE
  LDAP-SYNTAX               dn.&id
  LDAP-NAME                 {"msds-memberTransitive"}
  ID                        id-at-msds-memberTransitive }

-- OID written as MSADat6:18.1.347 and expanded with this file's objectidentifier macros.
msSFU30PosixMemberOf ATTRIBUTE ::= {
  WITH SYNTAX               DistinguishedName
  LDAP-SYNTAX               dn.&id
  LDAP-NAME                 {"msSFU30PosixMemberOf"}
  ID                        id-at-msSFU30PosixMemberOf }

-- OID written as MSADat6:13.3.102 and expanded with this file's objectidentifier macros.
msDFSR-MemberReferenceBL ATTRIBUTE ::= {
  WITH SYNTAX               DistinguishedName
  LDAP-SYNTAX               dn.&id
  LDAP-NAME                 {"msDFSR-MemberReferenceBL"}
  ID                        id-at-msDFSR-MemberReferenceBL }

-- OID written as MSADat6:13.3.103 and expanded with this file's objectidentifier macros.
msDFSR-ComputerReferenceBL ATTRIBUTE ::= {
  WITH SYNTAX               DistinguishedName
  LDAP-SYNTAX               dn.&id
  LDAP-NAME                 {"msDFSR-ComputerReferenceBL"}
  ID                        id-at-msDFSR-ComputerReferenceBL }

-- OID written as MSADat4:1792 and expanded with this file's objectidentifier macros.
msDS-AzLDAPQuery ATTRIBUTE ::= {
  WITH SYNTAX               UnboundedDirectoryString
  SINGLE VALUE              TRUE
  LDAP-SYNTAX               directoryString.&id
  LDAP-NAME                 {"msDS-AzLDAPQuery"}
  ID                        id-at-msDS-AzLDAPQuery }

-- OID written as MSADat4:1801 and expanded with this file's objectidentifier macros.
msDS-AzBizRule ATTRIBUTE ::= {
  WITH SYNTAX               UnboundedDirectoryString
  SINGLE VALUE              TRUE
  LDAP-SYNTAX               directoryString.&id
  LDAP-NAME                 {"msDS-AzBizRule"}
  ID                        id-at-msDS-AzBizRule }

-- OID written as MSADat4:1802 and expanded with this file's objectidentifier macros.
msDS-AzBizRuleLanguage ATTRIBUTE ::= {
  WITH SYNTAX               UnboundedDirectoryString
  SINGLE VALUE              TRUE
  LDAP-SYNTAX               directoryString.&id
  LDAP-NAME                 {"msDS-AzBizRuleLanguage"}
  ID                        id-at-msDS-AzBizRuleLanguage }

-- OID written as MSADat4:1803 and expanded with this file's objectidentifier macros.
msDS-AzLastImportedBizRulePath ATTRIBUTE ::= {
  WITH SYNTAX               UnboundedDirectoryString
  SINGLE VALUE              TRUE
  LDAP-SYNTAX               directoryString.&id
  LDAP-NAME                 {"msDS-AzLastImportedBizRulePath"}
  ID                        id-at-msDS-AzLastImportedBizRulePath }

-- OID written as MSADat4:1819 and expanded with this file's objectidentifier macros.
msDS-AzApplicationData ATTRIBUTE ::= {
  WITH SYNTAX               UnboundedDirectoryString
  SINGLE VALUE              TRUE
  LDAP-SYNTAX               directoryString.&id
  LDAP-NAME                 {"msDS-AzApplicationData"}
  ID                        id-at-msDS-AzApplicationData }

-- OID written as MSADat4:1949 and expanded with this file's objectidentifier macros.
msDS-AzObjectGuid ATTRIBUTE ::= {
  WITH SYNTAX               OCTET STRING
  SINGLE VALUE              TRUE
  NO USER MODIFICATION      TRUE
  LDAP-SYNTAX               octetString.&id
  LDAP-NAME                 {"msDS-AzObjectGuid"}
  ID                        id-at-msDS-AzObjectGuid }

-- OID written as MSADat4:1950 and expanded with this file's objectidentifier macros.
msDS-AzGenericData ATTRIBUTE ::= {
  WITH SYNTAX               UnboundedDirectoryString
  SINGLE VALUE              TRUE
  LDAP-SYNTAX               directoryString.&id
  LDAP-NAME                 {"msDS-AzGenericData"}
  ID                        id-at-msDS-AzGenericData }

-- OID written as MSADat4:2167 and expanded with this file's objectidentifier macros.
msDS-PrimaryComputer ATTRIBUTE ::= {
  WITH SYNTAX               DistinguishedName
  LDAP-SYNTAX               dn.&id
  LDAP-NAME                 {"msDS-PrimaryComputer"}
  ID                        id-at-msDS-PrimaryComputer }

-- OID written as MSADat6:18.1.309 and expanded with this file's objectidentifier macros.
msSFU30Name ATTRIBUTE ::= {
  WITH SYNTAX               IA5String
  SINGLE VALUE              TRUE
  LDAP-SYNTAX               ia5String.&id
  LDAP-NAME                 {"msSFU30Name"}
  ID                        id-at-msSFU30Name }

-- OID written as MSADat6:18.1.339 and expanded with this file's objectidentifier macros.
msSFU30NisDomain ATTRIBUTE ::= {
  WITH SYNTAX               IA5String
  SINGLE VALUE              TRUE
  LDAP-SYNTAX               ia5String.&id
  LDAP-NAME                 {"msSFU30NisDomain"}
  ID                        id-at-msSFU30NisDomain }

-- OID written as MSADat6:18.1.346 and expanded with this file's objectidentifier macros.
msSFU30PosixMember ATTRIBUTE ::= {
  WITH SYNTAX               DistinguishedName
  LDAP-SYNTAX               dn.&id
  LDAP-NAME                 {"msSFU30PosixMember"}
  ID                        id-at-msSFU30PosixMember }

-- OID written as MSADat4:1426 and expanded with this file's objectidentifier macros.
msCOM-UserPartitionSetLink ATTRIBUTE ::= {
  WITH SYNTAX               DistinguishedName
  SINGLE VALUE              TRUE
  LDAP-SYNTAX               dn.&id
  LDAP-NAME                 {"msCOM-UserPartitionSetLink"}
  ID                        id-at-msCOM-UserPartitionSetLink }

-- OID written as MSADat4:1441 and expanded with this file's objectidentifier macros.
msDS-Cached-Membership ATTRIBUTE ::= {
  WITH SYNTAX               OCTET STRING
  SINGLE VALUE              TRUE
  LDAP-SYNTAX               octetString.&id
  LDAP-NAME                 {"msDS-Cached-Membership"}
  ID                        id-at-msDS-Cached-Membership }

-- OID written as MSADat4:1442 and expanded with this file's objectidentifier macros.
-- SYNTAX MSADlargeInteger expanded to 1.3.6.1.4.1.1466.115.121.1.27 through an objectidentifier macro.
msDS-Cached-Membership-Time-Stamp ATTRIBUTE ::= {
  WITH SYNTAX               INTEGER
  SINGLE VALUE              TRUE
  LDAP-SYNTAX               integer.&id
  LDAP-NAME                 {"msDS-Cached-Membership-Time-Stamp"}
  ID                        id-at-msDS-Cached-Membership-Time-Stamp }

-- OID written as MSADat4:1443 and expanded with this file's objectidentifier macros.
msDS-Site-Affinity ATTRIBUTE ::= {
  WITH SYNTAX               OCTET STRING
  LDAP-SYNTAX               octetString.&id
  LDAP-NAME                 {"msDS-Site-Affinity"}
  ID                        id-at-msDS-Site-Affinity }

-- OID written as MSADat4:1460 and expanded with this file's objectidentifier macros.
msDS-User-Account-Control-Computed ATTRIBUTE ::= {
  WITH SYNTAX               INTEGER
  SINGLE VALUE              TRUE
  LDAP-SYNTAX               integer.&id
  LDAP-NAME                 {"msDS-User-Account-Control-Computed"}
  ID                        id-at-msDS-User-Account-Control-Computed }

-- OID written as MSADat4:1696 and expanded with this file's objectidentifier macros.
-- SYNTAX MSADlargeInteger expanded to 1.3.6.1.4.1.1466.115.121.1.27 through an objectidentifier macro.
lastLogonTimestamp ATTRIBUTE ::= {
  WITH SYNTAX               INTEGER
  SINGLE VALUE              TRUE
  LDAP-SYNTAX               integer.&id
  LDAP-NAME                 {"lastLogonTimestamp"}
  ID                        id-at-lastLogonTimestamp }

-- OID written as MSADat4:1785 and expanded with this file's objectidentifier macros.
msIIS-FTPRoot ATTRIBUTE ::= {
  WITH SYNTAX               UnboundedDirectoryString
  SINGLE VALUE              TRUE
  LDAP-SYNTAX               directoryString.&id
  LDAP-NAME                 {"msIIS-FTPRoot"}
  ID                        id-at-msIIS-FTPRoot }

-- OID written as MSADat4:1786 and expanded with this file's objectidentifier macros.
msIIS-FTPDir ATTRIBUTE ::= {
  WITH SYNTAX               UnboundedDirectoryString
  SINGLE VALUE              TRUE
  LDAP-SYNTAX               directoryString.&id
  LDAP-NAME                 {"msIIS-FTPDir"}
  ID                        id-at-msIIS-FTPDir }

-- OID written as MSADat4:1843 and expanded with this file's objectidentifier macros.
msDRM-IdentityCertificate ATTRIBUTE ::= {
  WITH SYNTAX               OCTET STRING
  LDAP-SYNTAX               octetString.&id
  LDAP-NAME                 {"msDRM-IdentityCertificate"}
  ID                        id-at-msDRM-IdentityCertificate }

-- OID written as MSADat4:1879 and expanded with this file's objectidentifier macros.
msDS-SourceObjectDN ATTRIBUTE ::= {
  WITH SYNTAX               UnboundedDirectoryString
  SINGLE VALUE              TRUE
  LDAP-SYNTAX               directoryString.&id
  LDAP-NAME                 {"msDS-SourceObjectDN"}
  ID                        id-at-msDS-SourceObjectDN }

-- OID written as MSADat4:1892 and expanded with this file's objectidentifier macros.
msPKIRoamingTimeStamp ATTRIBUTE ::= {
  WITH SYNTAX               OCTET STRING
  SINGLE VALUE              TRUE
  LDAP-SYNTAX               octetString.&id
  LDAP-NAME                 {"msPKIRoamingTimeStamp"}
  ID                        id-at-msPKIRoamingTimeStamp }

-- OID written as MSADat4:1893 and expanded with this file's objectidentifier macros.
-- SYNTAX MSADdnWithOctetString expanded to 1.3.6.1.4.1.1466.115.121.1.40 through an objectidentifier macro.
msPKIDPAPIMasterKeys ATTRIBUTE ::= {
  WITH SYNTAX               OCTET STRING
  LDAP-SYNTAX               octetString.&id
  LDAP-NAME                 {"msPKIDPAPIMasterKeys"}
  ID                        id-at-msPKIDPAPIMasterKeys }

-- OID written as MSADat4:1894 and expanded with this file's objectidentifier macros.
-- SYNTAX MSADdnWithOctetString expanded to 1.3.6.1.4.1.1466.115.121.1.40 through an objectidentifier macro.
msPKIAccountCredentials ATTRIBUTE ::= {
  WITH SYNTAX               OCTET STRING
  LDAP-SYNTAX               octetString.&id
  LDAP-NAME                 {"msPKIAccountCredentials"}
  ID                        id-at-msPKIAccountCredentials }

-- OID written as MSADat4:1913 and expanded with this file's objectidentifier macros.
msRADIUS-FramedInterfaceId ATTRIBUTE ::= {
  WITH SYNTAX               IA5String
  SINGLE VALUE              TRUE
  LDAP-SYNTAX               ia5String.&id
  LDAP-NAME                 {"msRADIUS-FramedInterfaceId"}
  ID                        id-at-msRADIUS-FramedInterfaceId }

-- OID written as MSADat4:1914 and expanded with this file's objectidentifier macros.
msRADIUS-SavedFramedInterfaceId ATTRIBUTE ::= {
  WITH SYNTAX               IA5String
  SINGLE VALUE              TRUE
  LDAP-SYNTAX               ia5String.&id
  LDAP-NAME                 {"msRADIUS-SavedFramedInterfaceId"}
  ID                        id-at-msRADIUS-SavedFramedInterfaceId }

-- OID written as MSADat4:1915 and expanded with this file's objectidentifier macros.
msRADIUS-FramedIpv6Prefix ATTRIBUTE ::= {
  WITH SYNTAX               IA5String
  SINGLE VALUE              TRUE
  LDAP-SYNTAX               ia5String.&id
  LDAP-NAME                 {"msRADIUS-FramedIpv6Prefix"}
  ID                        id-at-msRADIUS-FramedIpv6Prefix }

-- OID written as MSADat4:1916 and expanded with this file's objectidentifier macros.
msRADIUS-SavedFramedIpv6Prefix ATTRIBUTE ::= {
  WITH SYNTAX               IA5String
  SINGLE VALUE              TRUE
  LDAP-SYNTAX               ia5String.&id
  LDAP-NAME                 {"msRADIUS-SavedFramedIpv6Prefix"}
  ID                        id-at-msRADIUS-SavedFramedIpv6Prefix }

-- OID written as MSADat4:1917 and expanded with this file's objectidentifier macros.
msRADIUS-FramedIpv6Route ATTRIBUTE ::= {
  WITH SYNTAX               IA5String
  LDAP-SYNTAX               ia5String.&id
  LDAP-NAME                 {"msRADIUS-FramedIpv6Route"}
  ID                        id-at-msRADIUS-FramedIpv6Route }

-- OID written as MSADat4:1918 and expanded with this file's objectidentifier macros.
msRADIUS-SavedFramedIpv6Route ATTRIBUTE ::= {
  WITH SYNTAX               IA5String
  LDAP-SYNTAX               ia5String.&id
  LDAP-NAME                 {"msRADIUS-SavedFramedIpv6Route"}
  ID                        id-at-msRADIUS-SavedFramedIpv6Route }

-- OID written as MSADat4:1929 and expanded with this file's objectidentifier macros.
msDS-SecondaryKrbTgtNumber ATTRIBUTE ::= {
  WITH SYNTAX               INTEGER
  SINGLE VALUE              TRUE
  NO USER MODIFICATION      TRUE
  LDAP-SYNTAX               integer.&id
  LDAP-NAME                 {"msDS-SecondaryKrbTgtNumber"}
  ID                        id-at-msDS-SecondaryKrbTgtNumber }

-- OID written as MSADat4:1963 and expanded with this file's objectidentifier macros.
msDS-SupportedEncryptionTypes ATTRIBUTE ::= {
  WITH SYNTAX               INTEGER
  SINGLE VALUE              TRUE
  LDAP-SYNTAX               integer.&id
  LDAP-NAME                 {"msDS-SupportedEncryptionTypes"}
  ID                        id-at-msDS-SupportedEncryptionTypes }

-- OID written as MSADat4:1970 and expanded with this file's objectidentifier macros.
-- SYNTAX MSADlargeInteger expanded to 1.3.6.1.4.1.1466.115.121.1.27 through an objectidentifier macro.
msDS-LastSuccessfulInteractiveLogonTime ATTRIBUTE ::= {
  WITH SYNTAX               INTEGER
  SINGLE VALUE              TRUE
  NO USER MODIFICATION      TRUE
  LDAP-SYNTAX               integer.&id
  LDAP-NAME                 {"msDS-LastSuccessfulInteractiveLogonTime"}
  ID                        id-at-msDS-LastSuccessfulInteractiveLogonTime }

-- OID written as MSADat4:1971 and expanded with this file's objectidentifier macros.
-- SYNTAX MSADlargeInteger expanded to 1.3.6.1.4.1.1466.115.121.1.27 through an objectidentifier macro.
msDS-LastFailedInteractiveLogonTime ATTRIBUTE ::= {
  WITH SYNTAX               INTEGER
  SINGLE VALUE              TRUE
  NO USER MODIFICATION      TRUE
  LDAP-SYNTAX               integer.&id
  LDAP-NAME                 {"msDS-LastFailedInteractiveLogonTime"}
  ID                        id-at-msDS-LastFailedInteractiveLogonTime }

-- OID written as MSADat4:1972 and expanded with this file's objectidentifier macros.
msDS-FailedInteractiveLogonCount ATTRIBUTE ::= {
  WITH SYNTAX               INTEGER
  SINGLE VALUE              TRUE
  NO USER MODIFICATION      TRUE
  LDAP-SYNTAX               integer.&id
  LDAP-NAME                 {"msDS-FailedInteractiveLogonCount"}
  ID                        id-at-msDS-FailedInteractiveLogonCount }

-- OID written as MSADat4:1973 and expanded with this file's objectidentifier macros.
msDS-FailedInteractiveLogonCountAtLastSuccessfulLogon ATTRIBUTE ::= {
  WITH SYNTAX               INTEGER
  SINGLE VALUE              TRUE
  NO USER MODIFICATION      TRUE
  LDAP-SYNTAX               integer.&id
  LDAP-NAME                 {"msDS-FailedInteractiveLogonCountAtLastSuccessfulLogon"}
  ID                        id-at-msDS-FailedInteractiveLogonCountAtLastSuccessfulLogon }

-- OID written as MSADat4:1976 and expanded with this file's objectidentifier macros.
msTSProfilePath ATTRIBUTE ::= {
  WITH SYNTAX               UnboundedDirectoryString
  SINGLE VALUE              TRUE
  LDAP-SYNTAX               directoryString.&id
  LDAP-NAME                 {"msTSProfilePath"}
  ID                        id-at-msTSProfilePath }

-- OID written as MSADat4:1977 and expanded with this file's objectidentifier macros.
msTSHomeDirectory ATTRIBUTE ::= {
  WITH SYNTAX               UnboundedDirectoryString
  SINGLE VALUE              TRUE
  LDAP-SYNTAX               directoryString.&id
  LDAP-NAME                 {"msTSHomeDirectory"}
  ID                        id-at-msTSHomeDirectory }

-- OID written as MSADat4:1978 and expanded with this file's objectidentifier macros.
msTSHomeDrive ATTRIBUTE ::= {
  WITH SYNTAX               UnboundedDirectoryString
  SINGLE VALUE              TRUE
  LDAP-SYNTAX               directoryString.&id
  LDAP-NAME                 {"msTSHomeDrive"}
  ID                        id-at-msTSHomeDrive }

-- OID written as MSADat4:1979 and expanded with this file's objectidentifier macros.
msTSAllowLogon ATTRIBUTE ::= {
  WITH SYNTAX               BOOLEAN
  SINGLE VALUE              TRUE
  LDAP-SYNTAX               boolean.&id
  LDAP-NAME                 {"msTSAllowLogon"}
  ID                        id-at-msTSAllowLogon }

-- OID written as MSADat4:1980 and expanded with this file's objectidentifier macros.
msTSRemoteControl ATTRIBUTE ::= {
  WITH SYNTAX               INTEGER
  SINGLE VALUE              TRUE
  LDAP-SYNTAX               integer.&id
  LDAP-NAME                 {"msTSRemoteControl"}
  ID                        id-at-msTSRemoteControl }

-- OID written as MSADat4:1981 and expanded with this file's objectidentifier macros.
msTSMaxDisconnectionTime ATTRIBUTE ::= {
  WITH SYNTAX               INTEGER
  SINGLE VALUE              TRUE
  LDAP-SYNTAX               integer.&id
  LDAP-NAME                 {"msTSMaxDisconnectionTime"}
  ID                        id-at-msTSMaxDisconnectionTime }

-- OID written as MSADat4:1982 and expanded with this file's objectidentifier macros.
msTSMaxConnectionTime ATTRIBUTE ::= {
  WITH SYNTAX               INTEGER
  SINGLE VALUE              TRUE
  LDAP-SYNTAX               integer.&id
  LDAP-NAME                 {"msTSMaxConnectionTime"}
  ID                        id-at-msTSMaxConnectionTime }

-- OID written as MSADat4:1983 and expanded with this file's objectidentifier macros.
msTSMaxIdleTime ATTRIBUTE ::= {
  WITH SYNTAX               INTEGER
  SINGLE VALUE              TRUE
  LDAP-SYNTAX               integer.&id
  LDAP-NAME                 {"msTSMaxIdleTime"}
  ID                        id-at-msTSMaxIdleTime }

-- OID written as MSADat4:1984 and expanded with this file's objectidentifier macros.
msTSReconnectionAction ATTRIBUTE ::= {
  WITH SYNTAX               BOOLEAN
  SINGLE VALUE              TRUE
  LDAP-SYNTAX               boolean.&id
  LDAP-NAME                 {"msTSReconnectionAction"}
  ID                        id-at-msTSReconnectionAction }

-- OID written as MSADat4:1985 and expanded with this file's objectidentifier macros.
msTSBrokenConnectionAction ATTRIBUTE ::= {
  WITH SYNTAX               BOOLEAN
  SINGLE VALUE              TRUE
  LDAP-SYNTAX               boolean.&id
  LDAP-NAME                 {"msTSBrokenConnectionAction"}
  ID                        id-at-msTSBrokenConnectionAction }

-- OID written as MSADat4:1986 and expanded with this file's objectidentifier macros.
msTSConnectClientDrives ATTRIBUTE ::= {
  WITH SYNTAX               BOOLEAN
  SINGLE VALUE              TRUE
  LDAP-SYNTAX               boolean.&id
  LDAP-NAME                 {"msTSConnectClientDrives"}
  ID                        id-at-msTSConnectClientDrives }

-- OID written as MSADat4:1987 and expanded with this file's objectidentifier macros.
msTSConnectPrinterDrives ATTRIBUTE ::= {
  WITH SYNTAX               BOOLEAN
  SINGLE VALUE              TRUE
  LDAP-SYNTAX               boolean.&id
  LDAP-NAME                 {"msTSConnectPrinterDrives"}
  ID                        id-at-msTSConnectPrinterDrives }

-- OID written as MSADat4:1988 and expanded with this file's objectidentifier macros.
msTSDefaultToMainPrinter ATTRIBUTE ::= {
  WITH SYNTAX               BOOLEAN
  SINGLE VALUE              TRUE
  LDAP-SYNTAX               boolean.&id
  LDAP-NAME                 {"msTSDefaultToMainPrinter"}
  ID                        id-at-msTSDefaultToMainPrinter }

-- OID written as MSADat4:1989 and expanded with this file's objectidentifier macros.
msTSWorkDirectory ATTRIBUTE ::= {
  WITH SYNTAX               UnboundedDirectoryString
  SINGLE VALUE              TRUE
  LDAP-SYNTAX               directoryString.&id
  LDAP-NAME                 {"msTSWorkDirectory"}
  ID                        id-at-msTSWorkDirectory }

-- OID written as MSADat4:1990 and expanded with this file's objectidentifier macros.
msTSInitialProgram ATTRIBUTE ::= {
  WITH SYNTAX               UnboundedDirectoryString
  SINGLE VALUE              TRUE
  LDAP-SYNTAX               directoryString.&id
  LDAP-NAME                 {"msTSInitialProgram"}
  ID                        id-at-msTSInitialProgram }

-- OID written as MSADat4:1991 and expanded with this file's objectidentifier macros.
msTSProperty01 ATTRIBUTE ::= {
  WITH SYNTAX               UnboundedDirectoryString
  LDAP-SYNTAX               directoryString.&id
  LDAP-NAME                 {"msTSProperty01"}
  ID                        id-at-msTSProperty01 }

-- OID written as MSADat4:1992 and expanded with this file's objectidentifier macros.
msTSProperty02 ATTRIBUTE ::= {
  WITH SYNTAX               UnboundedDirectoryString
  LDAP-SYNTAX               directoryString.&id
  LDAP-NAME                 {"msTSProperty02"}
  ID                        id-at-msTSProperty02 }

-- OID written as MSADat4:1993 and expanded with this file's objectidentifier macros.
msTSExpireDate ATTRIBUTE ::= {
  WITH SYNTAX               GeneralizedTime
  SINGLE VALUE              TRUE
  LDAP-SYNTAX               generalizedTime.&id
  LDAP-NAME                 {"msTSExpireDate"}
  ID                        id-at-msTSExpireDate }

-- OID written as MSADat4:1994 and expanded with this file's objectidentifier macros.
msTSLicenseVersion ATTRIBUTE ::= {
  WITH SYNTAX               UnboundedDirectoryString
  SINGLE VALUE              TRUE
  LDAP-SYNTAX               directoryString.&id
  LDAP-NAME                 {"msTSLicenseVersion"}
  ID                        id-at-msTSLicenseVersion }

-- OID written as MSADat4:1995 and expanded with this file's objectidentifier macros.
msTSManagingLS ATTRIBUTE ::= {
  WITH SYNTAX               UnboundedDirectoryString
  SINGLE VALUE              TRUE
  LDAP-SYNTAX               directoryString.&id
  LDAP-NAME                 {"msTSManagingLS"}
  ID                        id-at-msTSManagingLS }

-- OID written as MSADat4:1996 and expanded with this file's objectidentifier macros.
-- SYNTAX MSADlargeInteger expanded to 1.3.6.1.4.1.1466.115.121.1.27 through an objectidentifier macro.
msDS-UserPasswordExpiryTimeComputed ATTRIBUTE ::= {
  WITH SYNTAX               INTEGER
  SINGLE VALUE              TRUE
  LDAP-SYNTAX               integer.&id
  LDAP-NAME                 {"msDS-UserPasswordExpiryTimeComputed"}
  ID                        id-at-msDS-UserPasswordExpiryTimeComputed }

-- OID written as MSADat4:2008 and expanded with this file's objectidentifier macros.
msTSManagingLS4 ATTRIBUTE ::= {
  WITH SYNTAX               UnboundedDirectoryString
  SINGLE VALUE              TRUE
  LDAP-SYNTAX               directoryString.&id
  LDAP-NAME                 {"msTSManagingLS4"}
  ID                        id-at-msTSManagingLS4 }

-- OID written as MSADat4:2005 and expanded with this file's objectidentifier macros.
msTSManagingLS3 ATTRIBUTE ::= {
  WITH SYNTAX               UnboundedDirectoryString
  SINGLE VALUE              TRUE
  LDAP-SYNTAX               directoryString.&id
  LDAP-NAME                 {"msTSManagingLS3"}
  ID                        id-at-msTSManagingLS3 }

-- OID written as MSADat4:2002 and expanded with this file's objectidentifier macros.
msTSManagingLS2 ATTRIBUTE ::= {
  WITH SYNTAX               UnboundedDirectoryString
  SINGLE VALUE              TRUE
  LDAP-SYNTAX               directoryString.&id
  LDAP-NAME                 {"msTSManagingLS2"}
  ID                        id-at-msTSManagingLS2 }

-- OID written as MSADat4:2006 and expanded with this file's objectidentifier macros.
msTSExpireDate4 ATTRIBUTE ::= {
  WITH SYNTAX               GeneralizedTime
  SINGLE VALUE              TRUE
  LDAP-SYNTAX               generalizedTime.&id
  LDAP-NAME                 {"msTSExpireDate4"}
  ID                        id-at-msTSExpireDate4 }

-- OID written as MSADat4:2003 and expanded with this file's objectidentifier macros.
msTSExpireDate3 ATTRIBUTE ::= {
  WITH SYNTAX               GeneralizedTime
  SINGLE VALUE              TRUE
  LDAP-SYNTAX               generalizedTime.&id
  LDAP-NAME                 {"msTSExpireDate3"}
  ID                        id-at-msTSExpireDate3 }

-- OID written as MSADat4:2000 and expanded with this file's objectidentifier macros.
msTSExpireDate2 ATTRIBUTE ::= {
  WITH SYNTAX               GeneralizedTime
  SINGLE VALUE              TRUE
  LDAP-SYNTAX               generalizedTime.&id
  LDAP-NAME                 {"msTSExpireDate2"}
  ID                        id-at-msTSExpireDate2 }

-- OID written as MSADat4:2004 and expanded with this file's objectidentifier macros.
msTSLicenseVersion3 ATTRIBUTE ::= {
  WITH SYNTAX               UnboundedDirectoryString
  SINGLE VALUE              TRUE
  LDAP-SYNTAX               directoryString.&id
  LDAP-NAME                 {"msTSLicenseVersion3"}
  ID                        id-at-msTSLicenseVersion3 }

-- OID written as MSADat4:2001 and expanded with this file's objectidentifier macros.
msTSLicenseVersion2 ATTRIBUTE ::= {
  WITH SYNTAX               UnboundedDirectoryString
  SINGLE VALUE              TRUE
  LDAP-SYNTAX               directoryString.&id
  LDAP-NAME                 {"msTSLicenseVersion2"}
  ID                        id-at-msTSLicenseVersion2 }

-- OID written as MSADat4:2007 and expanded with this file's objectidentifier macros.
msTSLicenseVersion4 ATTRIBUTE ::= {
  WITH SYNTAX               UnboundedDirectoryString
  SINGLE VALUE              TRUE
  LDAP-SYNTAX               directoryString.&id
  LDAP-NAME                 {"msTSLicenseVersion4"}
  ID                        id-at-msTSLicenseVersion4 }

-- OID written as MSADat4:2009 and expanded with this file's objectidentifier macros.
msTSLSProperty01 ATTRIBUTE ::= {
  WITH SYNTAX               UnboundedDirectoryString
  LDAP-SYNTAX               directoryString.&id
  LDAP-NAME                 {"msTSLSProperty01"}
  ID                        id-at-msTSLSProperty01 }

-- OID written as MSADat4:2010 and expanded with this file's objectidentifier macros.
msTSLSProperty02 ATTRIBUTE ::= {
  WITH SYNTAX               UnboundedDirectoryString
  LDAP-SYNTAX               directoryString.&id
  LDAP-NAME                 {"msTSLSProperty02"}
  ID                        id-at-msTSLSProperty02 }

-- OID written as MSADat4:2022 and expanded with this file's objectidentifier macros.
msDS-ResultantPSO ATTRIBUTE ::= {
  WITH SYNTAX               DistinguishedName
  SINGLE VALUE              TRUE
  NO USER MODIFICATION      TRUE
  LDAP-SYNTAX               dn.&id
  LDAP-NAME                 {"msDS-ResultantPSO"}
  ID                        id-at-msDS-ResultantPSO }

-- OID written as MSADat4:2050 and expanded with this file's objectidentifier macros.
-- SYNTAX MSADdnWithOctetString expanded to 1.3.6.1.4.1.1466.115.121.1.40 through an objectidentifier macro.
msPKI-CredentialRoamingTokens ATTRIBUTE ::= {
  WITH SYNTAX               OCTET STRING
  LDAP-SYNTAX               octetString.&id
  LDAP-NAME                 {"msPKI-CredentialRoamingTokens"}
  ID                        id-at-msPKI-CredentialRoamingTokens }

-- OID written as MSADat4:2073 and expanded with this file's objectidentifier macros.
msTSPrimaryDesktop ATTRIBUTE ::= {
  WITH SYNTAX               DistinguishedName
  SINGLE VALUE              TRUE
  LDAP-SYNTAX               dn.&id
  LDAP-NAME                 {"msTSPrimaryDesktop"}
  ID                        id-at-msTSPrimaryDesktop }

-- OID written as MSADat4:2075 and expanded with this file's objectidentifier macros.
msTSSecondaryDesktops ATTRIBUTE ::= {
  WITH SYNTAX               DistinguishedName
  LDAP-SYNTAX               dn.&id
  LDAP-NAME                 {"msTSSecondaryDesktops"}
  ID                        id-at-msTSSecondaryDesktops }

-- OID written as MSADat4:2276 and expanded with this file's objectidentifier macros.
msDS-SyncServerUrl ATTRIBUTE ::= {
  WITH SYNTAX               UnboundedDirectoryString
  LDAP-SYNTAX               directoryString.&id
  LDAP-NAME                 {"msDS-SyncServerUrl"}
  ID                        id-at-msDS-SyncServerUrl }

-- OID written as MSADat4:2285 and expanded with this file's objectidentifier macros.
msDS-AssignedAuthNPolicySilo ATTRIBUTE ::= {
  WITH SYNTAX               DistinguishedName
  SINGLE VALUE              TRUE
  LDAP-SYNTAX               dn.&id
  LDAP-NAME                 {"msDS-AssignedAuthNPolicySilo"}
  ID                        id-at-msDS-AssignedAuthNPolicySilo }

-- OID written as MSADat4:2288 and expanded with this file's objectidentifier macros.
msDS-AuthNPolicySiloMembersBL ATTRIBUTE ::= {
  WITH SYNTAX               DistinguishedName
  NO USER MODIFICATION      TRUE
  LDAP-SYNTAX               dn.&id
  LDAP-NAME                 {"msDS-AuthNPolicySiloMembersBL"}
  ID                        id-at-msDS-AuthNPolicySiloMembersBL }

-- OID written as MSADat4:2295 and expanded with this file's objectidentifier macros.
msDS-AssignedAuthNPolicy ATTRIBUTE ::= {
  WITH SYNTAX               DistinguishedName
  SINGLE VALUE              TRUE
  LDAP-SYNTAX               dn.&id
  LDAP-NAME                 {"msDS-AssignedAuthNPolicy"}
  ID                        id-at-msDS-AssignedAuthNPolicy }

-- OID written as MSADat4:1717 and expanded with this file's objectidentifier macros.
msDS-AdditionalDnsHostName ATTRIBUTE ::= {
  WITH SYNTAX               UnboundedDirectoryString
  NO USER MODIFICATION      TRUE
  LDAP-SYNTAX               directoryString.&id
  LDAP-NAME                 {"msDS-AdditionalDnsHostName"}
  ID                        id-at-msDS-AdditionalDnsHostName }

-- OID written as MSADat4:1718 and expanded with this file's objectidentifier macros.
msDS-AdditionalSamAccountName ATTRIBUTE ::= {
  WITH SYNTAX               UnboundedDirectoryString
  LDAP-SYNTAX               directoryString.&id
  LDAP-NAME                 {"msDS-AdditionalSamAccountName"}
  ID                        id-at-msDS-AdditionalSamAccountName }

-- OID written as MSADat4:1783 and expanded with this file's objectidentifier macros.
msDS-ExecuteScriptPassword ATTRIBUTE ::= {
  WITH SYNTAX               OCTET STRING
  SINGLE VALUE              TRUE
  NO USER MODIFICATION      TRUE
  LDAP-SYNTAX               octetString.&id
  LDAP-NAME                 {"msDS-ExecuteScriptPassword"}
  ID                        id-at-msDS-ExecuteScriptPassword }

-- OID written as MSADat4:1923 and expanded with this file's objectidentifier macros.
msDS-KrbTgtLink ATTRIBUTE ::= {
  WITH SYNTAX               DistinguishedName
  SINGLE VALUE              TRUE
  LDAP-SYNTAX               dn.&id
  LDAP-NAME                 {"msDS-KrbTgtLink"}
  ID                        id-at-msDS-KrbTgtLink }

-- OID written as MSADat4:1924 and expanded with this file's objectidentifier macros.
-- SYNTAX MSADdnWithOctetString expanded to 1.3.6.1.4.1.1466.115.121.1.40 through an objectidentifier macro.
msDS-RevealedUsers ATTRIBUTE ::= {
  WITH SYNTAX               OCTET STRING
  NO USER MODIFICATION      TRUE
  LDAP-SYNTAX               octetString.&id
  LDAP-NAME                 {"msDS-RevealedUsers"}
  ID                        id-at-msDS-RevealedUsers }

-- OID written as MSADat4:1926 and expanded with this file's objectidentifier macros.
msDS-NeverRevealGroup ATTRIBUTE ::= {
  WITH SYNTAX               DistinguishedName
  LDAP-SYNTAX               dn.&id
  LDAP-NAME                 {"msDS-NeverRevealGroup"}
  ID                        id-at-msDS-NeverRevealGroup }

-- OID written as MSADat4:1928 and expanded with this file's objectidentifier macros.
msDS-RevealOnDemandGroup ATTRIBUTE ::= {
  WITH SYNTAX               DistinguishedName
  LDAP-SYNTAX               dn.&id
  LDAP-NAME                 {"msDS-RevealOnDemandGroup"}
  ID                        id-at-msDS-RevealOnDemandGroup }

-- OID written as MSADat4:1940 and expanded with this file's objectidentifier macros.
-- SYNTAX MSADdnWithString expanded to 1.3.6.1.4.1.1466.115.121.1.40 through an objectidentifier macro.
msDS-RevealedList ATTRIBUTE ::= {
  WITH SYNTAX               OCTET STRING
  NO USER MODIFICATION      TRUE
  LDAP-SYNTAX               octetString.&id
  LDAP-NAME                 {"msDS-RevealedList"}
  ID                        id-at-msDS-RevealedList }

-- OID written as MSADat4:1959 and expanded with this file's objectidentifier macros.
msDS-isGC ATTRIBUTE ::= {
  WITH SYNTAX               BOOLEAN
  SINGLE VALUE              TRUE
  LDAP-SYNTAX               boolean.&id
  LDAP-NAME                 {"msDS-isGC"}
  ID                        id-at-msDS-isGC }

-- OID written as MSADat4:1960 and expanded with this file's objectidentifier macros.
msDS-isRODC ATTRIBUTE ::= {
  WITH SYNTAX               BOOLEAN
  SINGLE VALUE              TRUE
  LDAP-SYNTAX               boolean.&id
  LDAP-NAME                 {"msDS-isRODC"}
  ID                        id-at-msDS-isRODC }

-- OID written as MSADat4:1961 and expanded with this file's objectidentifier macros.
msDS-SiteName ATTRIBUTE ::= {
  WITH SYNTAX               UnboundedDirectoryString
  SINGLE VALUE              TRUE
  LDAP-SYNTAX               directoryString.&id
  LDAP-NAME                 {"msDS-SiteName"}
  ID                        id-at-msDS-SiteName }

-- OID written as MSADat4:1962 and expanded with this file's objectidentifier macros.
msDS-PromotionSettings ATTRIBUTE ::= {
  WITH SYNTAX               UnboundedDirectoryString
  SINGLE VALUE              TRUE
  NO USER MODIFICATION      TRUE
  LDAP-SYNTAX               directoryString.&id
  LDAP-NAME                 {"msDS-PromotionSettings"}
  ID                        id-at-msDS-PromotionSettings }

-- OID written as MSADat4:1966 and expanded with this file's objectidentifier macros.
msTPM-OwnerInformation ATTRIBUTE ::= {
  WITH SYNTAX               UnboundedDirectoryString
  SINGLE VALUE              TRUE
  LDAP-SYNTAX               directoryString.&id
  LDAP-NAME                 {"msTPM-OwnerInformation"}
  ID                        id-at-msTPM-OwnerInformation }

-- OID written as MSADat4:2025 and expanded with this file's objectidentifier macros.
msDS-IsUserCachableAtRodc ATTRIBUTE ::= {
  WITH SYNTAX               INTEGER
  SINGLE VALUE              TRUE
  LDAP-SYNTAX               integer.&id
  LDAP-NAME                 {"msDS-IsUserCachableAtRodc"}
  ID                        id-at-msDS-IsUserCachableAtRodc }

-- OID written as MSADat4:2056 and expanded with this file's objectidentifier macros.
msDS-HostServiceAccount ATTRIBUTE ::= {
  WITH SYNTAX               DistinguishedName
  LDAP-SYNTAX               dn.&id
  LDAP-NAME                 {"msDS-HostServiceAccount"}
  ID                        id-at-msDS-HostServiceAccount }

-- OID written as MSADat4:2070 and expanded with this file's objectidentifier macros.
msTSEndpointData ATTRIBUTE ::= {
  WITH SYNTAX               UnboundedDirectoryString
  SINGLE VALUE              TRUE
  LDAP-SYNTAX               directoryString.&id
  LDAP-NAME                 {"msTSEndpointData"}
  ID                        id-at-msTSEndpointData }

-- OID written as MSADat4:2071 and expanded with this file's objectidentifier macros.
msTSEndpointType ATTRIBUTE ::= {
  WITH SYNTAX               INTEGER
  SINGLE VALUE              TRUE
  LDAP-SYNTAX               integer.&id
  LDAP-NAME                 {"msTSEndpointType"}
  ID                        id-at-msTSEndpointType }

-- OID written as MSADat4:2072 and expanded with this file's objectidentifier macros.
msTSEndpointPlugin ATTRIBUTE ::= {
  WITH SYNTAX               UnboundedDirectoryString
  SINGLE VALUE              TRUE
  LDAP-SYNTAX               directoryString.&id
  LDAP-NAME                 {"msTSEndpointPlugin"}
  ID                        id-at-msTSEndpointPlugin }

-- OID written as MSADat4:2074 and expanded with this file's objectidentifier macros.
msTSPrimaryDesktopBL ATTRIBUTE ::= {
  WITH SYNTAX               DistinguishedName
  NO USER MODIFICATION      TRUE
  LDAP-SYNTAX               dn.&id
  LDAP-NAME                 {"msTSPrimaryDesktopBL"}
  ID                        id-at-msTSPrimaryDesktopBL }

-- OID written as MSADat4:2078 and expanded with this file's objectidentifier macros.
msTSSecondaryDesktopBL ATTRIBUTE ::= {
  WITH SYNTAX               DistinguishedName
  NO USER MODIFICATION      TRUE
  LDAP-SYNTAX               dn.&id
  LDAP-NAME                 {"msTSSecondaryDesktopBL"}
  ID                        id-at-msTSSecondaryDesktopBL }

-- OID written as MSADat4:2109 and expanded with this file's objectidentifier macros.
msTPM-TpmInformationForComputer ATTRIBUTE ::= {
  WITH SYNTAX               DistinguishedName
  SINGLE VALUE              TRUE
  LDAP-SYNTAX               dn.&id
  LDAP-NAME                 {"msTPM-TpmInformationForComputer"}
  ID                        id-at-msTPM-TpmInformationForComputer }

-- OID written as MSADat4:2166 and expanded with this file's objectidentifier macros.
msDS-GenerationId ATTRIBUTE ::= {
  WITH SYNTAX               OCTET STRING
  SINGLE VALUE              TRUE
  NO USER MODIFICATION      TRUE
  LDAP-SYNTAX               octetString.&id
  LDAP-NAME                 {"msDS-GenerationId"}
  ID                        id-at-msDS-GenerationId }

-- OID written as MSADat4:2180 and expanded with this file's objectidentifier macros.
msImaging-ThumbprintHash ATTRIBUTE ::= {
  WITH SYNTAX               OCTET STRING
  SINGLE VALUE              TRUE
  LDAP-SYNTAX               octetString.&id
  LDAP-NAME                 {"msImaging-ThumbprintHash"}
  ID                        id-at-msImaging-ThumbprintHash }

-- OID written as MSADat4:2181 and expanded with this file's objectidentifier macros.
msImaging-HashAlgorithm ATTRIBUTE ::= {
  WITH SYNTAX               UnboundedDirectoryString
  SINGLE VALUE              TRUE
  LDAP-SYNTAX               directoryString.&id
  LDAP-NAME                 {"msImaging-HashAlgorithm"}
  ID                        id-at-msImaging-HashAlgorithm }

-- OID written as MSADat4:2234 and expanded with this file's objectidentifier macros.
netbootDUID ATTRIBUTE ::= {
  WITH SYNTAX               OCTET STRING
  SINGLE VALUE              TRUE
  LDAP-SYNTAX               octetString.&id
  LDAP-NAME                 {"netbootDUID"}
  ID                        id-at-netbootDUID }

-- OID written as MSADat6:18.1.323 and expanded with this file's objectidentifier macros.
msSFU30Aliases ATTRIBUTE ::= {
  WITH SYNTAX               IA5String
  LDAP-SYNTAX               ia5String.&id
  LDAP-NAME                 {"msSFU30Aliases"}
  ID                        id-at-msSFU30Aliases }

-- OID written as MSADat4:856 and expanded with this file's objectidentifier macros.
netbootNewMachineOU ATTRIBUTE ::= {
  WITH SYNTAX               DistinguishedName
  SINGLE VALUE              TRUE
  LDAP-SYNTAX               dn.&id
  LDAP-NAME                 {"netbootNewMachineOU"}
  ID                        id-at-netbootNewMachineOU }

-- OID written as MSADat4:13 and expanded with this file's objectidentifier macros.
-- SYNTAX MSADlargeInteger expanded to 1.3.6.1.4.1.1466.115.121.1.27 through an objectidentifier macro.
builtinCreationTime ATTRIBUTE ::= {
  WITH SYNTAX               INTEGER
  SINGLE VALUE              TRUE
  LDAP-SYNTAX               integer.&id
  LDAP-NAME                 {"builtinCreationTime"}
  ID                        id-at-builtinCreationTime }

-- OID written as MSADat4:1335 and expanded with this file's objectidentifier macros.
-- SYNTAX MSADcis expanded to 1.3.6.1.4.1.1466.115.121.1.44 through an objectidentifier macro.
pKIEnrollmentAccess ATTRIBUTE ::= {
  WITH SYNTAX               PrintableString
  LDAP-SYNTAX               printableString.&id
  LDAP-NAME                 {"pKIEnrollmentAccess"}
  ID                        id-at-pKIEnrollmentAccess }

-- OID written as MSADat4:1333 and expanded with this file's objectidentifier macros.
pKIExtendedKeyUsage ATTRIBUTE ::= {
  WITH SYNTAX               UnboundedDirectoryString
  LDAP-SYNTAX               directoryString.&id
  LDAP-NAME                 {"pKIExtendedKeyUsage"}
  ID                        id-at-pKIExtendedKeyUsage }

-- OID written as MSADat4:1123 and expanded with this file's objectidentifier macros.
msNPCalledStationID ATTRIBUTE ::= {
  WITH SYNTAX               IA5String
  LDAP-SYNTAX               ia5String.&id
  LDAP-NAME                 {"msNPCalledStationID"}
  ID                        id-at-msNPCalledStationID }

-- OID written as MSADat4:539 and expanded with this file's objectidentifier macros.
initialAuthIncoming ATTRIBUTE ::= {
  WITH SYNTAX               UnboundedDirectoryString
  SINGLE VALUE              TRUE
  LDAP-SYNTAX               directoryString.&id
  LDAP-NAME                 {"initialAuthIncoming"}
  ID                        id-at-initialAuthIncoming }

-- OID written as MSADat2:370 and expanded with this file's objectidentifier macros.
objectClassCategory ATTRIBUTE ::= {
  WITH SYNTAX               INTEGER
  SINGLE VALUE              TRUE
  NO USER MODIFICATION      TRUE
  LDAP-SYNTAX               integer.&id
  LDAP-NAME                 {"objectClassCategory"}
  ID                        id-at-objectClassCategory }

-- OID written as MSADat4:41 and expanded with this file's objectidentifier macros.
generatedConnection ATTRIBUTE ::= {
  WITH SYNTAX               BOOLEAN
  SINGLE VALUE              TRUE
  LDAP-SYNTAX               boolean.&id
  LDAP-NAME                 {"generatedConnection"}
  ID                        id-at-generatedConnection }

-- OID written as MSADat4:911 and expanded with this file's objectidentifier macros.
allowedChildClasses ATTRIBUTE ::= {
  WITH SYNTAX               OBJECT IDENTIFIER
  NO USER MODIFICATION      TRUE
  LDAP-SYNTAX               oid.&id
  LDAP-NAME                 {"allowedChildClasses"}
  ID                        id-at-allowedChildClasses }

-- OID written as MSADat4:68 and expanded with this file's objectidentifier macros.
machineArchitecture ATTRIBUTE ::= {
  WITH SYNTAX               INTEGER
  LDAP-SYNTAX               integer.&id
  LDAP-NAME                 {"machineArchitecture"}
  ID                        id-at-machineArchitecture }

-- OID written as MSADat4:767 and expanded with this file's objectidentifier macros.
-- SYNTAX MSADlargeInteger expanded to 1.3.6.1.4.1.1466.115.121.1.27 through an objectidentifier macro.
aCSMaxPeakBandwidth ATTRIBUTE ::= {
  WITH SYNTAX               INTEGER
  SINGLE VALUE              TRUE
  LDAP-SYNTAX               integer.&id
  LDAP-NAME                 {"aCSMaxPeakBandwidth"}
  ID                        id-at-aCSMaxPeakBandwidth }

-- OID written as MSADat4:72 and expanded with this file's objectidentifier macros.
marshalledInterface ATTRIBUTE ::= {
  WITH SYNTAX               OCTET STRING
  LDAP-SYNTAX               octetString.&id
  LDAP-NAME                 {"marshalledInterface"}
  ID                        id-at-marshalledInterface }

-- OID written as MSADat4:368 and expanded with this file's objectidentifier macros.
rIDManagerReference ATTRIBUTE ::= {
  WITH SYNTAX               DistinguishedName
  SINGLE VALUE              TRUE
  NO USER MODIFICATION      TRUE
  LDAP-SYNTAX               dn.&id
  LDAP-NAME                 {"rIDManagerReference"}
  ID                        id-at-rIDManagerReference }

-- OID written as MSADat4:770 and expanded with this file's objectidentifier macros.
aCSEnableACSService ATTRIBUTE ::= {
  WITH SYNTAX               BOOLEAN
  SINGLE VALUE              TRUE
  LDAP-SYNTAX               boolean.&id
  LDAP-NAME                 {"aCSEnableACSService"}
  ID                        id-at-aCSEnableACSService }

-- OID written as MSADat4:1237 and expanded with this file's objectidentifier macros.
mSMQRoutingService ATTRIBUTE ::= {
  WITH SYNTAX               BOOLEAN
  SINGLE VALUE              TRUE
  LDAP-SYNTAX               boolean.&id
  LDAP-NAME                 {"mSMQRoutingService"}
  ID                        id-at-mSMQRoutingService }

-- OID written as MSADat4:1405 and expanded with this file's objectidentifier macros.
mS-SQL-AllowQueuedUpdatingSubscription ATTRIBUTE ::= {
  WITH SYNTAX               BOOLEAN
  SINGLE VALUE              TRUE
  LDAP-SYNTAX               boolean.&id
  LDAP-NAME                 {"mS-SQL-AllowQueuedUpdatingSubscription"}
  ID                        id-at-mS-SQL-AllowQueuedUpdatingSubscription }

-- OID written as MSADat4:648 and expanded with this file's objectidentifier macros.
primaryTelexNumber ATTRIBUTE ::= {
  WITH SYNTAX               UnboundedDirectoryString
  SINGLE VALUE              TRUE
  LDAP-SYNTAX               directoryString.&id
  LDAP-NAME                 {"primaryTelexNumber"}
  ID                        id-at-primaryTelexNumber }

-- OID written as MSADat4:8 and expanded with this file's objectidentifier macros.
userAccountControl ATTRIBUTE ::= {
  WITH SYNTAX               INTEGER
  SINGLE VALUE              TRUE
  LDAP-SYNTAX               integer.&id
  LDAP-NAME                 {"userAccountControl"}
  ID                        id-at-userAccountControl }

-- OID written as MSADat4:563 and expanded with this file's objectidentifier macros.
shellPropertyPages ATTRIBUTE ::= {
  WITH SYNTAX               UnboundedDirectoryString
  LDAP-SYNTAX               directoryString.&id
  LDAP-NAME                 {"shellPropertyPages"}
  ID                        id-at-shellPropertyPages }

-- OID written as MSADat4:4 and expanded with this file's objectidentifier macros.
replUpToDateVector ATTRIBUTE ::= {
  WITH SYNTAX               OCTET STRING
  SINGLE VALUE              TRUE
  NO USER MODIFICATION      TRUE
  LDAP-SYNTAX               octetString.&id
  LDAP-NAME                 {"replUpToDateVector"}
  ID                        id-at-replUpToDateVector }

-- OID 1.2.840.113556.1.4.484 is also used by calOtherCAPURIs in RFC2739Calendar. The LDAP names differ, so this definition was kept.
-- OID written as MSADat4:484 and expanded with this file's objectidentifier macros.
fRSDirectoryFilter ATTRIBUTE ::= {
  WITH SYNTAX               UnboundedDirectoryString
  SINGLE VALUE              TRUE
  LDAP-SYNTAX               directoryString.&id
  LDAP-NAME                 {"fRSDirectoryFilter"}
  ID                        id-at-fRSDirectoryFilter }

-- OID written as MSADat4:230 and expanded with this file's objectidentifier macros.
printSeparatorFile ATTRIBUTE ::= {
  WITH SYNTAX               UnboundedDirectoryString
  SINGLE VALUE              TRUE
  LDAP-SYNTAX               directoryString.&id
  LDAP-NAME                 {"printSeparatorFile"}
  ID                        id-at-printSeparatorFile }

-- OID written as MSADat4:1329 and expanded with this file's objectidentifier macros.
pKIMaxIssuingDepth ATTRIBUTE ::= {
  WITH SYNTAX               INTEGER
  SINGLE VALUE              TRUE
  LDAP-SYNTAX               integer.&id
  LDAP-NAME                 {"pKIMaxIssuingDepth"}
  ID                        id-at-pKIMaxIssuingDepth }

-- OID written as MSADat4:1307 and expanded with this file's objectidentifier macros.
accountNameHistory ATTRIBUTE ::= {
  WITH SYNTAX               UnboundedDirectoryString
  LDAP-SYNTAX               directoryString.&id
  LDAP-NAME                 {"accountNameHistory"}
  ID                        id-at-accountNameHistory }

-- OID written as MSADat4:1386 and expanded with this file's objectidentifier macros.
mS-SQL-GPSLongitude ATTRIBUTE ::= {
  WITH SYNTAX               UnboundedDirectoryString
  SINGLE VALUE              TRUE
  LDAP-SYNTAX               directoryString.&id
  LDAP-NAME                 {"mS-SQL-GPSLongitude"}
  ID                        id-at-mS-SQL-GPSLongitude }

-- OID written as MSADat4:562 and expanded with this file's objectidentifier macros.
adminPropertyPages ATTRIBUTE ::= {
  WITH SYNTAX               UnboundedDirectoryString
  LDAP-SYNTAX               directoryString.&id
  LDAP-NAME                 {"adminPropertyPages"}
  ID                        id-at-adminPropertyPages }

-- OID written as MSADat4:121 and expanded with this file's objectidentifier macros.
securityIdentifier ATTRIBUTE ::= {
  WITH SYNTAX               OCTET STRING
  SINGLE VALUE              TRUE
  LDAP-SYNTAX               octetString.&id
  LDAP-NAME                 {"securityIdentifier"}
  ID                        id-at-securityIdentifier }

-- OID written as MSADat4:166 and expanded with this file's objectidentifier macros.
groupMembershipSAM ATTRIBUTE ::= {
  WITH SYNTAX               OCTET STRING
  SINGLE VALUE              TRUE
  LDAP-SYNTAX               octetString.&id
  LDAP-NAME                 {"groupMembershipSAM"}
  ID                        id-at-groupMembershipSAM }

-- OID written as MSADat4:659 and expanded with this file's objectidentifier macros.
serviceDNSNameType ATTRIBUTE ::= {
  WITH SYNTAX               UnboundedDirectoryString
  SINGLE VALUE              TRUE
  LDAP-SYNTAX               directoryString.&id
  LDAP-NAME                 {"serviceDNSNameType"}
  ID                        id-at-serviceDNSNameType }

-- OID written as MSADat4:585 and expanded with this file's objectidentifier macros.
meetingIsEncrypted ATTRIBUTE ::= {
  WITH SYNTAX               UnboundedDirectoryString
  SINGLE VALUE              TRUE
  LDAP-SYNTAX               directoryString.&id
  LDAP-NAME                 {"meetingIsEncrypted"}
  ID                        id-at-meetingIsEncrypted }

-- OID written as MSADat4:1400 and expanded with this file's objectidentifier macros.
mS-SQL-Applications ATTRIBUTE ::= {
  WITH SYNTAX               UnboundedDirectoryString
  LDAP-SYNTAX               directoryString.&id
  LDAP-NAME                 {"mS-SQL-Applications"}
  ID                        id-at-mS-SQL-Applications }

-- OID written as MSADat4:330 and expanded with this file's objectidentifier macros.
lastUpdateSequence ATTRIBUTE ::= {
  WITH SYNTAX               UnboundedDirectoryString
  SINGLE VALUE              TRUE
  LDAP-SYNTAX               directoryString.&id
  LDAP-NAME                 {"lastUpdateSequence"}
  ID                        id-at-lastUpdateSequence }

-- OID written as MSADat4:50 and expanded with this file's objectidentifier macros.
-- SYNTAX MSADlargeInteger expanded to 1.3.6.1.4.1.1466.115.121.1.27 through an objectidentifier macro.
lastContentIndexed ATTRIBUTE ::= {
  WITH SYNTAX               INTEGER
  SINGLE VALUE              TRUE
  LDAP-SYNTAX               integer.&id
  LDAP-NAME                 {"lastContentIndexed"}
  ID                        id-at-lastContentIndexed }

-- OID written as MSADat4:567 and expanded with this file's objectidentifier macros.
meetingDescription ATTRIBUTE ::= {
  WITH SYNTAX               UnboundedDirectoryString
  SINGLE VALUE              TRUE
  LDAP-SYNTAX               directoryString.&id
  LDAP-NAME                 {"meetingDescription"}
  ID                        id-at-meetingDescription }

-- OID written as MSADat4:83 and expanded with this file's objectidentifier macros.
monikerDisplayName ATTRIBUTE ::= {
  WITH SYNTAX               UnboundedDirectoryString
  LDAP-SYNTAX               directoryString.&id
  LDAP-NAME                 {"monikerDisplayName"}
  ID                        id-at-monikerDisplayName }

-- OID written as MSADat4:321 and expanded with this file's objectidentifier macros.
requiredCategories ATTRIBUTE ::= {
  WITH SYNTAX               OCTET STRING
  LDAP-SYNTAX               octetString.&id
  LDAP-NAME                 {"requiredCategories"}
  ID                        id-at-requiredCategories }

-- OID written as MSADat4:813 and expanded with this file's objectidentifier macros.
upgradeProductCode ATTRIBUTE ::= {
  WITH SYNTAX               OCTET STRING
  LDAP-SYNTAX               octetString.&id
  LDAP-NAME                 {"upgradeProductCode"}
  ID                        id-at-upgradeProductCode }

-- OID written as MSADat4:774 and expanded with this file's objectidentifier macros.
aCSMaxNoOfLogFiles ATTRIBUTE ::= {
  WITH SYNTAX               INTEGER
  SINGLE VALUE              TRUE
  LDAP-SYNTAX               integer.&id
  LDAP-NAME                 {"aCSMaxNoOfLogFiles"}
  ID                        id-at-aCSMaxNoOfLogFiles }

-- OID written as MSADat4:1370 and expanded with this file's objectidentifier macros.
mS-SQL-CharacterSet ATTRIBUTE ::= {
  WITH SYNTAX               INTEGER
  SINGLE VALUE              TRUE
  LDAP-SYNTAX               integer.&id
  LDAP-NAME                 {"mS-SQL-CharacterSet"}
  ID                        id-at-mS-SQL-CharacterSet }

-- OID written as MSADat4:578 and expanded with this file's objectidentifier macros.
meetingContactInfo ATTRIBUTE ::= {
  WITH SYNTAX               UnboundedDirectoryString
  SINGLE VALUE              TRUE
  LDAP-SYNTAX               directoryString.&id
  LDAP-NAME                 {"meetingContactInfo"}
  ID                        id-at-meetingContactInfo }

-- OID written as MSADat4:1397 and expanded with this file's objectidentifier macros.
mS-SQL-CreationDate ATTRIBUTE ::= {
  WITH SYNTAX               UnboundedDirectoryString
  SINGLE VALUE              TRUE
  LDAP-SYNTAX               directoryString.&id
  LDAP-NAME                 {"mS-SQL-CreationDate"}
  ID                        id-at-mS-SQL-CreationDate }

-- OID written as MSADat4:32 and expanded with this file's objectidentifier macros.
domainPolicyObject ATTRIBUTE ::= {
  WITH SYNTAX               DistinguishedName
  SINGLE VALUE              TRUE
  LDAP-SYNTAX               dn.&id
  LDAP-NAME                 {"domainPolicyObject"}
  ID                        id-at-domainPolicyObject }

-- OID written as MSADat4:703 and expanded with this file's objectidentifier macros.
dhcpObjDescription ATTRIBUTE ::= {
  WITH SYNTAX               UnboundedDirectoryString
  SINGLE VALUE              TRUE
  LDAP-SYNTAX               directoryString.&id
  LDAP-NAME                 {"dhcpObjDescription"}
  ID                        id-at-dhcpObjDescription }

-- OID written as MSADat4:573 and expanded with this file's objectidentifier macros.
meetingApplication ATTRIBUTE ::= {
  WITH SYNTAX               UnboundedDirectoryString
  LDAP-SYNTAX               directoryString.&id
  LDAP-NAME                 {"meetingApplication"}
  ID                        id-at-meetingApplication }

-- OID written as MSADat4:518 and expanded with this file's objectidentifier macros.
defaultHidingValue ATTRIBUTE ::= {
  WITH SYNTAX               BOOLEAN
  SINGLE VALUE              TRUE
  LDAP-SYNTAX               boolean.&id
  LDAP-NAME                 {"defaultHidingValue"}
  ID                        id-at-defaultHidingValue }

-- OID written as MSADat4:875 and expanded with this file's objectidentifier macros.
fRSMemberReference ATTRIBUTE ::= {
  WITH SYNTAX               DistinguishedName
  SINGLE VALUE              TRUE
  LDAP-SYNTAX               dn.&id
  LDAP-NAME                 {"fRSMemberReference"}
  ID                        id-at-fRSMemberReference }

-- OID written as MSADat4:701 and expanded with this file's objectidentifier macros.
dhcpIdentification ATTRIBUTE ::= {
  WITH SYNTAX               UnboundedDirectoryString
  SINGLE VALUE              TRUE
  LDAP-SYNTAX               directoryString.&id
  LDAP-NAME                 {"dhcpIdentification"}
  ID                        id-at-dhcpIdentification }

-- OID written as MSADat4:135 and expanded with this file's objectidentifier macros.
trustAuthOutgoing ATTRIBUTE ::= {
  WITH SYNTAX               OCTET STRING
  SINGLE VALUE              TRUE
  LDAP-SYNTAX               octetString.&id
  LDAP-NAME                 {"trustAuthOutgoing"}
  ID                        id-at-trustAuthOutgoing }

-- OID written as MSADat4:197 and expanded with this file's objectidentifier macros.
systemMustContain ATTRIBUTE ::= {
  WITH SYNTAX               OBJECT IDENTIFIER
  NO USER MODIFICATION      TRUE
  LDAP-SYNTAX               oid.&id
  LDAP-NAME                 {"systemMustContain"}
  ID                        id-at-systemMustContain }

-- OID written as MSADat4:1412 and expanded with this file's objectidentifier macros.
primaryGroupToken ATTRIBUTE ::= {
  WITH SYNTAX               INTEGER
  SINGLE VALUE              TRUE
  NO USER MODIFICATION      TRUE
  LDAP-SYNTAX               integer.&id
  LDAP-NAME                 {"primaryGroupToken"}
  ID                        id-at-primaryGroupToken }

-- OID written as MSADat4:118 and expanded with this file's objectidentifier macros.
rpcNsProfileEntry ATTRIBUTE ::= {
  WITH SYNTAX               UnboundedDirectoryString
  SINGLE VALUE              TRUE
  LDAP-SYNTAX               directoryString.&id
  LDAP-NAME                 {"rpcNsProfileEntry"}
  ID                        id-at-rpcNsProfileEntry }

-- OID written as MSADat4:129 and expanded with this file's objectidentifier macros.
trustAuthIncoming ATTRIBUTE ::= {
  WITH SYNTAX               OCTET STRING
  SINGLE VALUE              TRUE
  LDAP-SYNTAX               octetString.&id
  LDAP-NAME                 {"trustAuthIncoming"}
  ID                        id-at-trustAuthIncoming }

-- OID written as MSADat4:1225 and expanded with this file's objectidentifier macros.
mSMQPrevSiteGates ATTRIBUTE ::= {
  WITH SYNTAX               DistinguishedName
  LDAP-SYNTAX               dn.&id
  LDAP-NAME                 {"mSMQPrevSiteGates"}
  ID                        id-at-mSMQPrevSiteGates }

-- OID written as MSADat4:607 and expanded with this file's objectidentifier macros.
queryPolicyObject ATTRIBUTE ::= {
  WITH SYNTAX               DistinguishedName
  SINGLE VALUE              TRUE
  LDAP-SYNTAX               dn.&id
  LDAP-NAME                 {"queryPolicyObject"}
  ID                        id-at-queryPolicyObject }

-- OID written as MSADat4:712 and expanded with this file's objectidentifier macros.
optionDescription ATTRIBUTE ::= {
  WITH SYNTAX               UnboundedDirectoryString
  LDAP-SYNTAX               directoryString.&id
  LDAP-NAME                 {"optionDescription"}
  ID                        id-at-optionDescription }

-- OID written as MSADat4:1314 and expanded with this file's objectidentifier macros.
-- SYNTAX MSADlargeInteger expanded to 1.3.6.1.4.1.1466.115.121.1.27 through an objectidentifier macro.
aCSMaximumSDUSize ATTRIBUTE ::= {
  WITH SYNTAX               INTEGER
  SINGLE VALUE              TRUE
  LDAP-SYNTAX               integer.&id
  LDAP-NAME                 {"aCSMaximumSDUSize"}
  ID                        id-at-aCSMaximumSDUSize }

-- OID written as MSADat4:530 and expanded with this file's objectidentifier macros.
nonSecurityMember ATTRIBUTE ::= {
  WITH SYNTAX               DistinguishedName
  LDAP-SYNTAX               dn.&id
  LDAP-NAME                 {"nonSecurityMember"}
  ID                        id-at-nonSecurityMember }

-- OID written as MSADat4:31 and expanded with this file's objectidentifier macros.
fRSReplicaSetType ATTRIBUTE ::= {
  WITH SYNTAX               INTEGER
  SINGLE VALUE              TRUE
  LDAP-SYNTAX               integer.&id
  LDAP-NAME                 {"fRSReplicaSetType"}
  ID                        id-at-fRSReplicaSetType }

-- OID written as MSADat4:763 and expanded with this file's objectidentifier macros.
aCSTotalNoOfFlows ATTRIBUTE ::= {
  WITH SYNTAX               INTEGER
  SINGLE VALUE              TRUE
  LDAP-SYNTAX               integer.&id
  LDAP-NAME                 {"aCSTotalNoOfFlows"}
  ID                        id-at-aCSTotalNoOfFlows }

-- OID written as MSADat4:915 and expanded with this file's objectidentifier macros.
possibleInferiors ATTRIBUTE ::= {
  WITH SYNTAX               OBJECT IDENTIFIER
  NO USER MODIFICATION      TRUE
  LDAP-SYNTAX               oid.&id
  LDAP-NAME                 {"possibleInferiors"}
  ID                        id-at-possibleInferiors }

-- OID written as MSADat4:851 and expanded with this file's objectidentifier macros.
netbootMaxClients ATTRIBUTE ::= {
  WITH SYNTAX               INTEGER
  SINGLE VALUE              TRUE
  LDAP-SYNTAX               integer.&id
  LDAP-NAME                 {"netbootMaxClients"}
  ID                        id-at-netbootMaxClients }

-- OID written as MSADat4:1385 and expanded with this file's objectidentifier macros.
mS-SQL-GPSLatitude ATTRIBUTE ::= {
  WITH SYNTAX               UnboundedDirectoryString
  SINGLE VALUE              TRUE
  LDAP-SYNTAX               directoryString.&id
  LDAP-NAME                 {"mS-SQL-GPSLatitude"}
  ID                        id-at-mS-SQL-GPSLatitude }

-- OID written as MSADat4:765 and expanded with this file's objectidentifier macros.
-- SYNTAX MSADlargeInteger expanded to 1.3.6.1.4.1.1466.115.121.1.27 through an objectidentifier macro.
aCSPermissionBits ATTRIBUTE ::= {
  WITH SYNTAX               INTEGER
  SINGLE VALUE              TRUE
  LDAP-SYNTAX               integer.&id
  LDAP-NAME                 {"aCSPermissionBits"}
  ID                        id-at-aCSPermissionBits }

-- OID written as MSADat4:926 and expanded with this file's objectidentifier macros.
mSMQTransactional ATTRIBUTE ::= {
  WITH SYNTAX               BOOLEAN
  SINGLE VALUE              TRUE
  LDAP-SYNTAX               boolean.&id
  LDAP-NAME                 {"mSMQTransactional"}
  ID                        id-at-mSMQTransactional }

-- OID written as MSADat4:1390 and expanded with this file's objectidentifier macros.
mS-SQL-Description ATTRIBUTE ::= {
  WITH SYNTAX               UnboundedDirectoryString
  SINGLE VALUE              TRUE
  LDAP-SYNTAX               directoryString.&id
  LDAP-NAME                 {"mS-SQL-Description"}
  ID                        id-at-mS-SQL-Description }

-- OID written as MSADat4:913 and expanded with this file's objectidentifier macros.
allowedAttributes ATTRIBUTE ::= {
  WITH SYNTAX               OBJECT IDENTIFIER
  NO USER MODIFICATION      TRUE
  LDAP-SYNTAX               oid.&id
  LDAP-NAME                 {"allowedAttributes"}
  ID                        id-at-allowedAttributes }

-- OID written as MSADat4:491 and expanded with this file's objectidentifier macros.
fRSFaultCondition ATTRIBUTE ::= {
  WITH SYNTAX               UnboundedDirectoryString
  SINGLE VALUE              TRUE
  LDAP-SYNTAX               directoryString.&id
  LDAP-NAME                 {"fRSFaultCondition"}
  ID                        id-at-fRSFaultCondition }

-- OID written as MSADat2:54 and expanded with this file's objectidentifier macros.
tombstoneLifetime ATTRIBUTE ::= {
  WITH SYNTAX               INTEGER
  SINGLE VALUE              TRUE
  LDAP-SYNTAX               integer.&id
  LDAP-NAME                 {"tombstoneLifetime"}
  ID                        id-at-tombstoneLifetime }

-- OID written as MSADat4:809 and expanded with this file's objectidentifier macros.
remoteStorageGUID ATTRIBUTE ::= {
  WITH SYNTAX               UnboundedDirectoryString
  SINGLE VALUE              TRUE
  LDAP-SYNTAX               directoryString.&id
  LDAP-NAME                 {"remoteStorageGUID"}
  ID                        id-at-remoteStorageGUID }

-- OID written as MSADat4:644 and expanded with this file's objectidentifier macros.
showInAddressBook ATTRIBUTE ::= {
  WITH SYNTAX               DistinguishedName
  LDAP-SYNTAX               dn.&id
  LDAP-NAME                 {"showInAddressBook"}
  ID                        id-at-showInAddressBook }

-- OID written as MSADat4:213 and expanded with this file's objectidentifier macros.
defaultClassStore ATTRIBUTE ::= {
  WITH SYNTAX               DistinguishedName
  LDAP-SYNTAX               dn.&id
  LDAP-NAME                 {"defaultClassStore"}
  ID                        id-at-defaultClassStore }

-- OID written as MSADat4:577 and expanded with this file's objectidentifier macros.
meetingOriginator ATTRIBUTE ::= {
  WITH SYNTAX               UnboundedDirectoryString
  SINGLE VALUE              TRUE
  LDAP-SYNTAX               directoryString.&id
  LDAP-NAME                 {"meetingOriginator"}
  ID                        id-at-meetingOriginator }

-- OID written as MSADat4:656 and expanded with this file's objectidentifier macros.
userPrincipalName ATTRIBUTE ::= {
  WITH SYNTAX               UnboundedDirectoryString
  SINGLE VALUE              TRUE
  LDAP-SYNTAX               directoryString.&id
  LDAP-NAME                 {"userPrincipalName"}
  ID                        id-at-userPrincipalName }

-- OID written as MSADat4:1316 and expanded with this file's objectidentifier macros.
-- SYNTAX MSADlargeInteger expanded to 1.3.6.1.4.1.1466.115.121.1.27 through an objectidentifier macro.
aCSMinimumLatency ATTRIBUTE ::= {
  WITH SYNTAX               INTEGER
  SINGLE VALUE              TRUE
  LDAP-SYNTAX               integer.&id
  LDAP-NAME                 {"aCSMinimumLatency"}
  ID                        id-at-aCSMinimumLatency }

-- OID written as MSADat4:638 and expanded with this file's objectidentifier macros.
isPrivilegeHolder ATTRIBUTE ::= {
  WITH SYNTAX               DistinguishedName
  NO USER MODIFICATION      TRUE
  LDAP-SYNTAX               dn.&id
  LDAP-NAME                 {"isPrivilegeHolder"}
  ID                        id-at-isPrivilegeHolder }

-- OID written as MSADat4:533 and expanded with this file's objectidentifier macros.
fRSReplicaSetGUID ATTRIBUTE ::= {
  WITH SYNTAX               OCTET STRING
  SINGLE VALUE              TRUE
  LDAP-SYNTAX               octetString.&id
  LDAP-NAME                 {"fRSReplicaSetGUID"}
  ID                        id-at-fRSReplicaSetGUID }

-- OID written as MSADat4:371 and expanded with this file's objectidentifier macros.
-- SYNTAX MSADlargeInteger expanded to 1.3.6.1.4.1.1466.115.121.1.27 through an objectidentifier macro.
rIDAllocationPool ATTRIBUTE ::= {
  WITH SYNTAX               INTEGER
  SINGLE VALUE              TRUE
  NO USER MODIFICATION      TRUE
  LDAP-SYNTAX               integer.&id
  LDAP-NAME                 {"rIDAllocationPool"}
  ID                        id-at-rIDAllocationPool }

-- OID written as MSADat4:1327 and expanded with this file's objectidentifier macros.
pKIDefaultKeySpec ATTRIBUTE ::= {
  WITH SYNTAX               INTEGER
  SINGLE VALUE              TRUE
  LDAP-SYNTAX               integer.&id
  LDAP-NAME                 {"pKIDefaultKeySpec"}
  ID                        id-at-pKIDefaultKeySpec }

-- OID written as MSADat4:537 and expanded with this file's objectidentifier macros.
dynamicLDAPServer ATTRIBUTE ::= {
  WITH SYNTAX               DistinguishedName
  SINGLE VALUE              TRUE
  LDAP-SYNTAX               dn.&id
  LDAP-NAME                 {"dynamicLDAPServer"}
  ID                        id-at-dynamicLDAPServer }

-- OID written as MSADat4:516 and expanded with this file's objectidentifier macros.
serverReferenceBL ATTRIBUTE ::= {
  WITH SYNTAX               DistinguishedName
  SINGLE VALUE              TRUE
  NO USER MODIFICATION      TRUE
  LDAP-SYNTAX               dn.&id
  LDAP-NAME                 {"serverReferenceBL"}
  ID                        id-at-serverReferenceBL }

-- OID written as MSADat4:500 and expanded with this file's objectidentifier macros.
fRSServiceCommand ATTRIBUTE ::= {
  WITH SYNTAX               UnboundedDirectoryString
  SINGLE VALUE              TRUE
  LDAP-SYNTAX               directoryString.&id
  LDAP-NAME                 {"fRSServiceCommand"}
  ID                        id-at-fRSServiceCommand }

-- OID written as MSADat4:1304 and expanded with this file's objectidentifier macros.
sDRightsEffective ATTRIBUTE ::= {
  WITH SYNTAX               INTEGER
  SINGLE VALUE              TRUE
  LDAP-SYNTAX               integer.&id
  LDAP-NAME                 {"sDRightsEffective"}
  ID                        id-at-sDRightsEffective }

-- OID written as MSADat4:1249 and expanded with this file's objectidentifier macros.
-- SYNTAX MSADdnWithOctetString expanded to 1.3.6.1.4.1.1466.115.121.1.40 through an objectidentifier macro.
proxiedObjectName ATTRIBUTE ::= {
  WITH SYNTAX               OCTET STRING
  SINGLE VALUE              TRUE
  NO USER MODIFICATION      TRUE
  LDAP-SYNTAX               octetString.&id
  LDAP-NAME                 {"proxiedObjectName"}
  ID                        id-at-proxiedObjectName }

-- OID written as MSADat4:586 and expanded with this file's objectidentifier macros.
meetingRecurrence ATTRIBUTE ::= {
  WITH SYNTAX               UnboundedDirectoryString
  SINGLE VALUE              TRUE
  LDAP-SYNTAX               directoryString.&id
  LDAP-NAME                 {"meetingRecurrence"}
  ID                        id-at-meetingRecurrence }

-- OID written as MSADat4:251 and expanded with this file's objectidentifier macros.
cOMTreatAsClassId ATTRIBUTE ::= {
  WITH SYNTAX               UnboundedDirectoryString
  SINGLE VALUE              TRUE
  LDAP-SYNTAX               directoryString.&id
  LDAP-NAME                 {"cOMTreatAsClassId"}
  ID                        id-at-cOMTreatAsClassId }

-- OID written as MSADat4:1245 and expanded with this file's objectidentifier macros.
globalAddressList ATTRIBUTE ::= {
  WITH SYNTAX               DistinguishedName
  LDAP-SYNTAX               dn.&id
  LDAP-NAME                 {"globalAddressList"}
  ID                        id-at-globalAddressList }

-- OID written as MSADat4:908 and expanded with this file's objectidentifier macros.
extendedClassInfo ATTRIBUTE ::= {
  WITH SYNTAX               UnboundedDirectoryString
  NO USER MODIFICATION      TRUE
  LDAP-SYNTAX               directoryString.&id
  LDAP-NAME                 {"extendedClassInfo"}
  ID                        id-at-extendedClassInfo }

-- OID written as MSADat4:459 and expanded with this file's objectidentifier macros.
machineWidePolicy ATTRIBUTE ::= {
  WITH SYNTAX               OCTET STRING
  LDAP-SYNTAX               octetString.&id
  LDAP-NAME                 {"machineWidePolicy"}
  ID                        id-at-machineWidePolicy }

-- OID written as MSADat4:356 and expanded with this file's objectidentifier macros.
foreignIdentifier ATTRIBUTE ::= {
  WITH SYNTAX               OCTET STRING
  SINGLE VALUE              TRUE
  LDAP-SYNTAX               octetString.&id
  LDAP-NAME                 {"foreignIdentifier"}
  ID                        id-at-foreignIdentifier }

-- OID written as MSADat4:1242 and expanded with this file's objectidentifier macros.
dNReferenceUpdate ATTRIBUTE ::= {
  WITH SYNTAX               DistinguishedName
  NO USER MODIFICATION      TRUE
  LDAP-SYNTAX               dn.&id
  LDAP-NAME                 {"dNReferenceUpdate"}
  ID                        id-at-dNReferenceUpdate }

-- OID written as MSADat4:134 and expanded with this file's objectidentifier macros.
trustPosixOffset ATTRIBUTE ::= {
  WITH SYNTAX               INTEGER
  SINGLE VALUE              TRUE
  LDAP-SYNTAX               integer.&id
  LDAP-NAME                 {"trustPosixOffset"}
  ID                        id-at-trustPosixOffset }

-- OID written as MSADat4:36 and expanded with this file's objectidentifier macros.
enabledConnection ATTRIBUTE ::= {
  WITH SYNTAX               BOOLEAN
  SINGLE VALUE              TRUE
  LDAP-SYNTAX               boolean.&id
  LDAP-NAME                 {"enabledConnection"}
  ID                        id-at-enabledConnection }

-- OID written as MSADat4:627 and expanded with this file's objectidentifier macros.
ipsecNFAReference ATTRIBUTE ::= {
  WITH SYNTAX               DistinguishedName
  LDAP-SYNTAX               dn.&id
  LDAP-NAME                 {"ipsecNFAReference"}
  ID                        id-at-ipsecNFAReference }

-- OID written as MSADat4:86 and expanded with this file's objectidentifier macros.
userWorkstations ATTRIBUTE ::= {
  WITH SYNTAX               UnboundedDirectoryString
  SINGLE VALUE              TRUE
  LDAP-SYNTAX               directoryString.&id
  LDAP-NAME                 {"userWorkstations"}
  ID                        id-at-userWorkstations }

-- OID written as MSADat2:301 and expanded with this file's objectidentifier macros.
garbageCollPeriod ATTRIBUTE ::= {
  WITH SYNTAX               INTEGER
  SINGLE VALUE              TRUE
  LDAP-SYNTAX               integer.&id
  LDAP-NAME                 {"garbageCollPeriod"}
  ID                        id-at-garbageCollPeriod }

-- OID written as MSADat4:933 and expanded with this file's objectidentifier macros.
-- SYNTAX MSADtelex expanded to 1.3.6.1.4.1.1466.115.121.1.44 through an objectidentifier macro.
mSMQComputerType ATTRIBUTE ::= {
  WITH SYNTAX               PrintableString
  SINGLE VALUE              TRUE
  LDAP-SYNTAX               printableString.&id
  LDAP-NAME                 {"mSMQComputerType"}
  ID                        id-at-mSMQComputerType }

-- OID written as MSADat4:65 and expanded with this file's objectidentifier macros.
logonWorkstation ATTRIBUTE ::= {
  WITH SYNTAX               OCTET STRING
  SINGLE VALUE              TRUE
  LDAP-SYNTAX               octetString.&id
  LDAP-NAME                 {"logonWorkstation"}
  ID                        id-at-logonWorkstation }

-- OID written as MSADat4:921 and expanded with this file's objectidentifier macros.
mSMQJournalQuota ATTRIBUTE ::= {
  WITH SYNTAX               INTEGER
  SINGLE VALUE              TRUE
  LDAP-SYNTAX               integer.&id
  LDAP-NAME                 {"mSMQJournalQuota"}
  ID                        id-at-mSMQJournalQuota }

-- OID written as MSADat4:108 and expanded with this file's objectidentifier macros.
remoteSourceType ATTRIBUTE ::= {
  WITH SYNTAX               INTEGER
  SINGLE VALUE              TRUE
  LDAP-SYNTAX               integer.&id
  LDAP-NAME                 {"remoteSourceType"}
  ID                        id-at-remoteSourceType }

-- OID written as MSADat4:95 and expanded with this file's objectidentifier macros.
pwdHistoryLength ATTRIBUTE ::= {
  WITH SYNTAX               INTEGER
  SINGLE VALUE              TRUE
  LDAP-SYNTAX               integer.&id
  LDAP-NAME                 {"pwdHistoryLength"}
  ID                        id-at-pwdHistoryLength }

-- OID written as MSADat4:920 and expanded with this file's objectidentifier macros.
mSMQBasePriority ATTRIBUTE ::= {
  WITH SYNTAX               INTEGER
  SINGLE VALUE              TRUE
  LDAP-SYNTAX               integer.&id
  LDAP-NAME                 {"mSMQBasePriority"}
  ID                        id-at-mSMQBasePriority }

-- OID written as MSADat4:196 and expanded with this file's objectidentifier macros.
systemMayContain ATTRIBUTE ::= {
  WITH SYNTAX               OBJECT IDENTIFIER
  NO USER MODIFICATION      TRUE
  LDAP-SYNTAX               oid.&id
  LDAP-NAME                 {"systemMayContain"}
  ID                        id-at-systemMayContain }

-- OID written as MSADat4:1407 and expanded with this file's objectidentifier macros.
mS-SQL-ThirdParty ATTRIBUTE ::= {
  WITH SYNTAX               BOOLEAN
  SINGLE VALUE              TRUE
  LDAP-SYNTAX               boolean.&id
  LDAP-NAME                 {"mS-SQL-ThirdParty"}
  ID                        id-at-mS-SQL-ThirdParty }

-- OID written as MSADat4:1243 and expanded with this file's objectidentifier macros.
mSMQQueueNameExt ATTRIBUTE ::= {
  WITH SYNTAX               UnboundedDirectoryString
  SINGLE VALUE              TRUE
  LDAP-SYNTAX               directoryString.&id
  LDAP-NAME                 {"mSMQQueueNameExt"}
  ID                        id-at-mSMQQueueNameExt }

-- OID 1.2.840.113556.1.4.485 is also used by calOtherCalAdrURIs in RFC2739Calendar. The LDAP names differ, so this definition was kept.
-- OID written as MSADat4:485 and expanded with this file's objectidentifier macros.
fRSUpdateTimeout ATTRIBUTE ::= {
  WITH SYNTAX               INTEGER
  SINGLE VALUE              TRUE
  LDAP-SYNTAX               integer.&id
  LDAP-NAME                 {"fRSUpdateTimeout"}
  ID                        id-at-fRSUpdateTimeout }

-- OID written as MSADat4:924 and expanded with this file's objectidentifier macros.
mSMQPrivacyLevel ATTRIBUTE ::= {
  WITH SYNTAX               INTEGER
  SINGLE VALUE              TRUE
  LDAP-SYNTAX               integer.&id
  LDAP-NAME                 {"mSMQPrivacyLevel"}
  ID                        id-at-mSMQPrivacyLevel }

-- OID written as MSADat4:615 and expanded with this file's objectidentifier macros.
shellContextMenu ATTRIBUTE ::= {
  WITH SYNTAX               UnboundedDirectoryString
  LDAP-SYNTAX               directoryString.&id
  LDAP-NAME                 {"shellContextMenu"}
  ID                        id-at-shellContextMenu }

-- OID written as MSADat4:618 and expanded with this file's objectidentifier macros.
-- SYNTAX MSADdnWithOctetString expanded to 1.3.6.1.4.1.1466.115.121.1.40 through an objectidentifier macro.
wellKnownObjects ATTRIBUTE ::= {
  WITH SYNTAX               OCTET STRING
  NO USER MODIFICATION      TRUE
  LDAP-SYNTAX               octetString.&id
  LDAP-NAME                 {"wellKnownObjects"}
  ID                        id-at-wellKnownObjects }

-- OID written as MSADat4:789 and expanded with this file's objectidentifier macros.
transportDLLName ATTRIBUTE ::= {
  WITH SYNTAX               UnboundedDirectoryString
  SINGLE VALUE              TRUE
  LDAP-SYNTAX               directoryString.&id
  LDAP-NAME                 {"transportDLLName"}
  ID                        id-at-transportDLLName }

-- OID written as MSADat4:458 and expanded with this file's objectidentifier macros.
qualityOfService ATTRIBUTE ::= {
  WITH SYNTAX               INTEGER
  SINGLE VALUE              TRUE
  LDAP-SYNTAX               integer.&id
  LDAP-NAME                 {"qualityOfService"}
  ID                        id-at-qualityOfService }

-- OID written as MSADat4:73 and expanded with this file's objectidentifier macros.
lockoutThreshold ATTRIBUTE ::= {
  WITH SYNTAX               INTEGER
  SINGLE VALUE              TRUE
  LDAP-SYNTAX               integer.&id
  LDAP-NAME                 {"lockoutThreshold"}
  ID                        id-at-lockoutThreshold }

-- OID written as MSADat4:105 and expanded with this file's objectidentifier macros.
remoteServerName ATTRIBUTE ::= {
  WITH SYNTAX               UnboundedDirectoryString
  LDAP-SYNTAX               directoryString.&id
  LDAP-NAME                 {"remoteServerName"}
  ID                        id-at-remoteServerName }

-- OID written as MSADat4:694 and expanded with this file's objectidentifier macros.
previousParentCA ATTRIBUTE ::= {
  WITH SYNTAX               DistinguishedName
  LDAP-SYNTAX               dn.&id
  LDAP-NAME                 {"previousParentCA"}
  ID                        id-at-previousParentCA }

-- OID written as MSADat4:1345 and expanded with this file's objectidentifier macros.
dSUIShellMaximum ATTRIBUTE ::= {
  WITH SYNTAX               INTEGER
  SINGLE VALUE              TRUE
  LDAP-SYNTAX               integer.&id
  LDAP-NAME                 {"dSUIShellMaximum"}
  ID                        id-at-dSUIShellMaximum }

-- OID written as MSADat4:303 and expanded with this file's objectidentifier macros.
notificationList ATTRIBUTE ::= {
  WITH SYNTAX               DistinguishedName
  SINGLE VALUE              TRUE
  LDAP-SYNTAX               dn.&id
  LDAP-NAME                 {"notificationList"}
  ID                        id-at-notificationList }

-- OID written as MSADat4:1244 and expanded with this file's objectidentifier macros.
addressBookRoots ATTRIBUTE ::= {
  WITH SYNTAX               DistinguishedName
  LDAP-SYNTAX               dn.&id
  LDAP-NAME                 {"addressBookRoots"}
  ID                        id-at-addressBookRoots }

-- OID written as MSADat4:878 and expanded with this file's objectidentifier macros.
fRSPrimaryMember ATTRIBUTE ::= {
  WITH SYNTAX               DistinguishedName
  SINGLE VALUE              TRUE
  LDAP-SYNTAX               dn.&id
  LDAP-NAME                 {"fRSPrimaryMember"}
  ID                        id-at-fRSPrimaryMember }

-- OID written as MSADat4:1310 and expanded with this file's objectidentifier macros.
mSMQSiteGatesMig ATTRIBUTE ::= {
  WITH SYNTAX               DistinguishedName
  LDAP-SYNTAX               dn.&id
  LDAP-NAME                 {"mSMQSiteGatesMig"}
  ID                        id-at-mSMQSiteGatesMig }

-- OID written as MSADat4:709 and expanded with this file's objectidentifier macros.
dhcpReservations ATTRIBUTE ::= {
  WITH SYNTAX               PrintableString
  LDAP-SYNTAX               printableString.&id
  LDAP-NAME                 {"dhcpReservations"}
  ID                        id-at-dhcpReservations }

-- OID written as MSADat4:614 and expanded with this file's objectidentifier macros.
adminContextMenu ATTRIBUTE ::= {
  WITH SYNTAX               UnboundedDirectoryString
  LDAP-SYNTAX               directoryString.&id
  LDAP-NAME                 {"adminContextMenu"}
  ID                        id-at-adminContextMenu }

-- OID written as MSADat4:1332 and expanded with this file's objectidentifier macros.
pKIOverlapPeriod ATTRIBUTE ::= {
  WITH SYNTAX               OCTET STRING
  SINGLE VALUE              TRUE
  LDAP-SYNTAX               octetString.&id
  LDAP-NAME                 {"pKIOverlapPeriod"}
  ID                        id-at-pKIOverlapPeriod }

-- OID written as MSADat4:142 and expanded with this file's objectidentifier macros.
winsockAddresses ATTRIBUTE ::= {
  WITH SYNTAX               OCTET STRING
  LDAP-SYNTAX               octetString.&id
  LDAP-NAME                 {"winsockAddresses"}
  ID                        id-at-winsockAddresses }

-- OID written as MSADat4:923 and expanded with this file's objectidentifier macros.
mSMQAuthenticate ATTRIBUTE ::= {
  WITH SYNTAX               BOOLEAN
  SINGLE VALUE              TRUE
  LDAP-SYNTAX               boolean.&id
  LDAP-NAME                 {"mSMQAuthenticate"}
  ID                        id-at-mSMQAuthenticate }

-- OID written as MSADat4:1344 and expanded with this file's objectidentifier macros.
dSUIAdminMaximum ATTRIBUTE ::= {
  WITH SYNTAX               INTEGER
  SINGLE VALUE              TRUE
  LDAP-SYNTAX               integer.&id
  LDAP-NAME                 {"dSUIAdminMaximum"}
  ID                        id-at-dSUIAdminMaximum }

-- OID written as MSADat4:848 and expanded with this file's objectidentifier macros.
appSchemaVersion ATTRIBUTE ::= {
  WITH SYNTAX               INTEGER
  SINGLE VALUE              TRUE
  LDAP-SYNTAX               integer.&id
  LDAP-NAME                 {"appSchemaVersion"}
  ID                        id-at-appSchemaVersion }

-- OID written as MSADat4:123 and expanded with this file's objectidentifier macros.
serviceClassInfo ATTRIBUTE ::= {
  WITH SYNTAX               OCTET STRING
  LDAP-SYNTAX               octetString.&id
  LDAP-NAME                 {"serviceClassInfo"}
  ID                        id-at-serviceClassInfo }

-- OID written as MSADat4:769 and expanded with this file's objectidentifier macros.
aCSEventLogLevel ATTRIBUTE ::= {
  WITH SYNTAX               INTEGER
  SINGLE VALUE              TRUE
  LDAP-SYNTAX               integer.&id
  LDAP-NAME                 {"aCSEventLogLevel"}
  ID                        id-at-aCSEventLogLevel }

-- OID written as MSADat4:751 and expanded with this file's objectidentifier macros.
userSharedFolder ATTRIBUTE ::= {
  WITH SYNTAX               UnboundedDirectoryString
  SINGLE VALUE              TRUE
  LDAP-SYNTAX               directoryString.&id
  LDAP-NAME                 {"userSharedFolder"}
  ID                        id-at-userSharedFolder }

-- OID written as MSADat4:421 and expanded with this file's objectidentifier macros.
domainWidePolicy ATTRIBUTE ::= {
  WITH SYNTAX               OCTET STRING
  LDAP-SYNTAX               octetString.&id
  LDAP-NAME                 {"domainWidePolicy"}
  ID                        id-at-domainWidePolicy }

-- OID written as MSADat4:669 and expanded with this file's objectidentifier macros.
rIDSetReferences ATTRIBUTE ::= {
  WITH SYNTAX               DistinguishedName
  NO USER MODIFICATION      TRUE
  LDAP-SYNTAX               dn.&id
  LDAP-NAME                 {"rIDSetReferences"}
  ID                        id-at-rIDSetReferences }

-- OID written as MSADat4:815 and expanded with this file's objectidentifier macros.
canUpgradeScript ATTRIBUTE ::= {
  WITH SYNTAX               UnboundedDirectoryString
  LDAP-SYNTAX               directoryString.&id
  LDAP-NAME                 {"canUpgradeScript"}
  ID                        id-at-canUpgradeScript }

-- OID written as MSADat4:610 and expanded with this file's objectidentifier macros.
classDisplayName ATTRIBUTE ::= {
  WITH SYNTAX               UnboundedDirectoryString
  LDAP-SYNTAX               directoryString.&id
  LDAP-NAME                 {"classDisplayName"}
  ID                        id-at-classDisplayName }

-- OID written as MSADat2:226 and expanded with this file's objectidentifier macros.
adminDescription ATTRIBUTE ::= {
  WITH SYNTAX               UnboundedDirectoryString
  SINGLE VALUE              TRUE
  LDAP-SYNTAX               directoryString.&id
  LDAP-NAME                 {"adminDescription"}
  ID                        id-at-adminDescription }

-- OID written as MSADat4:67 and expanded with this file's objectidentifier macros.
-- SYNTAX MSADlargeInteger expanded to 1.3.6.1.4.1.1466.115.121.1.27 through an objectidentifier macro.
lSAModifiedCount ATTRIBUTE ::= {
  WITH SYNTAX               INTEGER
  SINGLE VALUE              TRUE
  LDAP-SYNTAX               integer.&id
  LDAP-NAME                 {"lSAModifiedCount"}
  ID                        id-at-lSAModifiedCount }

-- OID written as MSADat4:509 and expanded with this file's objectidentifier macros.
serviceClassName ATTRIBUTE ::= {
  WITH SYNTAX               UnboundedDirectoryString
  SINGLE VALUE              TRUE
  LDAP-SYNTAX               directoryString.&id
  LDAP-NAME                 {"serviceClassName"}
  ID                        id-at-serviceClassName }

-- OID written as MSADat4:56 and expanded with this file's objectidentifier macros.
localPolicyFlags ATTRIBUTE ::= {
  WITH SYNTAX               INTEGER
  SINGLE VALUE              TRUE
  LDAP-SYNTAX               integer.&id
  LDAP-NAME                 {"localPolicyFlags"}
  ID                        id-at-localPolicyFlags }

-- OID written as MSADat4:115 and expanded with this file's objectidentifier macros.
rpcNsInterfaceID ATTRIBUTE ::= {
  WITH SYNTAX               UnboundedDirectoryString
  SINGLE VALUE              TRUE
  LDAP-SYNTAX               directoryString.&id
  LDAP-NAME                 {"rpcNsInterfaceID"}
  ID                        id-at-rpcNsInterfaceID }

-- OID written as MSADat2:194 and expanded with this file's objectidentifier macros.
adminDisplayName ATTRIBUTE ::= {
  WITH SYNTAX               UnboundedDirectoryString
  SINGLE VALUE              TRUE
  LDAP-SYNTAX               directoryString.&id
  LDAP-NAME                 {"adminDisplayName"}
  ID                        id-at-adminDisplayName }

-- OID written as MSADat4:753 and expanded with this file's objectidentifier macros.
nameServiceFlags ATTRIBUTE ::= {
  WITH SYNTAX               INTEGER
  SINGLE VALUE              TRUE
  LDAP-SYNTAX               integer.&id
  LDAP-NAME                 {"nameServiceFlags"}
  ID                        id-at-nameServiceFlags }

-- OID written as MSADat4:589 and expanded with this file's objectidentifier macros.
meetingBandwidth ATTRIBUTE ::= {
  WITH SYNTAX               INTEGER
  LDAP-SYNTAX               integer.&id
  LDAP-NAME                 {"meetingBandwidth"}
  ID                        id-at-meetingBandwidth }

-- OID written as MSADat4:755 and expanded with this file's objectidentifier macros.
domainIdentifier ATTRIBUTE ::= {
  WITH SYNTAX               INTEGER
  SINGLE VALUE              TRUE
  NO USER MODIFICATION      TRUE
  LDAP-SYNTAX               integer.&id
  LDAP-NAME                 {"domainIdentifier"}
  ID                        id-at-domainIdentifier }

-- OID written as MSADat4:370 and expanded with this file's objectidentifier macros.
-- SYNTAX MSADlargeInteger expanded to 1.3.6.1.4.1.1466.115.121.1.27 through an objectidentifier macro.
rIDAvailablePool ATTRIBUTE ::= {
  WITH SYNTAX               INTEGER
  SINGLE VALUE              TRUE
  LDAP-SYNTAX               integer.&id
  LDAP-NAME                 {"rIDAvailablePool"}
  ID                        id-at-rIDAvailablePool }

-- OID written as MSADat4:655 and expanded with this file's objectidentifier macros.
-- SYNTAX MSADtelex expanded to 1.3.6.1.4.1.1466.115.121.1.44 through an objectidentifier macro.
legacyExchangeDN ATTRIBUTE ::= {
  WITH SYNTAX               PrintableString
  SINGLE VALUE              TRUE
  LDAP-SYNTAX               printableString.&id
  LDAP-NAME                 {"legacyExchangeDN"}
  ID                        id-at-legacyExchangeDN }

-- OID written as MSADat4:470 and expanded with this file's objectidentifier macros.
trustAttributes ATTRIBUTE ::= {
  WITH SYNTAX               INTEGER
  SINGLE VALUE              TRUE
  LDAP-SYNTAX               integer.&id
  LDAP-NAME                 {"trustAttributes"}
  ID                        id-at-trustAttributes }

-- OID written as MSADat4:535 and expanded with this file's objectidentifier macros.
-- SYNTAX MSADcis expanded to 1.3.6.1.4.1.1466.115.121.1.44 through an objectidentifier macro.
fRSRootSecurity ATTRIBUTE ::= {
  WITH SYNTAX               PrintableString
  SINGLE VALUE              TRUE
  LDAP-SYNTAX               printableString.&id
  LDAP-NAME                 {"fRSRootSecurity"}
  ID                        id-at-fRSRootSecurity }

-- OID written as MSADat4:532 and expanded with this file's objectidentifier macros.
superiorDNSRoot ATTRIBUTE ::= {
  WITH SYNTAX               UnboundedDirectoryString
  SINGLE VALUE              TRUE
  LDAP-SYNTAX               directoryString.&id
  LDAP-NAME                 {"superiorDNSRoot"}
  ID                        id-at-superiorDNSRoot }

-- OID written as MSADat4:278 and expanded with this file's objectidentifier macros.
printMaxYExtent ATTRIBUTE ::= {
  WITH SYNTAX               INTEGER
  SINGLE VALUE              TRUE
  LDAP-SYNTAX               integer.&id
  LDAP-NAME                 {"printMaxYExtent"}
  ID                        id-at-printMaxYExtent }

-- OID written as MSADat4:277 and expanded with this file's objectidentifier macros.
printMaxXExtent ATTRIBUTE ::= {
  WITH SYNTAX               INTEGER
  SINGLE VALUE              TRUE
  LDAP-SYNTAX               integer.&id
  LDAP-NAME                 {"printMaxXExtent"}
  ID                        id-at-printMaxXExtent }

-- OID written as MSADat4:280 and expanded with this file's objectidentifier macros.
printMinYExtent ATTRIBUTE ::= {
  WITH SYNTAX               INTEGER
  SINGLE VALUE              TRUE
  LDAP-SYNTAX               integer.&id
  LDAP-NAME                 {"printMinYExtent"}
  ID                        id-at-printMinYExtent }

-- OID written as MSADat4:279 and expanded with this file's objectidentifier macros.
printMinXExtent ATTRIBUTE ::= {
  WITH SYNTAX               INTEGER
  SINGLE VALUE              TRUE
  LDAP-SYNTAX               integer.&id
  LDAP-NAME                 {"printMinXExtent"}
  ID                        id-at-printMinXExtent }

-- OID written as MSADat2:32 and expanded with this file's objectidentifier macros.
attributeSyntax ATTRIBUTE ::= {
  WITH SYNTAX               OBJECT IDENTIFIER
  SINGLE VALUE              TRUE
  NO USER MODIFICATION      TRUE
  LDAP-SYNTAX               oid.&id
  LDAP-NAME                 {"attributeSyntax"}
  ID                        id-at-attributeSyntax }

-- OID written as MSADat4:247 and expanded with this file's objectidentifier macros.
printAttributes ATTRIBUTE ::= {
  WITH SYNTAX               INTEGER
  SINGLE VALUE              TRUE
  LDAP-SYNTAX               integer.&id
  LDAP-NAME                 {"printAttributes"}
  ID                        id-at-printAttributes }

-- OID written as MSADat4:152 and expanded with this file's objectidentifier macros.
groupAttributes ATTRIBUTE ::= {
  WITH SYNTAX               INTEGER
  SINGLE VALUE              TRUE
  LDAP-SYNTAX               integer.&id
  LDAP-NAME                 {"groupAttributes"}
  ID                        id-at-groupAttributes }

-- OID written as MSADat4:816 and expanded with this file's objectidentifier macros.
fileExtPriority ATTRIBUTE ::= {
  WITH SYNTAX               UnboundedDirectoryString
  LDAP-SYNTAX               directoryString.&id
  LDAP-NAME                 {"fileExtPriority"}
  ID                        id-at-fileExtPriority }

-- OID written as MSADat4:930 and expanded with this file's objectidentifier macros.
mSMQServiceType ATTRIBUTE ::= {
  WITH SYNTAX               INTEGER
  SINGLE VALUE              TRUE
  LDAP-SYNTAX               integer.&id
  LDAP-NAME                 {"mSMQServiceType"}
  ID                        id-at-mSMQServiceType }

-- OID written as MSADat4:363 and expanded with this file's objectidentifier macros.
operatingSystem ATTRIBUTE ::= {
  WITH SYNTAX               UnboundedDirectoryString
  SINGLE VALUE              TRUE
  LDAP-SYNTAX               directoryString.&id
  LDAP-NAME                 {"operatingSystem"}
  ID                        id-at-operatingSystem }

-- OID written as MSADat4:1371 and expanded with this file's objectidentifier macros.
mS-SQL-SortOrder ATTRIBUTE ::= {
  WITH SYNTAX               UnboundedDirectoryString
  SINGLE VALUE              TRUE
  LDAP-SYNTAX               directoryString.&id
  LDAP-NAME                 {"mS-SQL-SortOrder"}
  ID                        id-at-mS-SQL-SortOrder }

-- OID written as MSADat4:329 and expanded with this file's objectidentifier macros.
versionNumberLo ATTRIBUTE ::= {
  WITH SYNTAX               INTEGER
  SINGLE VALUE              TRUE
  LDAP-SYNTAX               integer.&id
  LDAP-NAME                 {"versionNumberLo"}
  ID                        id-at-versionNumberLo }

-- OID written as MSADat4:884 and expanded with this file's objectidentifier macros.
msRRASAttribute ATTRIBUTE ::= {
  WITH SYNTAX               UnboundedDirectoryString
  LDAP-SYNTAX               directoryString.&id
  LDAP-NAME                 {"msRRASAttribute"}
  ID                        id-at-msRRASAttribute }

-- OID written as MSADat4:781 and expanded with this file's objectidentifier macros.
lastKnownParent ATTRIBUTE ::= {
  WITH SYNTAX               DistinguishedName
  SINGLE VALUE              TRUE
  LDAP-SYNTAX               dn.&id
  LDAP-NAME                 {"lastKnownParent"}
  ID                        id-at-lastKnownParent }

-- OID written as MSADat4:1209 and expanded with this file's objectidentifier macros.
shortServerName ATTRIBUTE ::= {
  WITH SYNTAX               UnboundedDirectoryString
  SINGLE VALUE              TRUE
  LDAP-SYNTAX               directoryString.&id
  LDAP-NAME                 {"shortServerName"}
  ID                        id-at-shortServerName }

-- OID written as MSADat4:60 and expanded with this file's objectidentifier macros.
-- SYNTAX MSADlargeInteger expanded to 1.3.6.1.4.1.1466.115.121.1.27 through an objectidentifier macro.
lockoutDuration ATTRIBUTE ::= {
  WITH SYNTAX               INTEGER
  SINGLE VALUE              TRUE
  LDAP-SYNTAX               integer.&id
  LDAP-NAME                 {"lockoutDuration"}
  ID                        id-at-lockoutDuration }

-- OID written as MSADat4:232 and expanded with this file's objectidentifier macros.
defaultPriority ATTRIBUTE ::= {
  WITH SYNTAX               INTEGER
  SINGLE VALUE              TRUE
  LDAP-SYNTAX               integer.&id
  LDAP-NAME                 {"defaultPriority"}
  ID                        id-at-defaultPriority }

-- OID written as MSADat4:754 and expanded with this file's objectidentifier macros.
rpcNsEntryFlags ATTRIBUTE ::= {
  WITH SYNTAX               INTEGER
  SINGLE VALUE              TRUE
  LDAP-SYNTAX               integer.&id
  LDAP-NAME                 {"rpcNsEntryFlags"}
  ID                        id-at-rpcNsEntryFlags }

-- OID written as MSADat4:713 and expanded with this file's objectidentifier macros.
optionsLocation ATTRIBUTE ::= {
  WITH SYNTAX               PrintableString
  LDAP-SYNTAX               printableString.&id
  LDAP-NAME                 {"optionsLocation"}
  ID                        id-at-optionsLocation }

-- OID written as MSADat4:328 and expanded with this file's objectidentifier macros.
versionNumberHi ATTRIBUTE ::= {
  WITH SYNTAX               INTEGER
  SINGLE VALUE              TRUE
  LDAP-SYNTAX               integer.&id
  LDAP-NAME                 {"versionNumberHi"}
  ID                        id-at-versionNumberHi }

-- OID written as MSADat4:366 and expanded with this file's objectidentifier macros.
rpcNsAnnotation ATTRIBUTE ::= {
  WITH SYNTAX               UnboundedDirectoryString
  SINGLE VALUE              TRUE
  LDAP-SYNTAX               directoryString.&id
  LDAP-NAME                 {"rpcNsAnnotation"}
  ID                        id-at-rpcNsAnnotation }

-- OID written as MSADat4:886 and expanded with this file's objectidentifier macros.
purportedSearch ATTRIBUTE ::= {
  WITH SYNTAX               UnboundedDirectoryString
  SINGLE VALUE              TRUE
  LDAP-SYNTAX               directoryString.&id
  LDAP-NAME                 {"purportedSearch"}
  ID                        id-at-purportedSearch }

-- OID written as MSADat4:776 and expanded with this file's objectidentifier macros.
aCSDSBMPriority ATTRIBUTE ::= {
  WITH SYNTAX               INTEGER
  SINGLE VALUE              TRUE
  LDAP-SYNTAX               integer.&id
  LDAP-NAME                 {"aCSDSBMPriority"}
  ID                        id-at-aCSDSBMPriority }

-- OID written as MSADat4:961 and expanded with this file's objectidentifier macros.
mSMQSiteForeign ATTRIBUTE ::= {
  WITH SYNTAX               BOOLEAN
  LDAP-SYNTAX               boolean.&id
  LDAP-NAME                 {"mSMQSiteForeign"}
  ID                        id-at-mSMQSiteForeign }

-- OID written as MSADat4:335 and expanded with this file's objectidentifier macros.
currentLocation ATTRIBUTE ::= {
  WITH SYNTAX               OCTET STRING
  SINGLE VALUE              TRUE
  LDAP-SYNTAX               octetString.&id
  LDAP-NAME                 {"currentLocation"}
  ID                        id-at-currentLocation }

-- OID written as MSADat4:570 and expanded with this file's objectidentifier macros.
meetingProtocol ATTRIBUTE ::= {
  WITH SYNTAX               UnboundedDirectoryString
  LDAP-SYNTAX               directoryString.&id
  LDAP-NAME                 {"meetingProtocol"}
  ID                        id-at-meetingProtocol }

-- OID written as MSADat4:420 and expanded with this file's objectidentifier macros.
publicKeyPolicy ATTRIBUTE ::= {
  WITH SYNTAX               OCTET STRING
  SINGLE VALUE              TRUE
  LDAP-SYNTAX               octetString.&id
  LDAP-NAME                 {"publicKeyPolicy"}
  ID                        id-at-publicKeyPolicy }

-- OID written as MSADat4:1402 and expanded with this file's objectidentifier macros.
mS-SQL-Publisher ATTRIBUTE ::= {
  WITH SYNTAX               UnboundedDirectoryString
  SINGLE VALUE              TRUE
  LDAP-SYNTAX               directoryString.&id
  LDAP-NAME                 {"mS-SQL-Publisher"}
  ID                        id-at-mS-SQL-Publisher }

-- OID written as MSADat4:812 and expanded with this file's objectidentifier macros.
createWizardExt ATTRIBUTE ::= {
  WITH SYNTAX               UnboundedDirectoryString
  LDAP-SYNTAX               directoryString.&id
  LDAP-NAME                 {"createWizardExt"}
  ID                        id-at-createWizardExt }

-- OID written as MSADat4:1373 and expanded with this file's objectidentifier macros.
mS-SQL-Clustered ATTRIBUTE ::= {
  WITH SYNTAX               BOOLEAN
  SINGLE VALUE              TRUE
  LDAP-SYNTAX               boolean.&id
  LDAP-NAME                 {"mS-SQL-Clustered"}
  ID                        id-at-mS-SQL-Clustered }

-- OID written as MSADat4:334 and expanded with this file's objectidentifier macros.
volTableIdxGUID ATTRIBUTE ::= {
  WITH SYNTAX               OCTET STRING
  SINGLE VALUE              TRUE
  LDAP-SYNTAX               octetString.&id
  LDAP-NAME                 {"volTableIdxGUID"}
  ID                        id-at-volTableIdxGUID }

-- OID written as MSADat4:696 and expanded with this file's objectidentifier macros.
currentParentCA ATTRIBUTE ::= {
  WITH SYNTAX               DistinguishedName
  LDAP-SYNTAX               dn.&id
  LDAP-NAME                 {"currentParentCA"}
  ID                        id-at-currentParentCA }

-- OID written as MSADat4:504 and expanded with this file's objectidentifier macros.
seqNotification ATTRIBUTE ::= {
  WITH SYNTAX               INTEGER
  SINGLE VALUE              TRUE
  LDAP-SYNTAX               integer.&id
  LDAP-NAME                 {"seqNotification"}
  ID                        id-at-seqNotification }

-- OID written as MSADat4:515 and expanded with this file's objectidentifier macros.
serverReference ATTRIBUTE ::= {
  WITH SYNTAX               DistinguishedName
  SINGLE VALUE              TRUE
  LDAP-SYNTAX               dn.&id
  LDAP-NAME                 {"serverReference"}
  ID                        id-at-serverReference }

-- OID written as MSADat4:1119 and expanded with this file's objectidentifier macros.
msNPAllowDialin ATTRIBUTE ::= {
  WITH SYNTAX               BOOLEAN
  SINGLE VALUE              TRUE
  LDAP-SYNTAX               boolean.&id
  LDAP-NAME                 {"msNPAllowDialin"}
  ID                        id-at-msNPAllowDialin }

-- OID written as MSADat4:1387 and expanded with this file's objectidentifier macros.
mS-SQL-GPSHeight ATTRIBUTE ::= {
  WITH SYNTAX               UnboundedDirectoryString
  SINGLE VALUE              TRUE
  LDAP-SYNTAX               directoryString.&id
  LDAP-NAME                 {"mS-SQL-GPSHeight"}
  ID                        id-at-mS-SQL-GPSHeight }

-- OID written as MSADat4:1378 and expanded with this file's objectidentifier macros.
mS-SQL-AppleTalk ATTRIBUTE ::= {
  WITH SYNTAX               UnboundedDirectoryString
  SINGLE VALUE              TRUE
  LDAP-SYNTAX               directoryString.&id
  LDAP-NAME                 {"mS-SQL-AppleTalk"}
  ID                        id-at-mS-SQL-AppleTalk }

-- OID written as MSADat4:269 and expanded with this file's objectidentifier macros.
linkTrackSecret ATTRIBUTE ::= {
  WITH SYNTAX               OCTET STRING
  SINGLE VALUE              TRUE
  LDAP-SYNTAX               octetString.&id
  LDAP-NAME                 {"linkTrackSecret"}
  ID                        id-at-linkTrackSecret }

-- OID written as MSADat4:378 and expanded with this file's objectidentifier macros.
dnsAllowDynamic ATTRIBUTE ::= {
  WITH SYNTAX               BOOLEAN
  SINGLE VALUE              TRUE
  LDAP-SYNTAX               boolean.&id
  LDAP-NAME                 {"dnsAllowDynamic"}
  ID                        id-at-dnsAllowDynamic }

-- OID written as MSADat4:49 and expanded with this file's objectidentifier macros.
-- SYNTAX MSADlargeInteger expanded to 1.3.6.1.4.1.1466.115.121.1.27 through an objectidentifier macro.
badPasswordTime ATTRIBUTE ::= {
  WITH SYNTAX               INTEGER
  SINGLE VALUE              TRUE
  LDAP-SYNTAX               integer.&id
  LDAP-NAME                 {"badPasswordTime"}
  ID                        id-at-badPasswordTime }

-- OID written as MSADat4:637 and expanded with this file's objectidentifier macros.
privilegeHolder ATTRIBUTE ::= {
  WITH SYNTAX               DistinguishedName
  LDAP-SYNTAX               dn.&id
  LDAP-NAME                 {"privilegeHolder"}
  ID                        id-at-privilegeHolder }

-- OID written as MSADat4:289 and expanded with this file's objectidentifier macros.
printMediaReady ATTRIBUTE ::= {
  WITH SYNTAX               UnboundedDirectoryString
  LDAP-SYNTAX               directoryString.&id
  LDAP-NAME                 {"printMediaReady"}
  ID                        id-at-printMediaReady }

-- OID written as MSADat4:288 and expanded with this file's objectidentifier macros.
printMACAddress ATTRIBUTE ::= {
  WITH SYNTAX               UnboundedDirectoryString
  SINGLE VALUE              TRUE
  LDAP-SYNTAX               directoryString.&id
  LDAP-NAME                 {"printMACAddress"}
  ID                        id-at-printMACAddress }

-- OID written as MSADat4:66 and expanded with this file's objectidentifier macros.
-- SYNTAX MSADlargeInteger expanded to 1.3.6.1.4.1.1466.115.121.1.27 through an objectidentifier macro.
lSACreationTime ATTRIBUTE ::= {
  WITH SYNTAX               INTEGER
  SINGLE VALUE              TRUE
  LDAP-SYNTAX               integer.&id
  LDAP-NAME                 {"lSACreationTime"}
  ID                        id-at-lSACreationTime }

-- OID written as MSADat4:569 and expanded with this file's objectidentifier macros.
meetingLocation ATTRIBUTE ::= {
  WITH SYNTAX               UnboundedDirectoryString
  LDAP-SYNTAX               directoryString.&id
  LDAP-NAME                 {"meetingLocation"}
  ID                        id-at-meetingLocation }

-- OID written as MSADat4:784 and expanded with this file's objectidentifier macros.
aCSIdentityName ATTRIBUTE ::= {
  WITH SYNTAX               UnboundedDirectoryString
  LDAP-SYNTAX               directoryString.&id
  LDAP-NAME                 {"aCSIdentityName"}
  ID                        id-at-aCSIdentityName }

-- OID written as MSADat4:1410 and expanded with this file's objectidentifier macros.
mS-DS-CreatorSID ATTRIBUTE ::= {
  WITH SYNTAX               OCTET STRING
  SINGLE VALUE              TRUE
  NO USER MODIFICATION      TRUE
  LDAP-SYNTAX               octetString.&id
  LDAP-NAME                 {"mS-DS-CreatorSID"}
  ID                        id-at-mS-DS-CreatorSID }

-- OID written as MSADat4:1374 and expanded with this file's objectidentifier macros.
mS-SQL-NamedPipe ATTRIBUTE ::= {
  WITH SYNTAX               UnboundedDirectoryString
  SINGLE VALUE              TRUE
  LDAP-SYNTAX               directoryString.&id
  LDAP-NAME                 {"mS-SQL-NamedPipe"}
  ID                        id-at-mS-SQL-NamedPipe }

-- OID written as MSADat4:843 and expanded with this file's objectidentifier macros.
lDAPAdminLimits ATTRIBUTE ::= {
  WITH SYNTAX               UnboundedDirectoryString
  LDAP-SYNTAX               directoryString.&id
  LDAP-NAME                 {"lDAPAdminLimits"}
  ID                        id-at-lDAPAdminLimits }

-- OID written as MSADat2:460 and expanded with this file's objectidentifier macros.
lDAPDisplayName ATTRIBUTE ::= {
  WITH SYNTAX               UnboundedDirectoryString
  SINGLE VALUE              TRUE
  LDAP-SYNTAX               directoryString.&id
  LDAP-NAME                 {"lDAPDisplayName"}
  ID                        id-at-lDAPDisplayName }

-- OID written as MSADat4:218 and expanded with this file's objectidentifier macros.
applicationName ATTRIBUTE ::= {
  WITH SYNTAX               UnboundedDirectoryString
  SINGLE VALUE              TRUE
  LDAP-SYNTAX               directoryString.&id
  LDAP-NAME                 {"applicationName"}
  ID                        id-at-applicationName }

-- OID written as MSADat4:695 and expanded with this file's objectidentifier macros.
pendingParentCA ATTRIBUTE ::= {
  WITH SYNTAX               DistinguishedName
  LDAP-SYNTAX               dn.&id
  LDAP-NAME                 {"pendingParentCA"}
  ID                        id-at-pendingParentCA }

-- OID written as MSADat4:779 and expanded with this file's objectidentifier macros.
aCSCacheTimeout ATTRIBUTE ::= {
  WITH SYNTAX               INTEGER
  SINGLE VALUE              TRUE
  LDAP-SYNTAX               integer.&id
  LDAP-NAME                 {"aCSCacheTimeout"}
  ID                        id-at-aCSCacheTimeout }

-- OID written as MSADat4:574 and expanded with this file's objectidentifier macros.
meetingLanguage ATTRIBUTE ::= {
  WITH SYNTAX               UnboundedDirectoryString
  LDAP-SYNTAX               directoryString.&id
  LDAP-NAME                 {"meetingLanguage"}
  ID                        id-at-meetingLanguage }

-- OID written as MSADat4:778 and expanded with this file's objectidentifier macros.
aCSDSBMDeadTime ATTRIBUTE ::= {
  WITH SYNTAX               INTEGER
  SINGLE VALUE              TRUE
  LDAP-SYNTAX               integer.&id
  LDAP-NAME                 {"aCSDSBMDeadTime"}
  ID                        id-at-aCSDSBMDeadTime }

-- OID written as MSADat4:697 and expanded with this file's objectidentifier macros.
cACertificateDN ATTRIBUTE ::= {
  WITH SYNTAX               UnboundedDirectoryString
  SINGLE VALUE              TRUE
  LDAP-SYNTAX               directoryString.&id
  LDAP-NAME                 {"cACertificateDN"}
  ID                        id-at-cACertificateDN }

-- OID written as MSADat4:138 and expanded with this file's objectidentifier macros.
userParameters ATTRIBUTE ::= {
  WITH SYNTAX               UnboundedDirectoryString
  SINGLE VALUE              TRUE
  LDAP-SYNTAX               directoryString.&id
  LDAP-NAME                 {"userParameters"}
  ID                        id-at-userParameters }

-- OID written as MSADat4:132 and expanded with this file's objectidentifier macros.
trustDirection ATTRIBUTE ::= {
  WITH SYNTAX               INTEGER
  SINGLE VALUE              TRUE
  LDAP-SYNTAX               integer.&id
  LDAP-NAME                 {"trustDirection"}
  ID                        id-at-trustDirection }

-- OID written as MSADat4:962 and expanded with this file's objectidentifier macros.
mSMQQueueQuota ATTRIBUTE ::= {
  WITH SYNTAX               INTEGER
  SINGLE VALUE              TRUE
  LDAP-SYNTAX               integer.&id
  LDAP-NAME                 {"mSMQQueueQuota"}
  ID                        id-at-mSMQQueueQuota }

-- OID written as MSADat4:936 and expanded with this file's objectidentifier macros.
mSMQEncryptKey ATTRIBUTE ::= {
  WITH SYNTAX               OCTET STRING
  SINGLE VALUE              TRUE
  LDAP-SYNTAX               octetString.&id
  LDAP-NAME                 {"mSMQEncryptKey"}
  ID                        id-at-mSMQEncryptKey }

-- OID written as MSADat4:885 and expanded with this file's objectidentifier macros.
terminalServer ATTRIBUTE ::= {
  WITH SYNTAX               OCTET STRING
  SINGLE VALUE              TRUE
  LDAP-SYNTAX               octetString.&id
  LDAP-NAME                 {"terminalServer"}
  ID                        id-at-terminalServer }

-- OID written as MSADat4:233 and expanded with this file's objectidentifier macros.
printStartTime ATTRIBUTE ::= {
  WITH SYNTAX               INTEGER
  SINGLE VALUE              TRUE
  LDAP-SYNTAX               integer.&id
  LDAP-NAME                 {"printStartTime"}
  ID                        id-at-printStartTime }

-- OID written as MSADat4:664 and expanded with this file's objectidentifier macros.
syncWithObject ATTRIBUTE ::= {
  WITH SYNTAX               DistinguishedName
  SINGLE VALUE              TRUE
  LDAP-SYNTAX               dn.&id
  LDAP-NAME                 {"syncWithObject"}
  ID                        id-at-syncWithObject }

-- OID written as MSADat4:344 and expanded with this file's objectidentifier macros.
groupsToIgnore ATTRIBUTE ::= {
  WITH SYNTAX               UnboundedDirectoryString
  LDAP-SYNTAX               directoryString.&id
  LDAP-NAME                 {"groupsToIgnore"}
  ID                        id-at-groupsToIgnore }

-- OID written as MSADat4:665 and expanded with this file's objectidentifier macros.
syncMembership ATTRIBUTE ::= {
  WITH SYNTAX               DistinguishedName
  LDAP-SYNTAX               dn.&id
  LDAP-NAME                 {"syncMembership"}
  ID                        id-at-syncMembership }

-- OID written as MSADat4:666 and expanded with this file's objectidentifier macros.
syncAttributes ATTRIBUTE ::= {
  WITH SYNTAX               INTEGER
  SINGLE VALUE              TRUE
  LDAP-SYNTAX               integer.&id
  LDAP-NAME                 {"syncAttributes"}
  ID                        id-at-syncAttributes }

-- OID written as MSADat4:214 and expanded with this file's objectidentifier macros.
nextLevelStore ATTRIBUTE ::= {
  WITH SYNTAX               DistinguishedName
  SINGLE VALUE              TRUE
  LDAP-SYNTAX               dn.&id
  LDAP-NAME                 {"nextLevelStore"}
  ID                        id-at-nextLevelStore }

-- OID written as MSADat4:302 and expanded with this file's objectidentifier macros.
sAMAccountType ATTRIBUTE ::= {
  WITH SYNTAX               INTEGER
  SINGLE VALUE              TRUE
  LDAP-SYNTAX               integer.&id
  LDAP-NAME                 {"sAMAccountType"}
  ID                        id-at-sAMAccountType }

-- OID written as MSADat4:1401 and expanded with this file's objectidentifier macros.
mS-SQL-Keywords ATTRIBUTE ::= {
  WITH SYNTAX               UnboundedDirectoryString
  LDAP-SYNTAX               directoryString.&id
  LDAP-NAME                 {"mS-SQL-Keywords"}
  ID                        id-at-mS-SQL-Keywords }

-- OID written as MSADat2:210 and expanded with this file's objectidentifier macros.
proxyAddresses ATTRIBUTE ::= {
  WITH SYNTAX               UnboundedDirectoryString
  LDAP-SYNTAX               directoryString.&id
  LDAP-NAME                 {"proxyAddresses"}
  ID                        id-at-proxyAddresses }

-- OID written as MSADat4:284 and expanded with this file's objectidentifier macros.
bytesPerMinute ATTRIBUTE ::= {
  WITH SYNTAX               INTEGER
  SINGLE VALUE              TRUE
  LDAP-SYNTAX               integer.&id
  LDAP-NAME                 {"bytesPerMinute"}
  ID                        id-at-bytesPerMinute }

-- OID written as MSADat4:241 and expanded with this file's objectidentifier macros.
printMaxCopies ATTRIBUTE ::= {
  WITH SYNTAX               INTEGER
  SINGLE VALUE              TRUE
  LDAP-SYNTAX               integer.&id
  LDAP-NAME                 {"printMaxCopies"}
  ID                        id-at-printMaxCopies }

-- OID written as MSADat4:98 and expanded with this file's objectidentifier macros.
primaryGroupID ATTRIBUTE ::= {
  WITH SYNTAX               INTEGER
  SINGLE VALUE              TRUE
  LDAP-SYNTAX               integer.&id
  LDAP-NAME                 {"primaryGroupID"}
  ID                        id-at-primaryGroupID }

-- OID written as MSADat4:89 and expanded with this file's objectidentifier macros.
nTGroupMembers ATTRIBUTE ::= {
  WITH SYNTAX               OCTET STRING
  LDAP-SYNTAX               octetString.&id
  LDAP-NAME                 {"nTGroupMembers"}
  ID                        id-at-nTGroupMembers }

-- OID written as MSADat4:1228 and expanded with this file's objectidentifier macros.
mSMQDsServices ATTRIBUTE ::= {
  WITH SYNTAX               BOOLEAN
  SINGLE VALUE              TRUE
  LDAP-SYNTAX               boolean.&id
  LDAP-NAME                 {"mSMQDsServices"}
  ID                        id-at-mSMQDsServices }

-- OID written as MSADat4:43 and expanded with this file's objectidentifier macros.
fRSVersionGUID ATTRIBUTE ::= {
  WITH SYNTAX               OCTET STRING
  SINGLE VALUE              TRUE
  LDAP-SYNTAX               octetString.&id
  LDAP-NAME                 {"fRSVersionGUID"}
  ID                        id-at-fRSVersionGUID }

-- OID written as MSADat4:486 and expanded with this file's objectidentifier macros.
fRSWorkingPath ATTRIBUTE ::= {
  WITH SYNTAX               UnboundedDirectoryString
  SINGLE VALUE              TRUE
  LDAP-SYNTAX               directoryString.&id
  LDAP-NAME                 {"fRSWorkingPath"}
  ID                        id-at-fRSWorkingPath }

-- OID written as MSADat2:18 and expanded with this file's objectidentifier macros.
otherTelephone ATTRIBUTE ::= {
  WITH SYNTAX               UnboundedDirectoryString
  LDAP-SYNTAX               directoryString.&id
  LDAP-NAME                 {"otherTelephone"}
  ID                        id-at-otherTelephone }

-- OID written as MSADat2:277 and expanded with this file's objectidentifier macros.
otherHomePhone ATTRIBUTE ::= {
  WITH SYNTAX               UnboundedDirectoryString
  LDAP-SYNTAX               directoryString.&id
  LDAP-NAME                 {"otherHomePhone"}
  ID                        id-at-otherHomePhone }

-- OID written as MSADat4:151 and expanded with this file's objectidentifier macros.
oEMInformation ATTRIBUTE ::= {
  WITH SYNTAX               UnboundedDirectoryString
  SINGLE VALUE              TRUE
  LDAP-SYNTAX               directoryString.&id
  LDAP-NAME                 {"oEMInformation"}
  ID                        id-at-oEMInformation }

-- OID written as MSADat2:459 and expanded with this file's objectidentifier macros.
-- SYNTAX MSADtelex expanded to 1.3.6.1.4.1.1466.115.121.1.44 through an objectidentifier macro.
networkAddress ATTRIBUTE ::= {
  WITH SYNTAX               PrintableString
  LDAP-SYNTAX               printableString.&id
  LDAP-NAME                 {"networkAddress"}
  ID                        id-at-networkAddress }

-- OID written as MSADat4:966 and expanded with this file's objectidentifier macros.
mSMQDigestsMig ATTRIBUTE ::= {
  WITH SYNTAX               OCTET STRING
  LDAP-SYNTAX               octetString.&id
  LDAP-NAME                 {"mSMQDigestsMig"}
  ID                        id-at-mSMQDigestsMig }

-- OID written as MSADat4:568 and expanded with this file's objectidentifier macros.
meetingKeyword ATTRIBUTE ::= {
  WITH SYNTAX               UnboundedDirectoryString
  LDAP-SYNTAX               directoryString.&id
  LDAP-NAME                 {"meetingKeyword"}
  ID                        id-at-meetingKeyword }

-- OID written as MSADat4:844 and expanded with this file's objectidentifier macros.
lDAPIPDenyList ATTRIBUTE ::= {
  WITH SYNTAX               OCTET STRING
  LDAP-SYNTAX               octetString.&id
  LDAP-NAME                 {"lDAPIPDenyList"}
  ID                        id-at-lDAPIPDenyList }

-- OID written as MSADat4:847 and expanded with this file's objectidentifier macros.
installUiLevel ATTRIBUTE ::= {
  WITH SYNTAX               INTEGER
  SINGLE VALUE              TRUE
  LDAP-SYNTAX               integer.&id
  LDAP-NAME                 {"installUiLevel"}
  ID                        id-at-installUiLevel }

-- OID written as MSADat4:894 and expanded with this file's objectidentifier macros.
gPCFileSysPath ATTRIBUTE ::= {
  WITH SYNTAX               UnboundedDirectoryString
  SINGLE VALUE              TRUE
  LDAP-SYNTAX               directoryString.&id
  LDAP-NAME                 {"gPCFileSysPath"}
  ID                        id-at-gPCFileSysPath }

-- OID written as MSADat4:488 and expanded with this file's objectidentifier macros.
fRSStagingPath ATTRIBUTE ::= {
  WITH SYNTAX               UnboundedDirectoryString
  SINGLE VALUE              TRUE
  LDAP-SYNTAX               directoryString.&id
  LDAP-NAME                 {"fRSStagingPath"}
  ID                        id-at-fRSStagingPath }

-- OID written as MSADat2:351 and expanded with this file's objectidentifier macros.
auxiliaryClass ATTRIBUTE ::= {
  WITH SYNTAX               OBJECT IDENTIFIER
  LDAP-SYNTAX               oid.&id
  LDAP-NAME                 {"auxiliaryClass"}
  ID                        id-at-auxiliaryClass }

-- OID written as MSADat4:159 and expanded with this file's objectidentifier macros.
-- SYNTAX MSADlargeInteger expanded to 1.3.6.1.4.1.1466.115.121.1.27 through an objectidentifier macro.
accountExpires ATTRIBUTE ::= {
  WITH SYNTAX               INTEGER
  SINGLE VALUE              TRUE
  LDAP-SYNTAX               integer.&id
  LDAP-NAME                 {"accountExpires"}
  ID                        id-at-accountExpires }

-- OID written as MSADat4:718 and expanded with this file's objectidentifier macros.
dhcpProperties ATTRIBUTE ::= {
  WITH SYNTAX               OCTET STRING
  LDAP-SYNTAX               octetString.&id
  LDAP-NAME                 {"dhcpProperties"}
  ID                        id-at-dhcpProperties }

-- OID written as MSADat4:346 and expanded with this file's objectidentifier macros.
desktopProfile ATTRIBUTE ::= {
  WITH SYNTAX               UnboundedDirectoryString
  SINGLE VALUE              TRUE
  LDAP-SYNTAX               directoryString.&id
  LDAP-NAME                 {"desktopProfile"}
  ID                        id-at-desktopProfile }

-- OID written as MSADat4:762 and expanded with this file's objectidentifier macros.
aCSServiceType ATTRIBUTE ::= {
  WITH SYNTAX               INTEGER
  SINGLE VALUE              TRUE
  LDAP-SYNTAX               integer.&id
  LDAP-NAME                 {"aCSServiceType"}
  ID                        id-at-aCSServiceType }

-- OID written as MSADat4:1213 and expanded with this file's objectidentifier macros.
assocNTAccount ATTRIBUTE ::= {
  WITH SYNTAX               OCTET STRING
  SINGLE VALUE              TRUE
  LDAP-SYNTAX               octetString.&id
  LDAP-NAME                 {"assocNTAccount"}
  ID                        id-at-assocNTAccount }

-- OID written as MSADat4:498 and expanded with this file's objectidentifier macros.
creationWizard ATTRIBUTE ::= {
  WITH SYNTAX               UnboundedDirectoryString
  SINGLE VALUE              TRUE
  LDAP-SYNTAX               directoryString.&id
  LDAP-NAME                 {"creationWizard"}
  ID                        id-at-creationWizard }

-- OID written as MSADat4:253 and expanded with this file's objectidentifier macros.
cOMOtherProgId ATTRIBUTE ::= {
  WITH SYNTAX               UnboundedDirectoryString
  LDAP-SYNTAX               directoryString.&id
  LDAP-NAME                 {"cOMOtherProgId"}
  ID                        id-at-cOMOtherProgId }

-- OID written as MSADat4:202 and expanded with this file's objectidentifier macros.
auditingPolicy ATTRIBUTE ::= {
  WITH SYNTAX               OCTET STRING
  SINGLE VALUE              TRUE
  LDAP-SYNTAX               octetString.&id
  LDAP-NAME                 {"auditingPolicy"}
  ID                        id-at-auditingPolicy }

-- OID written as MSADat4:635 and expanded with this file's objectidentifier macros.
-- SYNTAX MSADlargeInteger expanded to 1.3.6.1.4.1.1466.115.121.1.27 through an objectidentifier macro.
privilegeValue ATTRIBUTE ::= {
  WITH SYNTAX               INTEGER
  SINGLE VALUE              TRUE
  LDAP-SYNTAX               integer.&id
  LDAP-NAME                 {"privilegeValue"}
  ID                        id-at-privilegeValue }

-- OID written as MSADat4:1366 and expanded with this file's objectidentifier macros.
mS-SQL-Location ATTRIBUTE ::= {
  WITH SYNTAX               UnboundedDirectoryString
  SINGLE VALUE              TRUE
  LDAP-SYNTAX               directoryString.&id
  LDAP-NAME                 {"mS-SQL-Location"}
  ID                        id-at-mS-SQL-Location }

-- OID written as MSADat4:1334 and expanded with this file's objectidentifier macros.
pKIDefaultCSPs ATTRIBUTE ::= {
  WITH SYNTAX               UnboundedDirectoryString
  LDAP-SYNTAX               directoryString.&id
  LDAP-NAME                 {"pKIDefaultCSPs"}
  ID                        id-at-pKIDefaultCSPs }

-- OID written as MSADat4:270 and expanded with this file's objectidentifier macros.
printShareName ATTRIBUTE ::= {
  WITH SYNTAX               UnboundedDirectoryString
  LDAP-SYNTAX               directoryString.&id
  LDAP-NAME                 {"printShareName"}
  ID                        id-at-printShareName }

-- OID written as MSADat2:33 and expanded with this file's objectidentifier macros.
isSingleValued ATTRIBUTE ::= {
  WITH SYNTAX               BOOLEAN
  SINGLE VALUE              TRUE
  NO USER MODIFICATION      TRUE
  LDAP-SYNTAX               boolean.&id
  LDAP-NAME                 {"isSingleValued"}
  ID                        id-at-isSingleValued }

-- OID written as MSADat4:472 and expanded with this file's objectidentifier macros.
domainCrossRef ATTRIBUTE ::= {
  WITH SYNTAX               DistinguishedName
  SINGLE VALUE              TRUE
  LDAP-SYNTAX               dn.&id
  LDAP-NAME                 {"domainCrossRef"}
  ID                        id-at-domainCrossRef }

-- OID written as MSADat4:1240 and expanded with this file's objectidentifier macros.
netbootSIFFile ATTRIBUTE ::= {
  WITH SYNTAX               UnboundedDirectoryString
  LDAP-SYNTAX               directoryString.&id
  LDAP-NAME                 {"netbootSIFFile"}
  ID                        id-at-netbootSIFFile }

-- OID written as MSADat4:250 and expanded with this file's objectidentifier macros.
cOMUniqueLIBID ATTRIBUTE ::= {
  WITH SYNTAX               UnboundedDirectoryString
  SINGLE VALUE              TRUE
  LDAP-SYNTAX               directoryString.&id
  LDAP-NAME                 {"cOMUniqueLIBID"}
  ID                        id-at-cOMUniqueLIBID }

-- OID written as MSADat4:657 and expanded with this file's objectidentifier macros.
serviceDNSName ATTRIBUTE ::= {
  WITH SYNTAX               UnboundedDirectoryString
  SINGLE VALUE              TRUE
  LDAP-SYNTAX               directoryString.&id
  LDAP-NAME                 {"serviceDNSName"}
  ID                        id-at-serviceDNSName }

-- OID written as MSADat4:782 and expanded with this file's objectidentifier macros.
objectCategory ATTRIBUTE ::= {
  WITH SYNTAX               DistinguishedName
  SINGLE VALUE              TRUE
  LDAP-SYNTAX               dn.&id
  LDAP-NAME                 {"objectCategory"}
  ID                        id-at-objectCategory }

-- OID written as MSADat4:122 and expanded with this file's objectidentifier macros.
serviceClassID ATTRIBUTE ::= {
  WITH SYNTAX               OCTET STRING
  SINGLE VALUE              TRUE
  LDAP-SYNTAX               octetString.&id
  LDAP-NAME                 {"serviceClassID"}
  ID                        id-at-serviceClassID }

-- OID written as MSADat4:720 and expanded with this file's objectidentifier macros.
-- SYNTAX MSADlargeInteger expanded to 1.3.6.1.4.1.1466.115.121.1.27 through an objectidentifier macro.
dhcpUpdateTime ATTRIBUTE ::= {
  WITH SYNTAX               INTEGER
  SINGLE VALUE              TRUE
  LDAP-SYNTAX               integer.&id
  LDAP-NAME                 {"dhcpUpdateTime"}
  ID                        id-at-dhcpUpdateTime }

-- OID written as MSADat4:221 and expanded with this file's objectidentifier macros.
sAMAccountName ATTRIBUTE ::= {
  WITH SYNTAX               UnboundedDirectoryString
  SINGLE VALUE              TRUE
  LDAP-SYNTAX               directoryString.&id
  LDAP-NAME                 {"sAMAccountName"}
  ID                        id-at-sAMAccountName }

-- OID written as MSADat4:1389 and expanded with this file's objectidentifier macros.
mS-SQL-Language ATTRIBUTE ::= {
  WITH SYNTAX               UnboundedDirectoryString
  SINGLE VALUE              TRUE
  LDAP-SYNTAX               directoryString.&id
  LDAP-NAME                 {"mS-SQL-Language"}
  ID                        id-at-mS-SQL-Language }

-- OID written as MSADat4:777 and expanded with this file's objectidentifier macros.
aCSDSBMRefresh ATTRIBUTE ::= {
  WITH SYNTAX               INTEGER
  SINGLE VALUE              TRUE
  LDAP-SYNTAX               integer.&id
  LDAP-NAME                 {"aCSDSBMRefresh"}
  ID                        id-at-aCSDSBMRefresh }

-- OID written as MSADat4:1393 and expanded with this file's objectidentifier macros.
mS-SQL-Database ATTRIBUTE ::= {
  WITH SYNTAX               UnboundedDirectoryString
  SINGLE VALUE              TRUE
  LDAP-SYNTAX               directoryString.&id
  LDAP-NAME                 {"mS-SQL-Database"}
  ID                        id-at-mS-SQL-Database }

-- OID written as MSADat4:20 and expanded with this file's objectidentifier macros.
cOMInterfaceID ATTRIBUTE ::= {
  WITH SYNTAX               UnboundedDirectoryString
  LDAP-SYNTAX               directoryString.&id
  LDAP-NAME                 {"cOMInterfaceID"}
  ID                        id-at-cOMInterfaceID }

-- OID written as MSADat4:1403 and expanded with this file's objectidentifier macros.
mS-SQL-AllowKnownPullSubscription ATTRIBUTE ::= {
  WITH SYNTAX               BOOLEAN
  SINGLE VALUE              TRUE
  LDAP-SYNTAX               boolean.&id
  LDAP-NAME                 {"mS-SQL-AllowKnownPullSubscription"}
  ID                        id-at-mS-SQL-AllowKnownPullSubscription }

-- OID written as MSADat4:1394 and expanded with this file's objectidentifier macros.
mS-SQL-AllowAnonymousSubscription ATTRIBUTE ::= {
  WITH SYNTAX               BOOLEAN
  SINGLE VALUE              TRUE
  LDAP-SYNTAX               boolean.&id
  LDAP-NAME                 {"mS-SQL-AllowAnonymousSubscription"}
  ID                        id-at-mS-SQL-AllowAnonymousSubscription }

-- OID written as MSADat4:654 and expanded with this file's objectidentifier macros.
managedObjects ATTRIBUTE ::= {
  WITH SYNTAX               DistinguishedName
  NO USER MODIFICATION      TRUE
  LDAP-SYNTAX               dn.&id
  LDAP-NAME                 {"managedObjects"}
  ID                        id-at-managedObjects }

-- OID written as MSADat2:8 and expanded with this file's objectidentifier macros.
possSuperiors ATTRIBUTE ::= {
  WITH SYNTAX               OBJECT IDENTIFIER
  LDAP-SYNTAX               oid.&id
  LDAP-NAME                 {"possSuperiors"}
  ID                        id-at-possSuperiors }

-- OID written as MSADat4:791 and expanded with this file's objectidentifier macros.
transportType ATTRIBUTE ::= {
  WITH SYNTAX               DistinguishedName
  SINGLE VALUE              TRUE
  LDAP-SYNTAX               dn.&id
  LDAP-NAME                 {"transportType"}
  ID                        id-at-transportType }

-- OID written as MSADat4:345 and expanded with this file's objectidentifier macros.
groupPriority ATTRIBUTE ::= {
  WITH SYNTAX               UnboundedDirectoryString
  LDAP-SYNTAX               directoryString.&id
  LDAP-NAME                 {"groupPriority"}
  ID                        id-at-groupPriority }

-- OID written as MSADat4:117 and expanded with this file's objectidentifier macros.
rpcNsPriority ATTRIBUTE ::= {
  WITH SYNTAX               INTEGER
  LDAP-SYNTAX               integer.&id
  LDAP-NAME                 {"rpcNsPriority"}
  ID                        id-at-rpcNsPriority }

-- OID written as MSADat4:917 and expanded with this file's objectidentifier macros.
mSMQQueueType ATTRIBUTE ::= {
  WITH SYNTAX               OCTET STRING
  SINGLE VALUE              TRUE
  LDAP-SYNTAX               octetString.&id
  LDAP-NAME                 {"mSMQQueueType"}
  ID                        id-at-mSMQQueueType }

-- OID written as MSADat4:141 and expanded with this file's objectidentifier macros.
versionNumber ATTRIBUTE ::= {
  WITH SYNTAX               INTEGER
  SINGLE VALUE              TRUE
  LDAP-SYNTAX               integer.&id
  LDAP-NAME                 {"versionNumber"}
  ID                        id-at-versionNumber }

-- OID written as MSADat2:121 and expanded with this file's objectidentifier macros.
-- SYNTAX MSADlargeInteger expanded to 1.3.6.1.4.1.1466.115.121.1.27 through an objectidentifier macro.
uSNLastObjRem ATTRIBUTE ::= {
  WITH SYNTAX               INTEGER
  SINGLE VALUE              TRUE
  NO USER MODIFICATION      TRUE
  LDAP-SYNTAX               integer.&id
  LDAP-NAME                 {"uSNLastObjRem"}
  ID                        id-at-uSNLastObjRem }

-- OID written as MSADat4:1346 and expanded with this file's objectidentifier macros.
templateRoots ATTRIBUTE ::= {
  WITH SYNTAX               DistinguishedName
  LDAP-SYNTAX               dn.&id
  LDAP-NAME                 {"templateRoots"}
  ID                        id-at-templateRoots }

-- OID written as MSADat4:93 and expanded with this file's objectidentifier macros.
pwdProperties ATTRIBUTE ::= {
  WITH SYNTAX               INTEGER
  SINGLE VALUE              TRUE
  LDAP-SYNTAX               integer.&id
  LDAP-NAME                 {"pwdProperties"}
  ID                        id-at-pwdProperties }

-- OID written as MSADat4:290 and expanded with this file's objectidentifier macros.
printNumberUp ATTRIBUTE ::= {
  WITH SYNTAX               INTEGER
  SINGLE VALUE              TRUE
  LDAP-SYNTAX               integer.&id
  LDAP-NAME                 {"printNumberUp"}
  ID                        id-at-printNumberUp }

-- OID written as MSADat4:536 and expanded with this file's objectidentifier macros.
fRSExtensions ATTRIBUTE ::= {
  WITH SYNTAX               OCTET STRING
  SINGLE VALUE              TRUE
  LDAP-SYNTAX               octetString.&id
  LDAP-NAME                 {"fRSExtensions"}
  ID                        id-at-fRSExtensions }

-- OID written as MSADat4:286 and expanded with this file's objectidentifier macros.
printRateUnit ATTRIBUTE ::= {
  WITH SYNTAX               UnboundedDirectoryString
  SINGLE VALUE              TRUE
  LDAP-SYNTAX               directoryString.&id
  LDAP-NAME                 {"printRateUnit"}
  ID                        id-at-printRateUnit }

-- OID written as MSADat4:846 and expanded with this file's objectidentifier macros.
msiScriptSize ATTRIBUTE ::= {
  WITH SYNTAX               INTEGER
  SINGLE VALUE              TRUE
  LDAP-SYNTAX               integer.&id
  LDAP-NAME                 {"msiScriptSize"}
  ID                        id-at-msiScriptSize }

-- OID written as MSADat4:274 and expanded with this file's objectidentifier macros.
printSpooling ATTRIBUTE ::= {
  WITH SYNTAX               UnboundedDirectoryString
  SINGLE VALUE              TRUE
  LDAP-SYNTAX               directoryString.&id
  LDAP-NAME                 {"printSpooling"}
  ID                        id-at-printSpooling }

-- OID written as MSADat4:608 and expanded with this file's objectidentifier macros.
queryPolicyBL ATTRIBUTE ::= {
  WITH SYNTAX               DistinguishedName
  NO USER MODIFICATION      TRUE
  LDAP-SYNTAX               dn.&id
  LDAP-NAME                 {"queryPolicyBL"}
  ID                        id-at-queryPolicyBL }

-- OID written as MSADat4:103 and expanded with this file's objectidentifier macros.
-- SYNTAX MSADlargeInteger expanded to 1.3.6.1.4.1.1466.115.121.1.27 through an objectidentifier macro.
proxyLifetime ATTRIBUTE ::= {
  WITH SYNTAX               INTEGER
  SINGLE VALUE              TRUE
  LDAP-SYNTAX               integer.&id
  LDAP-NAME                 {"proxyLifetime"}
  ID                        id-at-proxyLifetime }

-- OID written as MSADat4:144 and expanded with this file's objectidentifier macros.
operatorCount ATTRIBUTE ::= {
  WITH SYNTAX               INTEGER
  SINGLE VALUE              TRUE
  LDAP-SYNTAX               integer.&id
  LDAP-NAME                 {"operatorCount"}
  ID                        id-at-operatorCount }

-- OID written as MSADat4:860 and expanded with this file's objectidentifier macros.
netbootServer ATTRIBUTE ::= {
  WITH SYNTAX               DistinguishedName
  SINGLE VALUE              TRUE
  LDAP-SYNTAX               dn.&id
  LDAP-NAME                 {"netbootServer"}
  ID                        id-at-netbootServer }

-- OID written as MSADat4:369 and expanded with this file's objectidentifier macros.
fSMORoleOwner ATTRIBUTE ::= {
  WITH SYNTAX               DistinguishedName
  SINGLE VALUE              TRUE
  LDAP-SYNTAX               dn.&id
  LDAP-NAME                 {"fSMORoleOwner"}
  ID                        id-at-fSMORoleOwner }

-- OID written as MSADat4:276 and expanded with this file's objectidentifier macros.
driverVersion ATTRIBUTE ::= {
  WITH SYNTAX               INTEGER
  SINGLE VALUE              TRUE
  LDAP-SYNTAX               integer.&id
  LDAP-NAME                 {"driverVersion"}
  ID                        id-at-driverVersion }

-- OID written as MSADat4:1388 and expanded with this file's objectidentifier macros.
mS-SQL-Version ATTRIBUTE ::= {
  WITH SYNTAX               UnboundedDirectoryString
  SINGLE VALUE              TRUE
  LDAP-SYNTAX               directoryString.&id
  LDAP-NAME                 {"mS-SQL-Version"}
  ID                        id-at-mS-SQL-Version }

-- OID written as MSADat4:939 and expanded with this file's objectidentifier macros.
mSMQNameStyle ATTRIBUTE ::= {
  WITH SYNTAX               BOOLEAN
  SINGLE VALUE              TRUE
  LDAP-SYNTAX               boolean.&id
  LDAP-NAME                 {"mSMQNameStyle"}
  ID                        id-at-mSMQNameStyle }

-- OID written as MSADat2:471 and expanded with this file's objectidentifier macros.
schemaVersion ATTRIBUTE ::= {
  WITH SYNTAX               INTEGER
  LDAP-SYNTAX               integer.&id
  LDAP-NAME                 {"schemaVersion"}
  ID                        id-at-schemaVersion }

-- OID written as MSADat2:436 and expanded with this file's objectidentifier macros.
directReports ATTRIBUTE ::= {
  WITH SYNTAX               DistinguishedName
  NO USER MODIFICATION      TRUE
  LDAP-SYNTAX               dn.&id
  LDAP-NAME                 {"directReports"}
  ID                        id-at-directReports }

-- OID written as MSADat2:255 and expanded with this file's objectidentifier macros.
addressSyntax ATTRIBUTE ::= {
  WITH SYNTAX               OCTET STRING
  SINGLE VALUE              TRUE
  LDAP-SYNTAX               octetString.&id
  LDAP-NAME                 {"addressSyntax"}
  ID                        id-at-addressSyntax }

-- OID written as MSADat4:235 and expanded with this file's objectidentifier macros.
printFormName ATTRIBUTE ::= {
  WITH SYNTAX               UnboundedDirectoryString
  SINGLE VALUE              TRUE
  LDAP-SYNTAX               directoryString.&id
  LDAP-NAME                 {"printFormName"}
  ID                        id-at-printFormName }

-- OID written as MSADat4:15 and expanded with this file's objectidentifier macros.
msiScriptPath ATTRIBUTE ::= {
  WITH SYNTAX               UnboundedDirectoryString
  SINGLE VALUE              TRUE
  LDAP-SYNTAX               directoryString.&id
  LDAP-NAME                 {"msiScriptPath"}
  ID                        id-at-msiScriptPath }

-- OID written as MSADat4:1312 and expanded with this file's objectidentifier macros.
aCSServerList ATTRIBUTE ::= {
  WITH SYNTAX               UnboundedDirectoryString
  LDAP-SYNTAX               directoryString.&id
  LDAP-NAME                 {"aCSServerList"}
  ID                        id-at-aCSServerList }

-- OID written as MSADat4:1305 and expanded with this file's objectidentifier macros.
moveTreeState ATTRIBUTE ::= {
  WITH SYNTAX               OCTET STRING
  LDAP-SYNTAX               octetString.&id
  LDAP-NAME                 {"moveTreeState"}
  ID                        id-at-moveTreeState }

-- OID written as MSADat4:945 and expanded with this file's objectidentifier macros.
mSMQSiteGates ATTRIBUTE ::= {
  WITH SYNTAX               DistinguishedName
  LDAP-SYNTAX               dn.&id
  LDAP-NAME                 {"mSMQSiteGates"}
  ID                        id-at-mSMQSiteGates }

-- OID written as MSADat4:1238 and expanded with this file's objectidentifier macros.
mSMQDsService ATTRIBUTE ::= {
  WITH SYNTAX               BOOLEAN
  SINGLE VALUE              TRUE
  LDAP-SYNTAX               boolean.&id
  LDAP-NAME                 {"mSMQDsService"}
  ID                        id-at-mSMQDsService }

-- OID written as MSADat2:76 and expanded with this file's objectidentifier macros.
objectVersion ATTRIBUTE ::= {
  WITH SYNTAX               INTEGER
  SINGLE VALUE              TRUE
  LDAP-SYNTAX               integer.&id
  LDAP-NAME                 {"objectVersion"}
  ID                        id-at-objectVersion }

-- OID written as MSADat4:1414 and expanded with this file's objectidentifier macros.
dNSTombstoned ATTRIBUTE ::= {
  WITH SYNTAX               BOOLEAN
  SINGLE VALUE              TRUE
  LDAP-SYNTAX               boolean.&id
  LDAP-NAME                 {"dNSTombstoned"}
  ID                        id-at-dNSTombstoned }

-- OID written as MSADat4:941 and expanded with this file's objectidentifier macros.
mSMQLongLived ATTRIBUTE ::= {
  WITH SYNTAX               INTEGER
  SINGLE VALUE              TRUE
  LDAP-SYNTAX               integer.&id
  LDAP-NAME                 {"mSMQLongLived"}
  ID                        id-at-mSMQLongLived }

-- OID written as MSADat4:534 and expanded with this file's objectidentifier macros.
fRSLevelLimit ATTRIBUTE ::= {
  WITH SYNTAX               INTEGER
  SINGLE VALUE              TRUE
  LDAP-SYNTAX               integer.&id
  LDAP-NAME                 {"fRSLevelLimit"}
  ID                        id-at-fRSLevelLimit }

-- OID written as MSADat4:845 and expanded with this file's objectidentifier macros.
msiScriptName ATTRIBUTE ::= {
  WITH SYNTAX               UnboundedDirectoryString
  SINGLE VALUE              TRUE
  LDAP-SYNTAX               directoryString.&id
  LDAP-NAME                 {"msiScriptName"}
  ID                        id-at-msiScriptName }

-- OID written as MSADat4:698 and expanded with this file's objectidentifier macros.
-- SYNTAX MSADlargeInteger expanded to 1.3.6.1.4.1.1466.115.121.1.27 through an objectidentifier macro.
dhcpUniqueKey ATTRIBUTE ::= {
  WITH SYNTAX               INTEGER
  SINGLE VALUE              TRUE
  LDAP-SYNTAX               integer.&id
  LDAP-NAME                 {"dhcpUniqueKey"}
  ID                        id-at-dhcpUniqueKey }

-- OID written as MSADat2:227 and expanded with this file's objectidentifier macros.
extensionName ATTRIBUTE ::= {
  WITH SYNTAX               UnboundedDirectoryString
  LDAP-SYNTAX               directoryString.&id
  LDAP-NAME                 {"extensionName"}
  ID                        id-at-extensionName }

-- OID written as MSADat4:113 and expanded with this file's objectidentifier macros.
rpcNsBindings ATTRIBUTE ::= {
  WITH SYNTAX               UnboundedDirectoryString
  LDAP-SYNTAX               directoryString.&id
  LDAP-NAME                 {"rpcNsBindings"}
  ID                        id-at-rpcNsBindings }

-- OID written as MSADat4:237 and expanded with this file's objectidentifier macros.
printBinNames ATTRIBUTE ::= {
  WITH SYNTAX               UnboundedDirectoryString
  LDAP-SYNTAX               directoryString.&id
  LDAP-NAME                 {"printBinNames"}
  ID                        id-at-printBinNames }

-- OID written as MSADat4:109 and expanded with this file's objectidentifier macros.
replicaSource ATTRIBUTE ::= {
  WITH SYNTAX               UnboundedDirectoryString
  SINGLE VALUE              TRUE
  NO USER MODIFICATION      TRUE
  LDAP-SYNTAX               directoryString.&id
  LDAP-NAME                 {"replicaSource"}
  ID                        id-at-replicaSource }

-- OID written as MSADat4:246 and expanded with this file's objectidentifier macros.
printLanguage ATTRIBUTE ::= {
  WITH SYNTAX               UnboundedDirectoryString
  LDAP-SYNTAX               directoryString.&id
  LDAP-NAME                 {"printLanguage"}
  ID                        id-at-printLanguage }

-- OID written as MSADat4:1365 and expanded with this file's objectidentifier macros.
mS-SQL-Contact ATTRIBUTE ::= {
  WITH SYNTAX               UnboundedDirectoryString
  SINGLE VALUE              TRUE
  LDAP-SYNTAX               directoryString.&id
  LDAP-NAME                 {"mS-SQL-Contact"}
  ID                        id-at-mS-SQL-Contact }

-- OID written as MSADat4:357 and expanded with this file's objectidentifier macros.
nTMixedDomain ATTRIBUTE ::= {
  WITH SYNTAX               INTEGER
  SINGLE VALUE              TRUE
  LDAP-SYNTAX               integer.&id
  LDAP-NAME                 {"nTMixedDomain"}
  ID                        id-at-nTMixedDomain }

-- OID 1.2.840.113556.1.4.483 is also used by calOtherFBURLs in RFC2739Calendar. The LDAP names differ, so this definition was kept.
-- OID written as MSADat4:483 and expanded with this file's objectidentifier macros.
fRSFileFilter ATTRIBUTE ::= {
  WITH SYNTAX               UnboundedDirectoryString
  SINGLE VALUE              TRUE
  LDAP-SYNTAX               directoryString.&id
  LDAP-NAME                 {"fRSFileFilter"}
  ID                        id-at-fRSFileFilter }

-- OID written as MSADat4:332 and expanded with this file's objectidentifier macros.
birthLocation ATTRIBUTE ::= {
  WITH SYNTAX               OCTET STRING
  SINGLE VALUE              TRUE
  LDAP-SYNTAX               octetString.&id
  LDAP-NAME                 {"birthLocation"}
  ID                        id-at-birthLocation }

-- OID written as MSADat4:682 and expanded with this file's objectidentifier macros.
friendlyNames ATTRIBUTE ::= {
  WITH SYNTAX               UnboundedDirectoryString
  LDAP-SYNTAX               directoryString.&id
  LDAP-NAME                 {"friendlyNames"}
  ID                        id-at-friendlyNames }

-- OID written as MSADat4:622 and expanded with this file's objectidentifier macros.
ipsecDataType ATTRIBUTE ::= {
  WITH SYNTAX               INTEGER
  SINGLE VALUE              TRUE
  LDAP-SYNTAX               integer.&id
  LDAP-NAME                 {"ipsecDataType"}
  ID                        id-at-ipsecDataType }

-- OID written as MSADat4:584 and expanded with this file's objectidentifier macros.
meetingRating ATTRIBUTE ::= {
  WITH SYNTAX               UnboundedDirectoryString
  LDAP-SYNTAX               directoryString.&id
  LDAP-NAME                 {"meetingRating"}
  ID                        id-at-meetingRating }

-- OID written as MSADat4:681 and expanded with this file's objectidentifier macros.
indexedScopes ATTRIBUTE ::= {
  WITH SYNTAX               UnboundedDirectoryString
  LDAP-SYNTAX               directoryString.&id
  LDAP-NAME                 {"indexedScopes"}
  ID                        id-at-indexedScopes }

-- OID written as MSADat4:312 and expanded with this file's objectidentifier macros.
rpcNsObjectID ATTRIBUTE ::= {
  WITH SYNTAX               UnboundedDirectoryString
  LDAP-SYNTAX               directoryString.&id
  LDAP-NAME                 {"rpcNsObjectID"}
  ID                        id-at-rpcNsObjectID }

-- OID written as MSADat4:168 and expanded with this file's objectidentifier macros.
-- SYNTAX MSADlargeInteger expanded to 1.3.6.1.4.1.1466.115.121.1.27 through an objectidentifier macro.
modifiedCount ATTRIBUTE ::= {
  WITH SYNTAX               INTEGER
  SINGLE VALUE              TRUE
  LDAP-SYNTAX               integer.&id
  LDAP-NAME                 {"modifiedCount"}
  ID                        id-at-modifiedCount }

-- OID written as MSADat2:218 and expanded with this file's objectidentifier macros.
oMObjectClass ATTRIBUTE ::= {
  WITH SYNTAX               OCTET STRING
  SINGLE VALUE              TRUE
  NO USER MODIFICATION      TRUE
  LDAP-SYNTAX               octetString.&id
  LDAP-NAME                 {"oMObjectClass"}
  ID                        id-at-oMObjectClass }

-- OID written as MSADat4:772 and expanded with this file's objectidentifier macros.
aCSPolicyName ATTRIBUTE ::= {
  WITH SYNTAX               UnboundedDirectoryString
  SINGLE VALUE              TRUE
  LDAP-SYNTAX               directoryString.&id
  LDAP-NAME                 {"aCSPolicyName"}
  ID                        id-at-aCSPolicyName }

-- OID written as MSADat4:502 and expanded with this file's objectidentifier macros.
-- SYNTAX MSADlargeInteger expanded to 1.3.6.1.4.1.1466.115.121.1.27 through an objectidentifier macro.
timeVolChange ATTRIBUTE ::= {
  WITH SYNTAX               INTEGER
  SINGLE VALUE              TRUE
  LDAP-SYNTAX               integer.&id
  LDAP-NAME                 {"timeVolChange"}
  ID                        id-at-timeVolChange }

-- OID written as MSADat4:337 and expanded with this file's objectidentifier macros.
currMachineId ATTRIBUTE ::= {
  WITH SYNTAX               OCTET STRING
  SINGLE VALUE              TRUE
  LDAP-SYNTAX               octetString.&id
  LDAP-NAME                 {"currMachineId"}
  ID                        id-at-currMachineId }

-- OID written as MSADat4:120 and expanded with this file's objectidentifier macros.
schemaFlagsEx ATTRIBUTE ::= {
  WITH SYNTAX               INTEGER
  SINGLE VALUE              TRUE
  LDAP-SYNTAX               integer.&id
  LDAP-NAME                 {"schemaFlagsEx"}
  ID                        id-at-schemaFlagsEx }

-- OID written as MSADat4:1356 and expanded with this file's objectidentifier macros.
validAccesses ATTRIBUTE ::= {
  WITH SYNTAX               INTEGER
  SINGLE VALUE              TRUE
  LDAP-SYNTAX               integer.&id
  LDAP-NAME                 {"validAccesses"}
  ID                        id-at-validAccesses }

-- OID written as MSADat4:158 and expanded with this file's objectidentifier macros.
domainReplica ATTRIBUTE ::= {
  WITH SYNTAX               UnboundedDirectoryString
  SINGLE VALUE              TRUE
  LDAP-SYNTAX               directoryString.&id
  LDAP-NAME                 {"domainReplica"}
  ID                        id-at-domainReplica }

-- OID written as MSADat4:1309 and expanded with this file's objectidentifier macros.
mSMQInterval2 ATTRIBUTE ::= {
  WITH SYNTAX               INTEGER
  SINGLE VALUE              TRUE
  LDAP-SYNTAX               integer.&id
  LDAP-NAME                 {"mSMQInterval2"}
  ID                        id-at-mSMQInterval2 }

-- OID written as MSADat4:1308 and expanded with this file's objectidentifier macros.
mSMQInterval1 ATTRIBUTE ::= {
  WITH SYNTAX               INTEGER
  SINGLE VALUE              TRUE
  LDAP-SYNTAX               integer.&id
  LDAP-NAME                 {"mSMQInterval1"}
  ID                        id-at-mSMQInterval1 }

-- OID written as MSADat4:916 and expanded with this file's objectidentifier macros.
canonicalName ATTRIBUTE ::= {
  WITH SYNTAX               UnboundedDirectoryString
  NO USER MODIFICATION      TRUE
  LDAP-SYNTAX               directoryString.&id
  LDAP-NAME                 {"canonicalName"}
  ID                        id-at-canonicalName }

-- OID written as MSADat4:94 and expanded with this file's objectidentifier macros.
ntPwdHistory ATTRIBUTE ::= {
  WITH SYNTAX               OCTET STRING
  LDAP-SYNTAX               octetString.&id
  LDAP-NAME                 {"ntPwdHistory"}
  ID                        id-at-ntPwdHistory }

-- OID written as MSADat4:133 and expanded with this file's objectidentifier macros.
trustPartner ATTRIBUTE ::= {
  WITH SYNTAX               UnboundedDirectoryString
  SINGLE VALUE              TRUE
  LDAP-SYNTAX               directoryString.&id
  LDAP-NAME                 {"trustPartner"}
  ID                        id-at-trustPartner }

-- OID written as MSADat4:160 and expanded with this file's objectidentifier macros.
lmPwdHistory ATTRIBUTE ::= {
  WITH SYNTAX               OCTET STRING
  LDAP-SYNTAX               octetString.&id
  LDAP-NAME                 {"lmPwdHistory"}
  ID                        id-at-lmPwdHistory }

-- OID written as MSADat4:1380 and expanded with this file's objectidentifier macros.
-- SYNTAX MSADlargeInteger expanded to 1.3.6.1.4.1.1466.115.121.1.27 through an objectidentifier macro.
mS-SQL-Status ATTRIBUTE ::= {
  WITH SYNTAX               INTEGER
  SINGLE VALUE              TRUE
  LDAP-SYNTAX               integer.&id
  LDAP-NAME                 {"mS-SQL-Status"}
  ID                        id-at-mS-SQL-Status }

-- initial capital of "USNIntersite" lowercased so the assignment is a valuereference.
-- OID written as MSADat2:469 and expanded with this file's objectidentifier macros.
uSNIntersite ATTRIBUTE ::= {
  WITH SYNTAX               INTEGER
  SINGLE VALUE              TRUE
  LDAP-SYNTAX               integer.&id
  LDAP-NAME                 {"USNIntersite"}
  ID                        id-at-uSNIntersite }

-- OID written as MSADat4:858 and expanded with this file's objectidentifier macros.
netbootTools ATTRIBUTE ::= {
  WITH SYNTAX               UnboundedDirectoryString
  LDAP-SYNTAX               directoryString.&id
  LDAP-NAME                 {"netbootTools"}
  ID                        id-at-netbootTools }

-- OID written as MSADat4:99 and expanded with this file's objectidentifier macros.
-- SYNTAX MSADlargeInteger expanded to 1.3.6.1.4.1.1466.115.121.1.27 through an objectidentifier macro.
priorSetTime ATTRIBUTE ::= {
  WITH SYNTAX               INTEGER
  SINGLE VALUE              TRUE
  LDAP-SYNTAX               integer.&id
  LDAP-NAME                 {"priorSetTime"}
  ID                        id-at-priorSetTime }

-- OID written as MSADat4:1367 and expanded with this file's objectidentifier macros.
-- SYNTAX MSADlargeInteger expanded to 1.3.6.1.4.1.1466.115.121.1.27 through an objectidentifier macro.
mS-SQL-Memory ATTRIBUTE ::= {
  WITH SYNTAX               INTEGER
  SINGLE VALUE              TRUE
  LDAP-SYNTAX               integer.&id
  LDAP-NAME                 {"mS-SQL-Memory"}
  ID                        id-at-mS-SQL-Memory }

-- OID written as MSADat4:950 and expanded with this file's objectidentifier macros.
mSMQServices ATTRIBUTE ::= {
  WITH SYNTAX               INTEGER
  SINGLE VALUE              TRUE
  LDAP-SYNTAX               integer.&id
  LDAP-NAME                 {"mSMQServices"}
  ID                        id-at-mSMQServices }

-- OID written as MSADat4:27 and expanded with this file's objectidentifier macros.
currentValue ATTRIBUTE ::= {
  WITH SYNTAX               OCTET STRING
  SINGLE VALUE              TRUE
  LDAP-SYNTAX               octetString.&id
  LDAP-NAME                 {"currentValue"}
  ID                        id-at-currentValue }

-- OID written as MSADat4:822 and expanded with this file's objectidentifier macros.
siteLinkList ATTRIBUTE ::= {
  WITH SYNTAX               DistinguishedName
  LDAP-SYNTAX               dn.&id
  LDAP-NAME                 {"siteLinkList"}
  ID                        id-at-siteLinkList }

-- OID written as MSADat4:107 and expanded with this file's objectidentifier macros.
remoteSource ATTRIBUTE ::= {
  WITH SYNTAX               UnboundedDirectoryString
  SINGLE VALUE              TRUE
  LDAP-SYNTAX               directoryString.&id
  LDAP-NAME                 {"remoteSource"}
  ID                        id-at-remoteSource }

-- OID written as MSADat4:325 and expanded with this file's objectidentifier macros.
setupCommand ATTRIBUTE ::= {
  WITH SYNTAX               UnboundedDirectoryString
  SINGLE VALUE              TRUE
  LDAP-SYNTAX               directoryString.&id
  LDAP-NAME                 {"setupCommand"}
  ID                        id-at-setupCommand }

-- OID written as MSADat2:212 and expanded with this file's objectidentifier macros.
dSHeuristics ATTRIBUTE ::= {
  WITH SYNTAX               UnboundedDirectoryString
  SINGLE VALUE              TRUE
  LDAP-SYNTAX               directoryString.&id
  LDAP-NAME                 {"dSHeuristics"}
  ID                        id-at-dSHeuristics }

-- OID written as MSADat4:1336 and expanded with this file's objectidentifier macros.
replInterval ATTRIBUTE ::= {
  WITH SYNTAX               INTEGER
  SINGLE VALUE              TRUE
  LDAP-SYNTAX               integer.&id
  LDAP-NAME                 {"replInterval"}
  ID                        id-at-replInterval }

-- OID written as MSADat4:234 and expanded with this file's objectidentifier macros.
printEndTime ATTRIBUTE ::= {
  WITH SYNTAX               INTEGER
  SINGLE VALUE              TRUE
  LDAP-SYNTAX               integer.&id
  LDAP-NAME                 {"printEndTime"}
  ID                        id-at-printEndTime }

-- OID written as MSADat2:1 and expanded with this file's objectidentifier macros.
instanceType ATTRIBUTE ::= {
  WITH SYNTAX               INTEGER
  SINGLE VALUE              TRUE
  NO USER MODIFICATION      TRUE
  LDAP-SYNTAX               integer.&id
  LDAP-NAME                 {"instanceType"}
  ID                        id-at-instanceType }

-- OID written as MSADat4:722 and expanded with this file's objectidentifier macros.
otherIpPhone ATTRIBUTE ::= {
  WITH SYNTAX               UnboundedDirectoryString
  LDAP-SYNTAX               directoryString.&id
  LDAP-NAME                 {"otherIpPhone"}
  ID                        id-at-otherIpPhone }

-- OID written as MSADat4:965 and expanded with this file's objectidentifier macros.
-- SYNTAX MSADtelex expanded to 1.3.6.1.4.1.1466.115.121.1.44 through an objectidentifier macro.
mSMQSiteName ATTRIBUTE ::= {
  WITH SYNTAX               PrintableString
  SINGLE VALUE              TRUE
  LDAP-SYNTAX               printableString.&id
  LDAP-NAME                 {"mSMQSiteName"}
  ID                        id-at-mSMQSiteName }

-- OID written as MSADat4:579 and expanded with this file's objectidentifier macros.
meetingOwner ATTRIBUTE ::= {
  WITH SYNTAX               UnboundedDirectoryString
  SINGLE VALUE              TRUE
  LDAP-SYNTAX               directoryString.&id
  LDAP-NAME                 {"meetingOwner"}
  ID                        id-at-meetingOwner }

-- OID written as MSADat4:242 and expanded with this file's objectidentifier macros.
printCollate ATTRIBUTE ::= {
  WITH SYNTAX               BOOLEAN
  SINGLE VALUE              TRUE
  LDAP-SYNTAX               boolean.&id
  LDAP-NAME                 {"printCollate"}
  ID                        id-at-printCollate }

-- OID 1.2.840.113556.1.4.480 is also used by calCAPURI in RFC2739Calendar. The LDAP names differ, so this definition was kept.
-- OID written as MSADat4:480 and expanded with this file's objectidentifier macros.
defaultGroup ATTRIBUTE ::= {
  WITH SYNTAX               DistinguishedName
  SINGLE VALUE              TRUE
  LDAP-SYNTAX               dn.&id
  LDAP-NAME                 {"defaultGroup"}
  ID                        id-at-defaultGroup }

-- OID written as MSADat4:79 and expanded with this file's objectidentifier macros.
minPwdLength ATTRIBUTE ::= {
  WITH SYNTAX               INTEGER
  SINGLE VALUE              TRUE
  LDAP-SYNTAX               integer.&id
  LDAP-NAME                 {"minPwdLength"}
  ID                        id-at-minPwdLength }

-- OID written as MSADat4:864 and expanded with this file's objectidentifier macros.
netbootSCPBL ATTRIBUTE ::= {
  WITH SYNTAX               DistinguishedName
  SINGLE VALUE              TRUE
  NO USER MODIFICATION      TRUE
  LDAP-SYNTAX               dn.&id
  LDAP-NAME                 {"netbootSCPBL"}
  ID                        id-at-netbootSCPBL }

-- OID written as MSADat4:650 and expanded with this file's objectidentifier macros.
mhsORAddress ATTRIBUTE ::= {
  WITH SYNTAX               UnboundedDirectoryString
  LDAP-SYNTAX               directoryString.&id
  LDAP-NAME                 {"mhsORAddress"}
  ID                        id-at-mhsORAddress }

-- OID written as MSADat4:367 and expanded with this file's objectidentifier macros.
rpcNsCodeset ATTRIBUTE ::= {
  WITH SYNTAX               UnboundedDirectoryString
  LDAP-SYNTAX               directoryString.&id
  LDAP-NAME                 {"rpcNsCodeset"}
  ID                        id-at-rpcNsCodeset }

-- OID written as MSADat2:14 and expanded with this file's objectidentifier macros.
hasMasterNCs ATTRIBUTE ::= {
  WITH SYNTAX               DistinguishedName
  NO USER MODIFICATION      TRUE
  LDAP-SYNTAX               dn.&id
  LDAP-NAME                 {"hasMasterNCs"}
  ID                        id-at-hasMasterNCs }

-- OID written as MSADat4:952 and expanded with this file's objectidentifier macros.
mSMQMigrated ATTRIBUTE ::= {
  WITH SYNTAX               BOOLEAN
  SINGLE VALUE              TRUE
  LDAP-SYNTAX               boolean.&id
  LDAP-NAME                 {"mSMQMigrated"}
  ID                        id-at-mSMQMigrated }

-- OID written as MSADat2:74 and expanded with this file's objectidentifier macros.
dSASignature ATTRIBUTE ::= {
  WITH SYNTAX               OCTET STRING
  SINGLE VALUE              TRUE
  LDAP-SYNTAX               octetString.&id
  LDAP-NAME                 {"dSASignature"}
  ID                        id-at-dSASignature }

-- OID written as MSADat2:115 and expanded with this file's objectidentifier macros.
invocationId ATTRIBUTE ::= {
  WITH SYNTAX               OCTET STRING
  SINGLE VALUE              TRUE
  NO USER MODIFICATION      TRUE
  LDAP-SYNTAX               octetString.&id
  LDAP-NAME                 {"invocationId"}
  ID                        id-at-invocationId }

-- OID written as MSADat4:254 and expanded with this file's objectidentifier macros.
cOMTypelibId ATTRIBUTE ::= {
  WITH SYNTAX               UnboundedDirectoryString
  LDAP-SYNTAX               directoryString.&id
  LDAP-NAME                 {"cOMTypelibId"}
  ID                        id-at-cOMTypelibId }

-- OID written as MSADat4:26 and expanded with this file's objectidentifier macros.
-- SYNTAX MSADlargeInteger expanded to 1.3.6.1.4.1.1466.115.121.1.27 through an objectidentifier macro.
creationTime ATTRIBUTE ::= {
  WITH SYNTAX               INTEGER
  SINGLE VALUE              TRUE
  LDAP-SYNTAX               integer.&id
  LDAP-NAME                 {"creationTime"}
  ID                        id-at-creationTime }

-- OID written as MSADat4:581 and expanded with this file's objectidentifier macros.
meetingScope ATTRIBUTE ::= {
  WITH SYNTAX               UnboundedDirectoryString
  LDAP-SYNTAX               directoryString.&id
  LDAP-NAME                 {"meetingScope"}
  ID                        id-at-meetingScope }

-- OID written as MSADat4:336 and expanded with this file's objectidentifier macros.
volTableGUID ATTRIBUTE ::= {
  WITH SYNTAX               OCTET STRING
  SINGLE VALUE              TRUE
  LDAP-SYNTAX               octetString.&id
  LDAP-NAME                 {"volTableGUID"}
  ID                        id-at-volTableGUID }

-- OID written as MSADat4:513 and expanded with this file's objectidentifier macros.
siteObjectBL ATTRIBUTE ::= {
  WITH SYNTAX               DistinguishedName
  NO USER MODIFICATION      TRUE
  LDAP-SYNTAX               dn.&id
  LDAP-NAME                 {"siteObjectBL"}
  ID                        id-at-siteObjectBL }

-- OID written as MSADat4:756 and expanded with this file's objectidentifier macros.
aCSTimeOfDay ATTRIBUTE ::= {
  WITH SYNTAX               UnboundedDirectoryString
  SINGLE VALUE              TRUE
  LDAP-SYNTAX               directoryString.&id
  LDAP-NAME                 {"aCSTimeOfDay"}
  ID                        id-at-aCSTimeOfDay }

-- OID written as MSADat4:757 and expanded with this file's objectidentifier macros.
aCSDirection ATTRIBUTE ::= {
  WITH SYNTAX               INTEGER
  SINGLE VALUE              TRUE
  LDAP-SYNTAX               integer.&id
  LDAP-NAME                 {"aCSDirection"}
  ID                        id-at-aCSDirection }

-- OID written as MSADat4:77 and expanded with this file's objectidentifier macros.
-- SYNTAX MSADlargeInteger expanded to 1.3.6.1.4.1.1466.115.121.1.27 through an objectidentifier macro.
maxTicketAge ATTRIBUTE ::= {
  WITH SYNTAX               INTEGER
  SINGLE VALUE              TRUE
  LDAP-SYNTAX               integer.&id
  LDAP-NAME                 {"maxTicketAge"}
  ID                        id-at-maxTicketAge }

-- OID 1.2.840.113556.1.4.481 is also used by calCalAdrURI in RFC2739Calendar. The LDAP names differ, so this definition was kept.
-- OID written as MSADat4:481 and expanded with this file's objectidentifier macros.
schemaUpdate ATTRIBUTE ::= {
  WITH SYNTAX               GeneralizedTime
  SINGLE VALUE              TRUE
  LDAP-SYNTAX               generalizedTime.&id
  LDAP-NAME                 {"schemaUpdate"}
  ID                        id-at-schemaUpdate }

-- OID written as MSADat4:80 and expanded with this file's objectidentifier macros.
-- SYNTAX MSADlargeInteger expanded to 1.3.6.1.4.1.1466.115.121.1.27 through an objectidentifier macro.
minTicketAge ATTRIBUTE ::= {
  WITH SYNTAX               INTEGER
  SINGLE VALUE              TRUE
  LDAP-SYNTAX               integer.&id
  LDAP-NAME                 {"minTicketAge"}
  ID                        id-at-minTicketAge }

-- OID written as MSADat4:628 and expanded with this file's objectidentifier macros.
ipsecNegotiationPolicyReference ATTRIBUTE ::= {
  WITH SYNTAX               DistinguishedName
  SINGLE VALUE              TRUE
  LDAP-SYNTAX               dn.&id
  LDAP-NAME                 {"ipsecNegotiationPolicyReference"}
  ID                        id-at-ipsecNegotiationPolicyReference }

-- OID written as MSADat2:327 and expanded with this file's objectidentifier macros.
helpFileName ATTRIBUTE ::= {
  WITH SYNTAX               UnboundedDirectoryString
  SINGLE VALUE              TRUE
  LDAP-SYNTAX               directoryString.&id
  LDAP-NAME                 {"helpFileName"}
  ID                        id-at-helpFileName }

-- OID written as MSADat4:148 and expanded with this file's objectidentifier macros.
schemaIDGUID ATTRIBUTE ::= {
  WITH SYNTAX               OCTET STRING
  SINGLE VALUE              TRUE
  NO USER MODIFICATION      TRUE
  LDAP-SYNTAX               octetString.&id
  LDAP-NAME                 {"schemaIDGUID"}
  ID                        id-at-schemaIDGUID }

-- OID written as MSADat4:810 and expanded with this file's objectidentifier macros.
createDialog ATTRIBUTE ::= {
  WITH SYNTAX               UnboundedDirectoryString
  SINGLE VALUE              TRUE
  LDAP-SYNTAX               directoryString.&id
  LDAP-NAME                 {"createDialog"}
  ID                        id-at-createDialog }

-- OID written as MSADat4:964 and expanded with this file's objectidentifier macros.
mSMQNt4Flags ATTRIBUTE ::= {
  WITH SYNTAX               INTEGER
  SINGLE VALUE              TRUE
  LDAP-SYNTAX               integer.&id
  LDAP-NAME                 {"mSMQNt4Flags"}
  ID                        id-at-mSMQNt4Flags }

-- OID written as MSADat4:327 and expanded with this file's objectidentifier macros.
packageFlags ATTRIBUTE ::= {
  WITH SYNTAX               INTEGER
  SINGLE VALUE              TRUE
  LDAP-SYNTAX               integer.&id
  LDAP-NAME                 {"packageFlags"}
  ID                        id-at-packageFlags }

-- OID written as MSADat2:464 and expanded with this file's objectidentifier macros.
wWWHomePage ATTRIBUTE ::= {
  WITH SYNTAX               UnboundedDirectoryString
  SINGLE VALUE              TRUE
  LDAP-SYNTAX               directoryString.&id
  LDAP-NAME                 {"wWWHomePage"}
  ID                        id-at-wWWHomePage }

-- OID written as MSADat4:507 and expanded with this file's objectidentifier macros.
volumeCount ATTRIBUTE ::= {
  WITH SYNTAX               INTEGER
  SINGLE VALUE              TRUE
  LDAP-SYNTAX               integer.&id
  LDAP-NAME                 {"volumeCount"}
  ID                        id-at-volumeCount }

-- OID written as MSADat4:273 and expanded with this file's objectidentifier macros.
printStatus ATTRIBUTE ::= {
  WITH SYNTAX               UnboundedDirectoryString
  SINGLE VALUE              TRUE
  LDAP-SYNTAX               directoryString.&id
  LDAP-NAME                 {"printStatus"}
  ID                        id-at-printStatus }

-- OID written as MSADat4:890 and expanded with this file's objectidentifier macros.
uPNSuffixes ATTRIBUTE ::= {
  WITH SYNTAX               UnboundedDirectoryString
  LDAP-SYNTAX               directoryString.&id
  LDAP-NAME                 {"uPNSuffixes"}
  ID                        id-at-uPNSuffixes }

-- OID written as MSADat4:471 and expanded with this file's objectidentifier macros.
trustParent ATTRIBUTE ::= {
  WITH SYNTAX               DistinguishedName
  SINGLE VALUE              TRUE
  LDAP-SYNTAX               dn.&id
  LDAP-NAME                 {"trustParent"}
  ID                        id-at-trustParent }

-- OID written as MSADat4:1301 and expanded with this file's objectidentifier macros.
tokenGroups ATTRIBUTE ::= {
  WITH SYNTAX               OCTET STRING
  LDAP-SYNTAX               octetString.&id
  LDAP-NAME                 {"tokenGroups"}
  ID                        id-at-tokenGroups }

-- OID written as MSADat4:375 and expanded with this file's objectidentifier macros.
systemFlags ATTRIBUTE ::= {
  WITH SYNTAX               INTEGER
  SINGLE VALUE              TRUE
  NO USER MODIFICATION      TRUE
  LDAP-SYNTAX               integer.&id
  LDAP-NAME                 {"systemFlags"}
  ID                        id-at-systemFlags }

-- OID written as MSADat4:667 and expanded with this file's objectidentifier macros.
syncWithSID ATTRIBUTE ::= {
  WITH SYNTAX               OCTET STRING
  SINGLE VALUE              TRUE
  LDAP-SYNTAX               octetString.&id
  LDAP-NAME                 {"syncWithSID"}
  ID                        id-at-syncWithSID }

-- OID written as MSADat4:1306 and expanded with this file's objectidentifier macros.
dNSProperty ATTRIBUTE ::= {
  WITH SYNTAX               OCTET STRING
  LDAP-SYNTAX               octetString.&id
  LDAP-NAME                 {"dNSProperty"}
  ID                        id-at-dNSProperty }

-- OID written as MSADat4:710 and expanded with this file's objectidentifier macros.
superScopes ATTRIBUTE ::= {
  WITH SYNTAX               PrintableString
  LDAP-SYNTAX               printableString.&id
  LDAP-NAME                 {"superScopes"}
  ID                        id-at-superScopes }

-- OID written as MSADat4:1347 and expanded with this file's objectidentifier macros.
sPNMappings ATTRIBUTE ::= {
  WITH SYNTAX               UnboundedDirectoryString
  LDAP-SYNTAX               directoryString.&id
  LDAP-NAME                 {"sPNMappings"}
  ID                        id-at-sPNMappings }

-- OID written as MSADat4:272 and expanded with this file's objectidentifier macros.
printNotify ATTRIBUTE ::= {
  WITH SYNTAX               UnboundedDirectoryString
  SINGLE VALUE              TRUE
  LDAP-SYNTAX               directoryString.&id
  LDAP-NAME                 {"printNotify"}
  ID                        id-at-printNotify }

-- OID written as MSADat4:282 and expanded with this file's objectidentifier macros.
printMemory ATTRIBUTE ::= {
  WITH SYNTAX               INTEGER
  SINGLE VALUE              TRUE
  LDAP-SYNTAX               integer.&id
  LDAP-NAME                 {"printMemory"}
  ID                        id-at-printMemory }

-- OID written as MSADat4:154 and expanded with this file's objectidentifier macros.
serverState ATTRIBUTE ::= {
  WITH SYNTAX               INTEGER
  SINGLE VALUE              TRUE
  LDAP-SYNTAX               integer.&id
  LDAP-NAME                 {"serverState"}
  ID                        id-at-serverState }

-- OID written as MSADat4:942 and expanded with this file's objectidentifier macros.
mSMQVersion ATTRIBUTE ::= {
  WITH SYNTAX               INTEGER
  SINGLE VALUE              TRUE
  LDAP-SYNTAX               integer.&id
  LDAP-NAME                 {"mSMQVersion"}
  ID                        id-at-mSMQVersion }

-- OID written as MSADat4:373 and expanded with this file's objectidentifier macros.
-- SYNTAX MSADlargeInteger expanded to 1.3.6.1.4.1.1466.115.121.1.27 through an objectidentifier macro.
rIDUsedPool ATTRIBUTE ::= {
  WITH SYNTAX               INTEGER
  SINGLE VALUE              TRUE
  NO USER MODIFICATION      TRUE
  LDAP-SYNTAX               integer.&id
  LDAP-NAME                 {"rIDUsedPool"}
  ID                        id-at-rIDUsedPool }

-- OID written as MSADat4:1355 and expanded with this file's objectidentifier macros.
queryFilter ATTRIBUTE ::= {
  WITH SYNTAX               UnboundedDirectoryString
  SINGLE VALUE              TRUE
  LDAP-SYNTAX               directoryString.&id
  LDAP-NAME                 {"queryFilter"}
  ID                        id-at-queryFilter }

-- OID written as MSADat4:300 and expanded with this file's objectidentifier macros.
printerName ATTRIBUTE ::= {
  WITH SYNTAX               UnboundedDirectoryString
  SINGLE VALUE              TRUE
  LDAP-SYNTAX               directoryString.&id
  LDAP-NAME                 {"printerName"}
  ID                        id-at-printerName }

-- OID written as MSADat4:97 and expanded with this file's objectidentifier macros.
preferredOU ATTRIBUTE ::= {
  WITH SYNTAX               DistinguishedName
  SINGLE VALUE              TRUE
  LDAP-SYNTAX               dn.&id
  LDAP-NAME                 {"preferredOU"}
  ID                        id-at-preferredOU }

-- OID written as MSADat4:649 and expanded with this file's objectidentifier macros.
primaryInternationalISDNNumber ATTRIBUTE ::= {
  WITH SYNTAX               UnboundedDirectoryString
  SINGLE VALUE              TRUE
  LDAP-SYNTAX               directoryString.&id
  LDAP-NAME                 {"primaryInternationalISDNNumber"}
  ID                        id-at-primaryInternationalISDNNumber }

-- OID written as MSADat4:333 and expanded with this file's objectidentifier macros.
oMTIndxGuid ATTRIBUTE ::= {
  WITH SYNTAX               OCTET STRING
  SINGLE VALUE              TRUE
  LDAP-SYNTAX               octetString.&id
  LDAP-NAME                 {"oMTIndxGuid"}
  ID                        id-at-oMTIndxGuid }

-- OID written as MSADat4:1337 and expanded with this file's objectidentifier macros.
mSMQUserSid ATTRIBUTE ::= {
  WITH SYNTAX               OCTET STRING
  SINGLE VALUE              TRUE
  NO USER MODIFICATION      TRUE
  LDAP-SYNTAX               octetString.&id
  LDAP-NAME                 {"mSMQUserSid"}
  ID                        id-at-mSMQUserSid }

-- OID written as MSADat4:487 and expanded with this file's objectidentifier macros.
fRSRootPath ATTRIBUTE ::= {
  WITH SYNTAX               UnboundedDirectoryString
  SINGLE VALUE              TRUE
  LDAP-SYNTAX               directoryString.&id
  LDAP-NAME                 {"fRSRootPath"}
  ID                        id-at-fRSRootPath }

-- OID written as MSADat4:918 and expanded with this file's objectidentifier macros.
mSMQJournal ATTRIBUTE ::= {
  WITH SYNTAX               BOOLEAN
  SINGLE VALUE              TRUE
  LDAP-SYNTAX               boolean.&id
  LDAP-NAME                 {"mSMQJournal"}
  ID                        id-at-mSMQJournal }

-- OID written as MSADat4:499 and expanded with this file's objectidentifier macros.
contextMenu ATTRIBUTE ::= {
  WITH SYNTAX               UnboundedDirectoryString
  LDAP-SYNTAX               directoryString.&id
  LDAP-NAME                 {"contextMenu"}
  ID                        id-at-contextMenu }

-- OID written as MSADat4:764 and expanded with this file's objectidentifier macros.
aCSPriority ATTRIBUTE ::= {
  WITH SYNTAX               INTEGER
  SINGLE VALUE              TRUE
  LDAP-SYNTAX               integer.&id
  LDAP-NAME                 {"aCSPriority"}
  ID                        id-at-aCSPriority }

-- OID written as MSADat4:937 and expanded with this file's objectidentifier macros.
mSMQSignKey ATTRIBUTE ::= {
  WITH SYNTAX               OCTET STRING
  SINGLE VALUE              TRUE
  LDAP-SYNTAX               octetString.&id
  LDAP-NAME                 {"mSMQSignKey"}
  ID                        id-at-mSMQSignKey }

-- OID written as MSADat4:359 and expanded with this file's objectidentifier macros.
netbootGUID ATTRIBUTE ::= {
  WITH SYNTAX               OCTET STRING
  SINGLE VALUE              TRUE
  LDAP-SYNTAX               octetString.&id
  LDAP-NAME                 {"netbootGUID"}
  ID                        id-at-netbootGUID }

-- OID written as MSADat4:925 and expanded with this file's objectidentifier macros.
mSMQOwnerID ATTRIBUTE ::= {
  WITH SYNTAX               OCTET STRING
  SINGLE VALUE              TRUE
  LDAP-SYNTAX               octetString.&id
  LDAP-NAME                 {"mSMQOwnerID"}
  ID                        id-at-mSMQOwnerID }

-- OID written as MSADat2:24 and expanded with this file's objectidentifier macros.
mustContain ATTRIBUTE ::= {
  WITH SYNTAX               OBJECT IDENTIFIER
  LDAP-SYNTAX               oid.&id
  LDAP-NAME                 {"mustContain"}
  ID                        id-at-mustContain }

-- OID written as MSADat4:379 and expanded with this file's objectidentifier macros.
dnsAllowXFR ATTRIBUTE ::= {
  WITH SYNTAX               BOOLEAN
  SINGLE VALUE              TRUE
  LDAP-SYNTAX               boolean.&id
  LDAP-NAME                 {"dnsAllowXFR"}
  ID                        id-at-dnsAllowXFR }

-- OID written as MSADat4:1379 and expanded with this file's objectidentifier macros.
mS-SQL-Vines ATTRIBUTE ::= {
  WITH SYNTAX               UnboundedDirectoryString
  SINGLE VALUE              TRUE
  LDAP-SYNTAX               directoryString.&id
  LDAP-NAME                 {"mS-SQL-Vines"}
  ID                        id-at-mS-SQL-Vines }

-- OID written as MSADat4:948 and expanded with this file's objectidentifier macros.
mSMQDigests ATTRIBUTE ::= {
  WITH SYNTAX               OCTET STRING
  LDAP-SYNTAX               octetString.&id
  LDAP-NAME                 {"mSMQDigests"}
  ID                        id-at-mSMQDigests }

-- OID written as MSADat4:662 and expanded with this file's objectidentifier macros.
-- SYNTAX MSADlargeInteger expanded to 1.3.6.1.4.1.1466.115.121.1.27 through an objectidentifier macro.
lockoutTime ATTRIBUTE ::= {
  WITH SYNTAX               INTEGER
  SINGLE VALUE              TRUE
  LDAP-SYNTAX               integer.&id
  LDAP-NAME                 {"lockoutTime"}
  ID                        id-at-lockoutTime }

-- OID written as MSADat4:53 and expanded with this file's objectidentifier macros.
-- SYNTAX MSADlargeInteger expanded to 1.3.6.1.4.1.1466.115.121.1.27 through an objectidentifier macro.
lastSetTime ATTRIBUTE ::= {
  WITH SYNTAX               INTEGER
  SINGLE VALUE              TRUE
  LDAP-SYNTAX               integer.&id
  LDAP-NAME                 {"lastSetTime"}
  ID                        id-at-lastSetTime }

-- OID written as MSADat4:25 and expanded with this file's objectidentifier macros.
countryCode ATTRIBUTE ::= {
  WITH SYNTAX               INTEGER
  SINGLE VALUE              TRUE
  LDAP-SYNTAX               integer.&id
  LDAP-NAME                 {"countryCode"}
  ID                        id-at-countryCode }

-- OID written as MSADat4:1377 and expanded with this file's objectidentifier macros.
mS-SQL-TCPIP ATTRIBUTE ::= {
  WITH SYNTAX               UnboundedDirectoryString
  SINGLE VALUE              TRUE
  LDAP-SYNTAX               directoryString.&id
  LDAP-NAME                 {"mS-SQL-TCPIP"}
  ID                        id-at-mS-SQL-TCPIP }

-- OID written as MSADat4:934 and expanded with this file's objectidentifier macros.
mSMQForeign ATTRIBUTE ::= {
  WITH SYNTAX               BOOLEAN
  SINGLE VALUE              TRUE
  LDAP-SYNTAX               boolean.&id
  LDAP-NAME                 {"mSMQForeign"}
  ID                        id-at-mSMQForeign }

-- OID written as MSADat4:571 and expanded with this file's objectidentifier macros.
meetingType ATTRIBUTE ::= {
  WITH SYNTAX               UnboundedDirectoryString
  SINGLE VALUE              TRUE
  LDAP-SYNTAX               directoryString.&id
  LDAP-NAME                 {"meetingType"}
  ID                        id-at-meetingType }

-- OID written as MSADat4:714 and expanded with this file's objectidentifier macros.
dhcpOptions ATTRIBUTE ::= {
  WITH SYNTAX               OCTET STRING
  LDAP-SYNTAX               octetString.&id
  LDAP-NAME                 {"dhcpOptions"}
  ID                        id-at-dhcpOptions }

-- OID written as MSADat4:704 and expanded with this file's objectidentifier macros.
dhcpServers ATTRIBUTE ::= {
  WITH SYNTAX               PrintableString
  LDAP-SYNTAX               printableString.&id
  LDAP-NAME                 {"dhcpServers"}
  ID                        id-at-dhcpServers }

-- OID written as MSADat4:283 and expanded with this file's objectidentifier macros.
assetNumber ATTRIBUTE ::= {
  WITH SYNTAX               UnboundedDirectoryString
  SINGLE VALUE              TRUE
  LDAP-SYNTAX               directoryString.&id
  LDAP-NAME                 {"assetNumber"}
  ID                        id-at-assetNumber }

-- OID written as MSADat2:350 and expanded with this file's objectidentifier macros.
-- SYNTAX MSADtelex expanded to 1.3.6.1.4.1.1466.115.121.1.44 through an objectidentifier macro.
addressType ATTRIBUTE ::= {
  WITH SYNTAX               PrintableString
  SINGLE VALUE              TRUE
  LDAP-SYNTAX               printableString.&id
  LDAP-NAME                 {"addressType"}
  ID                        id-at-addressType }

-- OID written as MSADat4:940 and expanded with this file's objectidentifier macros.
-- SYNTAX MSADtelex expanded to 1.3.6.1.4.1.1466.115.121.1.44 through an objectidentifier macro.
mSMQCSPName ATTRIBUTE ::= {
  WITH SYNTAX               PrintableString
  SINGLE VALUE              TRUE
  LDAP-SYNTAX               printableString.&id
  LDAP-NAME                 {"mSMQCSPName"}
  ID                        id-at-mSMQCSPName }

-- OID written as MSADat4:671 and expanded with this file's objectidentifier macros.
msiFileList ATTRIBUTE ::= {
  WITH SYNTAX               UnboundedDirectoryString
  LDAP-SYNTAX               directoryString.&id
  LDAP-NAME                 {"msiFileList"}
  ID                        id-at-msiFileList }

-- OID written as MSADat4:619 and expanded with this file's objectidentifier macros.
dNSHostName ATTRIBUTE ::= {
  WITH SYNTAX               UnboundedDirectoryString
  SINGLE VALUE              TRUE
  LDAP-SYNTAX               directoryString.&id
  LDAP-NAME                 {"dNSHostName"}
  ID                        id-at-dNSHostName }

-- OID written as MSADat4:705 and expanded with this file's objectidentifier macros.
dhcpSubnets ATTRIBUTE ::= {
  WITH SYNTAX               PrintableString
  LDAP-SYNTAX               printableString.&id
  LDAP-NAME                 {"dhcpSubnets"}
  ID                        id-at-dhcpSubnets }

-- OID written as MSADat4:1328 and expanded with this file's objectidentifier macros.
pKIKeyUsage ATTRIBUTE ::= {
  WITH SYNTAX               OCTET STRING
  SINGLE VALUE              TRUE
  LDAP-SYNTAX               octetString.&id
  LDAP-NAME                 {"pKIKeyUsage"}
  ID                        id-at-pKIKeyUsage }

-- OID written as MSADat2:30 and expanded with this file's objectidentifier macros.
attributeID ATTRIBUTE ::= {
  WITH SYNTAX               OBJECT IDENTIFIER
  SINGLE VALUE              TRUE
  NO USER MODIFICATION      TRUE
  LDAP-SYNTAX               oid.&id
  LDAP-NAME                 {"attributeID"}
  ID                        id-at-attributeID }

-- OID written as MSADat4:506 and expanded with this file's objectidentifier macros.
objectCount ATTRIBUTE ::= {
  WITH SYNTAX               INTEGER
  SINGLE VALUE              TRUE
  LDAP-SYNTAX               integer.&id
  LDAP-NAME                 {"objectCount"}
  ID                        id-at-objectCount }

-- OID written as MSADat4:503 and expanded with this file's objectidentifier macros.
-- SYNTAX MSADlargeInteger expanded to 1.3.6.1.4.1.1466.115.121.1.27 through an objectidentifier macro.
timeRefresh ATTRIBUTE ::= {
  WITH SYNTAX               INTEGER
  SINGLE VALUE              TRUE
  LDAP-SYNTAX               integer.&id
  LDAP-NAME                 {"timeRefresh"}
  ID                        id-at-timeRefresh }

-- OID written as MSADat4:139 and expanded with this file's objectidentifier macros.
profilePath ATTRIBUTE ::= {
  WITH SYNTAX               UnboundedDirectoryString
  SINGLE VALUE              TRUE
  LDAP-SYNTAX               directoryString.&id
  LDAP-NAME                 {"profilePath"}
  ID                        id-at-profilePath }

-- OID written as MSADat4:818 and expanded with this file's objectidentifier macros.
productCode ATTRIBUTE ::= {
  WITH SYNTAX               OCTET STRING
  SINGLE VALUE              TRUE
  LDAP-SYNTAX               octetString.&id
  LDAP-NAME                 {"productCode"}
  ID                        id-at-productCode }

-- OID written as MSADat4:647 and expanded with this file's objectidentifier macros.
otherMobile ATTRIBUTE ::= {
  WITH SYNTAX               UnboundedDirectoryString
  LDAP-SYNTAX               directoryString.&id
  LDAP-NAME                 {"otherMobile"}
  ID                        id-at-otherMobile }

-- OID written as MSADat4:12 and expanded with this file's objectidentifier macros.
badPwdCount ATTRIBUTE ::= {
  WITH SYNTAX               INTEGER
  SINGLE VALUE              TRUE
  LDAP-SYNTAX               integer.&id
  LDAP-NAME                 {"badPwdCount"}
  ID                        id-at-badPwdCount }

-- OID written as MSADat4:1368 and expanded with this file's objectidentifier macros.
mS-SQL-Build ATTRIBUTE ::= {
  WITH SYNTAX               INTEGER
  SINGLE VALUE              TRUE
  LDAP-SYNTAX               integer.&id
  LDAP-NAME                 {"mS-SQL-Build"}
  ID                        id-at-mS-SQL-Build }

-- OID written as MSADat4:87 and expanded with this file's objectidentifier macros.
nETBIOSName ATTRIBUTE ::= {
  WITH SYNTAX               UnboundedDirectoryString
  SINGLE VALUE              TRUE
  LDAP-SYNTAX               directoryString.&id
  LDAP-NAME                 {"nETBIOSName"}
  ID                        id-at-nETBIOSName }

-- OID written as MSADat4:1395 and expanded with this file's objectidentifier macros.
mS-SQL-Alias ATTRIBUTE ::= {
  WITH SYNTAX               UnboundedDirectoryString
  SINGLE VALUE              TRUE
  LDAP-SYNTAX               directoryString.&id
  LDAP-NAME                 {"mS-SQL-Alias"}
  ID                        id-at-mS-SQL-Alias }

-- OID written as MSADat4:75 and expanded with this file's objectidentifier macros.
-- SYNTAX MSADlargeInteger expanded to 1.3.6.1.4.1.1466.115.121.1.27 through an objectidentifier macro.
maxRenewAge ATTRIBUTE ::= {
  WITH SYNTAX               INTEGER
  SINGLE VALUE              TRUE
  LDAP-SYNTAX               integer.&id
  LDAP-NAME                 {"maxRenewAge"}
  ID                        id-at-maxRenewAge }

-- OID written as MSADat4:806 and expanded with this file's objectidentifier macros.
treatAsLeaf ATTRIBUTE ::= {
  WITH SYNTAX               BOOLEAN
  SINGLE VALUE              TRUE
  LDAP-SYNTAX               boolean.&id
  LDAP-NAME                 {"treatAsLeaf"}
  ID                        id-at-treatAsLeaf }

-- OID written as MSADat4:960 and expanded with this file's objectidentifier macros.
mSMQNt4Stub ATTRIBUTE ::= {
  WITH SYNTAX               INTEGER
  LDAP-SYNTAX               integer.&id
  LDAP-NAME                 {"mSMQNt4Stub"}
  ID                        id-at-mSMQNt4Stub }

-- OID written as MSADat4:324 and expanded with this file's objectidentifier macros.
packageType ATTRIBUTE ::= {
  WITH SYNTAX               INTEGER
  SINGLE VALUE              TRUE
  LDAP-SYNTAX               integer.&id
  LDAP-NAME                 {"packageType"}
  ID                        id-at-packageType }

-- OID written as MSADat4:1212 and expanded with this file's objectidentifier macros.
isEphemeral ATTRIBUTE ::= {
  WITH SYNTAX               BOOLEAN
  SINGLE VALUE              TRUE
  NO USER MODIFICATION      TRUE
  LDAP-SYNTAX               boolean.&id
  LDAP-NAME                 {"isEphemeral"}
  ID                        id-at-isEphemeral }

-- OID written as MSADat2:36 and expanded with this file's objectidentifier macros.
dMDLocation ATTRIBUTE ::= {
  WITH SYNTAX               DistinguishedName
  SINGLE VALUE              TRUE
  NO USER MODIFICATION      TRUE
  LDAP-SYNTAX               dn.&id
  LDAP-NAME                 {"dMDLocation"}
  ID                        id-at-dMDLocation }

-- OID written as MSADat4:715 and expanded with this file's objectidentifier macros.
dhcpClasses ATTRIBUTE ::= {
  WITH SYNTAX               OCTET STRING
  LDAP-SYNTAX               octetString.&id
  LDAP-NAME                 {"dhcpClasses"}
  ID                        id-at-dhcpClasses }

-- OID written as MSADat4:39 and expanded with this file's objectidentifier macros.
-- SYNTAX MSADlargeInteger expanded to 1.3.6.1.4.1.1466.115.121.1.27 through an objectidentifier macro.
forceLogoff ATTRIBUTE ::= {
  WITH SYNTAX               INTEGER
  SINGLE VALUE              TRUE
  LDAP-SYNTAX               integer.&id
  LDAP-NAME                 {"forceLogoff"}
  ID                        id-at-forceLogoff }

-- OID written as MSADat2:2 and expanded with this file's objectidentifier macros.
whenCreated ATTRIBUTE ::= {
  WITH SYNTAX               GeneralizedTime
  SINGLE VALUE              TRUE
  NO USER MODIFICATION      TRUE
  LDAP-SYNTAX               generalizedTime.&id
  LDAP-NAME                 {"whenCreated"}
  ID                        id-at-whenCreated }

-- OID written as MSADat4:566 and expanded with this file's objectidentifier macros.
meetingName ATTRIBUTE ::= {
  WITH SYNTAX               UnboundedDirectoryString
  SINGLE VALUE              TRUE
  LDAP-SYNTAX               directoryString.&id
  LDAP-NAME                 {"meetingName"}
  ID                        id-at-meetingName }

-- OID written as MSADat4:786 and expanded with this file's objectidentifier macros.
mailAddress ATTRIBUTE ::= {
  WITH SYNTAX               UnboundedDirectoryString
  SINGLE VALUE              TRUE
  LDAP-SYNTAX               directoryString.&id
  LDAP-NAME                 {"mailAddress"}
  ID                        id-at-mailAddress }

-- OID written as MSADat4:590 and expanded with this file's objectidentifier macros.
meetingBlob ATTRIBUTE ::= {
  WITH SYNTAX               OCTET STRING
  SINGLE VALUE              TRUE
  LDAP-SYNTAX               octetString.&id
  LDAP-NAME                 {"meetingBlob"}
  ID                        id-at-meetingBlob }

-- OID written as MSADat4:71 and expanded with this file's objectidentifier macros.
machineRole ATTRIBUTE ::= {
  WITH SYNTAX               INTEGER
  SINGLE VALUE              TRUE
  LDAP-SYNTAX               integer.&id
  LDAP-NAME                 {"machineRole"}
  ID                        id-at-machineRole }

-- OID written as MSADat2:334 and expanded with this file's objectidentifier macros.
searchFlags ATTRIBUTE ::= {
  WITH SYNTAX               INTEGER
  SINGLE VALUE              TRUE
  LDAP-SYNTAX               integer.&id
  LDAP-NAME                 {"searchFlags"}
  ID                        id-at-searchFlags }

-- OID written as MSADat2:3 and expanded with this file's objectidentifier macros.
whenChanged ATTRIBUTE ::= {
  WITH SYNTAX               GeneralizedTime
  SINGLE VALUE              TRUE
  NO USER MODIFICATION      TRUE
  LDAP-SYNTAX               generalizedTime.&id
  LDAP-NAME                 {"whenChanged"}
  ID                        id-at-whenChanged }

-- OID written as MSADat4:702 and expanded with this file's objectidentifier macros.
dhcpObjName ATTRIBUTE ::= {
  WITH SYNTAX               UnboundedDirectoryString
  SINGLE VALUE              TRUE
  LDAP-SYNTAX               directoryString.&id
  LDAP-NAME                 {"dhcpObjName"}
  ID                        id-at-dhcpObjName }

-- OID written as MSADat4:897 and expanded with this file's objectidentifier macros.
-- SYNTAX MSADlargeInteger expanded to 1.3.6.1.4.1.1466.115.121.1.27 through an objectidentifier macro.
aCSMaxAggregatePeakRatePerUser ATTRIBUTE ::= {
  WITH SYNTAX               INTEGER
  SINGLE VALUE              TRUE
  LDAP-SYNTAX               integer.&id
  LDAP-NAME                 {"aCSMaxAggregatePeakRatePerUser"}
  ID                        id-at-aCSMaxAggregatePeakRatePerUser }

-- OID written as MSADat4:326 and expanded with this file's objectidentifier macros.
packageName ATTRIBUTE ::= {
  WITH SYNTAX               UnboundedDirectoryString
  SINGLE VALUE              TRUE
  LDAP-SYNTAX               directoryString.&id
  LDAP-NAME                 {"packageName"}
  ID                        id-at-packageName }

-- OID written as MSADat4:170 and expanded with this file's objectidentifier macros.
systemOnly ATTRIBUTE ::= {
  WITH SYNTAX               BOOLEAN
  SINGLE VALUE              TRUE
  NO USER MODIFICATION      TRUE
  LDAP-SYNTAX               boolean.&id
  LDAP-NAME                 {"systemOnly"}
  ID                        id-at-systemOnly }

-- OID written as MSADat4:935 and expanded with this file's objectidentifier macros.
mSMQOSType ATTRIBUTE ::= {
  WITH SYNTAX               INTEGER
  SINGLE VALUE              TRUE
  LDAP-SYNTAX               integer.&id
  LDAP-NAME                 {"mSMQOSType"}
  ID                        id-at-mSMQOSType }

-- OID written as MSADat4:680 and expanded with this file's objectidentifier macros.
queryPoint ATTRIBUTE ::= {
  WITH SYNTAX               UnboundedDirectoryString
  SINGLE VALUE              TRUE
  LDAP-SYNTAX               directoryString.&id
  LDAP-NAME                 {"queryPoint"}
  ID                        id-at-queryPoint }

-- OID written as MSADat4:271 and expanded with this file's objectidentifier macros.
printOwner ATTRIBUTE ::= {
  WITH SYNTAX               UnboundedDirectoryString
  SINGLE VALUE              TRUE
  LDAP-SYNTAX               directoryString.&id
  LDAP-NAME                 {"printOwner"}
  ID                        id-at-printOwner }

-- OID written as MSADat2:19 and expanded with this file's objectidentifier macros.
-- SYNTAX MSADlargeInteger expanded to 1.3.6.1.4.1.1466.115.121.1.27 through an objectidentifier macro.
uSNCreated ATTRIBUTE ::= {
  WITH SYNTAX               INTEGER
  SINGLE VALUE              TRUE
  NO USER MODIFICATION      TRUE
  LDAP-SYNTAX               integer.&id
  LDAP-NAME                 {"uSNCreated"}
  ID                        id-at-uSNCreated }

-- OID written as MSADat4:494 and expanded with this file's objectidentifier macros.
siteServer ATTRIBUTE ::= {
  WITH SYNTAX               DistinguishedName
  LDAP-SYNTAX               dn.&id
  LDAP-NAME                 {"siteServer"}
  ID                        id-at-siteServer }

-- OID written as MSADat4:114 and expanded with this file's objectidentifier macros.
rpcNsGroup ATTRIBUTE ::= {
  WITH SYNTAX               UnboundedDirectoryString
  LDAP-SYNTAX               directoryString.&id
  LDAP-NAME                 {"rpcNsGroup"}
  ID                        id-at-rpcNsGroup }

-- OID written as MSADat4:609 and expanded with this file's objectidentifier macros.
sIDHistory ATTRIBUTE ::= {
  WITH SYNTAX               OCTET STRING
  NO USER MODIFICATION      TRUE
  LDAP-SYNTAX               octetString.&id
  LDAP-NAME                 {"sIDHistory"}
  ID                        id-at-sIDHistory }

-- OID written as MSADat4:882 and expanded with this file's objectidentifier macros.
fRSVersion ATTRIBUTE ::= {
  WITH SYNTAX               UnboundedDirectoryString
  SINGLE VALUE              TRUE
  LDAP-SYNTAX               directoryString.&id
  LDAP-NAME                 {"fRSVersion"}
  ID                        id-at-fRSVersion }

-- OID written as MSADat4:64 and expanded with this file's objectidentifier macros.
logonHours ATTRIBUTE ::= {
  WITH SYNTAX               OCTET STRING
  SINGLE VALUE              TRUE
  LDAP-SYNTAX               octetString.&id
  LDAP-NAME                 {"logonHours"}
  ID                        id-at-logonHours }

-- OID written as MSADat4:854 and expanded with this file's objectidentifier macros.
netbootAnswerOnlyValidClients ATTRIBUTE ::= {
  WITH SYNTAX               BOOLEAN
  SINGLE VALUE              TRUE
  LDAP-SYNTAX               boolean.&id
  LDAP-NAME                 {"netbootAnswerOnlyValidClients"}
  ID                        id-at-netbootAnswerOnlyValidClients }

-- OID written as MSADat4:96 and expanded with this file's objectidentifier macros.
-- SYNTAX MSADlargeInteger expanded to 1.3.6.1.4.1.1466.115.121.1.27 through an objectidentifier macro.
pwdLastSet ATTRIBUTE ::= {
  WITH SYNTAX               INTEGER
  SINGLE VALUE              TRUE
  LDAP-SYNTAX               integer.&id
  LDAP-NAME                 {"pwdLastSet"}
  ID                        id-at-pwdLastSet }

-- OID written as MSADat4:243 and expanded with this file's objectidentifier macros.
printColor ATTRIBUTE ::= {
  WITH SYNTAX               BOOLEAN
  SINGLE VALUE              TRUE
  LDAP-SYNTAX               boolean.&id
  LDAP-NAME                 {"printColor"}
  ID                        id-at-printColor }

-- OID written as MSADat4:1391 and expanded with this file's objectidentifier macros.
mS-SQL-Type ATTRIBUTE ::= {
  WITH SYNTAX               UnboundedDirectoryString
  SINGLE VALUE              TRUE
  LDAP-SYNTAX               directoryString.&id
  LDAP-NAME                 {"mS-SQL-Type"}
  ID                        id-at-mS-SQL-Type }

-- OID written as MSADat4:40 and expanded with this file's objectidentifier macros.
fromServer ATTRIBUTE ::= {
  WITH SYNTAX               DistinguishedName
  SINGLE VALUE              TRUE
  LDAP-SYNTAX               dn.&id
  LDAP-NAME                 {"fromServer"}
  ID                        id-at-fromServer }

-- OID written as MSADat4:157 and expanded with this file's objectidentifier macros.
serverRole ATTRIBUTE ::= {
  WITH SYNTAX               INTEGER
  SINGLE VALUE              TRUE
  LDAP-SYNTAX               integer.&id
  LDAP-NAME                 {"serverRole"}
  ID                        id-at-serverRole }

-- OID written as MSADat4:100 and expanded with this file's objectidentifier macros.
priorValue ATTRIBUTE ::= {
  WITH SYNTAX               OCTET STRING
  SINGLE VALUE              TRUE
  LDAP-SYNTAX               octetString.&id
  LDAP-NAME                 {"priorValue"}
  ID                        id-at-priorValue }

-- OID written as MSADat4:169 and expanded with this file's objectidentifier macros.
logonCount ATTRIBUTE ::= {
  WITH SYNTAX               INTEGER
  SINGLE VALUE              TRUE
  LDAP-SYNTAX               integer.&id
  LDAP-NAME                 {"logonCount"}
  ID                        id-at-logonCount }

-- OID written as MSADat4:90 and expanded with this file's objectidentifier macros.
unicodePwd ATTRIBUTE ::= {
  WITH SYNTAX               OCTET STRING
  SINGLE VALUE              TRUE
  LDAP-SYNTAX               octetString.&id
  LDAP-NAME                 {"unicodePwd"}
  ID                        id-at-unicodePwd }

-- OID written as MSADat2:21 and expanded with this file's objectidentifier macros.
subClassOf ATTRIBUTE ::= {
  WITH SYNTAX               OBJECT IDENTIFIER
  SINGLE VALUE              TRUE
  NO USER MODIFICATION      TRUE
  LDAP-SYNTAX               oid.&id
  LDAP-NAME                 {"subClassOf"}
  ID                        id-at-subClassOf }

-- OID written as MSADat4:1396 and expanded with this file's objectidentifier macros.
-- SYNTAX MSADlargeInteger expanded to 1.3.6.1.4.1.1466.115.121.1.27 through an objectidentifier macro.
mS-SQL-Size ATTRIBUTE ::= {
  WITH SYNTAX               INTEGER
  SINGLE VALUE              TRUE
  LDAP-SYNTAX               integer.&id
  LDAP-NAME                 {"mS-SQL-Size"}
  ID                        id-at-mS-SQL-Size }

-- OID written as MSADat4:101 and expanded with this file's objectidentifier macros.
privateKey ATTRIBUTE ::= {
  WITH SYNTAX               OCTET STRING
  SINGLE VALUE              TRUE
  LDAP-SYNTAX               octetString.&id
  LDAP-NAME                 {"privateKey"}
  ID                        id-at-privateKey }

-- OID written as MSADat4:512 and expanded with this file's objectidentifier macros.
siteObject ATTRIBUTE ::= {
  WITH SYNTAX               DistinguishedName
  SINGLE VALUE              TRUE
  LDAP-SYNTAX               dn.&id
  LDAP-NAME                 {"siteObject"}
  ID                        id-at-siteObject }

-- OID written as MSADat4:62 and expanded with this file's objectidentifier macros.
scriptPath ATTRIBUTE ::= {
  WITH SYNTAX               UnboundedDirectoryString
  SINGLE VALUE              TRUE
  LDAP-SYNTAX               directoryString.&id
  LDAP-NAME                 {"scriptPath"}
  ID                        id-at-scriptPath }

-- OID written as MSADat4:223 and expanded with this file's objectidentifier macros.
serverName ATTRIBUTE ::= {
  WITH SYNTAX               UnboundedDirectoryString
  SINGLE VALUE              TRUE
  LDAP-SYNTAX               directoryString.&id
  LDAP-NAME                 {"serverName"}
  ID                        id-at-serverName }

-- OID written as MSADat4:953 and expanded with this file's objectidentifier macros.
mSMQSiteID ATTRIBUTE ::= {
  WITH SYNTAX               OCTET STRING
  SINGLE VALUE              TRUE
  LDAP-SYNTAX               octetString.&id
  LDAP-NAME                 {"mSMQSiteID"}
  ID                        id-at-mSMQSiteID }

-- OID written as MSADat4:340 and expanded with this file's objectidentifier macros.
rightsGuid ATTRIBUTE ::= {
  WITH SYNTAX               UnboundedDirectoryString
  SINGLE VALUE              TRUE
  LDAP-SYNTAX               directoryString.&id
  LDAP-NAME                 {"rightsGuid"}
  ID                        id-at-rightsGuid }

-- OID written as MSADat4:374 and expanded with this file's objectidentifier macros.
rIDNextRID ATTRIBUTE ::= {
  WITH SYNTAX               INTEGER
  SINGLE VALUE              TRUE
  NO USER MODIFICATION      TRUE
  LDAP-SYNTAX               integer.&id
  LDAP-NAME                 {"rIDNextRID"}
  ID                        id-at-rIDNextRID }

-- OID written as MSADat4:583 and expanded with this file's objectidentifier macros.
meetingURL ATTRIBUTE ::= {
  WITH SYNTAX               UnboundedDirectoryString
  LDAP-SYNTAX               directoryString.&id
  LDAP-NAME                 {"meetingURL"}
  ID                        id-at-meetingURL }

-- OID written as MSADat2:400 and expanded with this file's objectidentifier macros.
addressEntryDisplayTableMSDOS ATTRIBUTE ::= {
  WITH SYNTAX               OCTET STRING
  SINGLE VALUE              TRUE
  LDAP-SYNTAX               octetString.&id
  LDAP-NAME                 {"addressEntryDisplayTableMSDOS"}
  ID                        id-at-addressEntryDisplayTableMSDOS }

-- OID written as MSADat4:76 and expanded with this file's objectidentifier macros.
-- SYNTAX MSADlargeInteger expanded to 1.3.6.1.4.1.1466.115.121.1.27 through an objectidentifier macro.
maxStorage ATTRIBUTE ::= {
  WITH SYNTAX               INTEGER
  SINGLE VALUE              TRUE
  LDAP-SYNTAX               integer.&id
  LDAP-NAME                 {"maxStorage"}
  ID                        id-at-maxStorage }

-- OID written as MSADat2:35 and expanded with this file's objectidentifier macros.
rangeUpper ATTRIBUTE ::= {
  WITH SYNTAX               INTEGER
  SINGLE VALUE              TRUE
  LDAP-SYNTAX               integer.&id
  LDAP-NAME                 {"rangeUpper"}
  ID                        id-at-rangeUpper }

-- OID written as MSADat2:34 and expanded with this file's objectidentifier macros.
rangeLower ATTRIBUTE ::= {
  WITH SYNTAX               INTEGER
  SINGLE VALUE              TRUE
  LDAP-SYNTAX               integer.&id
  LDAP-NAME                 {"rangeLower"}
  ID                        id-at-rangeLower }

-- OID written as MSADat2:118 and expanded with this file's objectidentifier macros.
otherPager ATTRIBUTE ::= {
  WITH SYNTAX               UnboundedDirectoryString
  LDAP-SYNTAX               directoryString.&id
  LDAP-NAME                 {"otherPager"}
  ID                        id-at-otherPager }

-- OID written as MSADat4:639 and expanded with this file's objectidentifier macros.
isMemberOfPartialAttributeSet ATTRIBUTE ::= {
  WITH SYNTAX               BOOLEAN
  SINGLE VALUE              TRUE
  LDAP-SYNTAX               boolean.&id
  LDAP-NAME                 {"isMemberOfPartialAttributeSet"}
  ID                        id-at-isMemberOfPartialAttributeSet }

-- OID written as MSADat4:1224 and expanded with this file's objectidentifier macros.
parentGUID ATTRIBUTE ::= {
  WITH SYNTAX               OCTET STRING
  SINGLE VALUE              TRUE
  NO USER MODIFICATION      TRUE
  LDAP-SYNTAX               octetString.&id
  LDAP-NAME                 {"parentGUID"}
  ID                        id-at-parentGUID }

-- OID written as MSADat2:141 and expanded with this file's objectidentifier macros.
department ATTRIBUTE ::= {
  WITH SYNTAX               UnboundedDirectoryString
  SINGLE VALUE              TRUE
  LDAP-SYNTAX               directoryString.&id
  LDAP-NAME                 {"department"}
  ID                        id-at-department }

-- OID written as MSADat2:25 and expanded with this file's objectidentifier macros.
mayContain ATTRIBUTE ::= {
  WITH SYNTAX               OBJECT IDENTIFIER
  LDAP-SYNTAX               oid.&id
  LDAP-NAME                 {"mayContain"}
  ID                        id-at-mayContain }

-- OID written as MSADat4:150 and expanded with this file's objectidentifier macros.
adminCount ATTRIBUTE ::= {
  WITH SYNTAX               INTEGER
  SINGLE VALUE              TRUE
  LDAP-SYNTAX               integer.&id
  LDAP-NAME                 {"adminCount"}
  ID                        id-at-adminCount }

-- OID written as MSADat4:51 and expanded with this file's objectidentifier macros.
-- SYNTAX MSADlargeInteger expanded to 1.3.6.1.4.1.1466.115.121.1.27 through an objectidentifier macro.
lastLogoff ATTRIBUTE ::= {
  WITH SYNTAX               INTEGER
  SINGLE VALUE              TRUE
  LDAP-SYNTAX               integer.&id
  LDAP-NAME                 {"lastLogoff"}
  ID                        id-at-lastLogoff }

-- OID written as MSADat4:1409 and expanded with this file's objectidentifier macros.
masteredBy ATTRIBUTE ::= {
  WITH SYNTAX               DistinguishedName
  NO USER MODIFICATION      TRUE
  LDAP-SYNTAX               dn.&id
  LDAP-NAME                 {"masteredBy"}
  ID                        id-at-masteredBy }

-- OID written as MSADat4:35 and expanded with this file's objectidentifier macros.
employeeID ATTRIBUTE ::= {
  WITH SYNTAX               UnboundedDirectoryString
  SINGLE VALUE              TRUE
  LDAP-SYNTAX               directoryString.&id
  LDAP-NAME                 {"employeeID"}
  ID                        id-at-employeeID }

-- OID written as MSADat4:719 and expanded with this file's objectidentifier macros.
-- SYNTAX MSADlargeInteger expanded to 1.3.6.1.4.1.1466.115.121.1.27 through an objectidentifier macro.
dhcpMaxKey ATTRIBUTE ::= {
  WITH SYNTAX               INTEGER
  SINGLE VALUE              TRUE
  LDAP-SYNTAX               integer.&id
  LDAP-NAME                 {"dhcpMaxKey"}
  ID                        id-at-dhcpMaxKey }

-- OID written as MSADat4:229 and expanded with this file's objectidentifier macros.
driverName ATTRIBUTE ::= {
  WITH SYNTAX               UnboundedDirectoryString
  SINGLE VALUE              TRUE
  LDAP-SYNTAX               directoryString.&id
  LDAP-NAME                 {"driverName"}
  ID                        id-at-driverName }

-- OID written as MSADat4:1363 and expanded with this file's objectidentifier macros.
mS-SQL-Name ATTRIBUTE ::= {
  WITH SYNTAX               UnboundedDirectoryString
  SINGLE VALUE              TRUE
  LDAP-SYNTAX               directoryString.&id
  LDAP-NAME                 {"mS-SQL-Name"}
  ID                        id-at-mS-SQL-Name }

-- OID written as MSADat4:322 and expanded with this file's objectidentifier macros.
categoryId ATTRIBUTE ::= {
  WITH SYNTAX               OCTET STRING
  SINGLE VALUE              TRUE
  LDAP-SYNTAX               octetString.&id
  LDAP-NAME                 {"categoryId"}
  ID                        id-at-categoryId }

-- OID written as MSADat4:889 and expanded with this file's objectidentifier macros.
additionalTrustedServiceNames ATTRIBUTE ::= {
  WITH SYNTAX               UnboundedDirectoryString
  LDAP-SYNTAX               directoryString.&id
  LDAP-NAME                 {"additionalTrustedServiceNames"}
  ID                        id-at-additionalTrustedServiceNames }

-- OID written as MSADat4:1354 and expanded with this file's objectidentifier macros.
scopeFlags ATTRIBUTE ::= {
  WITH SYNTAX               INTEGER
  SINGLE VALUE              TRUE
  LDAP-SYNTAX               integer.&id
  LDAP-NAME                 {"scopeFlags"}
  ID                        id-at-scopeFlags }

-- OID written as MSADat4:672 and expanded with this file's objectidentifier macros.
categories ATTRIBUTE ::= {
  WITH SYNTAX               UnboundedDirectoryString
  LDAP-SYNTAX               directoryString.&id
  LDAP-NAME                 {"categories"}
  ID                        id-at-categories }

-- OID written as MSADat4:855 and expanded with this file's objectidentifier macros.
netbootNewMachineNamingPolicy ATTRIBUTE ::= {
  WITH SYNTAX               UnboundedDirectoryString
  LDAP-SYNTAX               directoryString.&id
  LDAP-NAME                 {"netbootNewMachineNamingPolicy"}
  ID                        id-at-netbootNewMachineNamingPolicy }

-- OID written as MSADat4:19 and expanded with this file's objectidentifier macros.
cOMClassID ATTRIBUTE ::= {
  WITH SYNTAX               UnboundedDirectoryString
  LDAP-SYNTAX               directoryString.&id
  LDAP-NAME                 {"cOMClassID"}
  ID                        id-at-cOMClassID }

-- OID written as MSADat2:120 and expanded with this file's objectidentifier macros.
-- SYNTAX MSADlargeInteger expanded to 1.3.6.1.4.1.1466.115.121.1.27 through an objectidentifier macro.
uSNChanged ATTRIBUTE ::= {
  WITH SYNTAX               INTEGER
  SINGLE VALUE              TRUE
  NO USER MODIFICATION      TRUE
  LDAP-SYNTAX               integer.&id
  LDAP-NAME                 {"uSNChanged"}
  ID                        id-at-uSNChanged }

-- OID written as MSADat4:2 and expanded with this file's objectidentifier macros.
objectGUID ATTRIBUTE ::= {
  WITH SYNTAX               OCTET STRING
  SINGLE VALUE              TRUE
  NO USER MODIFICATION      TRUE
  LDAP-SYNTAX               octetString.&id
  LDAP-NAME                 {"objectGUID"}
  ID                        id-at-objectGUID }

-- OID written as MSADat4:707 and expanded with this file's objectidentifier macros.
dhcpRanges ATTRIBUTE ::= {
  WITH SYNTAX               PrintableString
  LDAP-SYNTAX               printableString.&id
  LDAP-NAME                 {"dhcpRanges"}
  ID                        id-at-dhcpRanges }

-- OID written as MSADat4:1358 and expanded with this file's objectidentifier macros.
schemaInfo ATTRIBUTE ::= {
  WITH SYNTAX               OCTET STRING
  NO USER MODIFICATION      TRUE
  LDAP-SYNTAX               octetString.&id
  LDAP-NAME                 {"schemaInfo"}
  ID                        id-at-schemaInfo }

-- OID written as MSADat4:646 and expanded with this file's objectidentifier macros.
otherFacsimileTelephoneNumber ATTRIBUTE ::= {
  WITH SYNTAX               UnboundedDirectoryString
  LDAP-SYNTAX               directoryString.&id
  LDAP-NAME                 {"otherFacsimileTelephoneNumber"}
  ID                        id-at-otherFacsimileTelephoneNumber }

-- OID written as MSADat4:520 and expanded with this file's objectidentifier macros.
-- SYNTAX MSADlargeInteger expanded to 1.3.6.1.4.1.1466.115.121.1.27 through an objectidentifier macro.
machinePasswordChangeInterval ATTRIBUTE ::= {
  WITH SYNTAX               INTEGER
  SINGLE VALUE              TRUE
  LDAP-SYNTAX               integer.&id
  LDAP-NAME                 {"machinePasswordChangeInterval"}
  ID                        id-at-machinePasswordChangeInterval }

-- OID written as MSADat4:674 and expanded with this file's objectidentifier macros.
rootTrust ATTRIBUTE ::= {
  WITH SYNTAX               DistinguishedName
  LDAP-SYNTAX               dn.&id
  LDAP-NAME                 {"rootTrust"}
  ID                        id-at-rootTrust }

-- OID written as MSADat4:136 and expanded with this file's objectidentifier macros.
trustType ATTRIBUTE ::= {
  WITH SYNTAX               INTEGER
  SINGLE VALUE              TRUE
  LDAP-SYNTAX               integer.&id
  LDAP-NAME                 {"trustType"}
  ID                        id-at-trustType }

-- OID written as MSADat4:750 and expanded with this file's objectidentifier macros.
groupType ATTRIBUTE ::= {
  WITH SYNTAX               INTEGER
  SINGLE VALUE              TRUE
  LDAP-SYNTAX               integer.&id
  LDAP-NAME                 {"groupType"}
  ID                        id-at-groupType }

-- OID written as MSADat4:896 and expanded with this file's objectidentifier macros.
-- SYNTAX MSADlargeInteger expanded to 1.3.6.1.4.1.1466.115.121.1.27 through an objectidentifier macro.
uSNSource ATTRIBUTE ::= {
  WITH SYNTAX               INTEGER
  SINGLE VALUE              TRUE
  LDAP-SYNTAX               integer.&id
  LDAP-NAME                 {"uSNSource"}
  ID                        id-at-uSNSource }

-- OID written as MSADat4:919 and expanded with this file's objectidentifier macros.
mSMQQuota ATTRIBUTE ::= {
  WITH SYNTAX               INTEGER
  SINGLE VALUE              TRUE
  LDAP-SYNTAX               integer.&id
  LDAP-NAME                 {"mSMQQuota"}
  ID                        id-at-mSMQQuota }

-- OID written as MSADat4:927 and expanded with this file's objectidentifier macros.
mSMQSites ATTRIBUTE ::= {
  WITH SYNTAX               OCTET STRING
  LDAP-SYNTAX               octetString.&id
  LDAP-NAME                 {"mSMQSites"}
  ID                        id-at-mSMQSites }

-- OID written as MSADat4:910 and expanded with this file's objectidentifier macros.
fromEntry ATTRIBUTE ::= {
  WITH SYNTAX               BOOLEAN
  NO USER MODIFICATION      TRUE
  LDAP-SYNTAX               boolean.&id
  LDAP-NAME                 {"fromEntry"}
  ID                        id-at-fromEntry }

-- OID written as MSADat4:1376 and expanded with this file's objectidentifier macros.
mS-SQL-SPX ATTRIBUTE ::= {
  WITH SYNTAX               UnboundedDirectoryString
  SINGLE VALUE              TRUE
  LDAP-SYNTAX               directoryString.&id
  LDAP-NAME                 {"mS-SQL-SPX"}
  ID                        id-at-mS-SQL-SPX }

-- OID written as MSADat4:892 and expanded with this file's objectidentifier macros.
gPOptions ATTRIBUTE ::= {
  WITH SYNTAX               INTEGER
  SINGLE VALUE              TRUE
  LDAP-SYNTAX               integer.&id
  LDAP-NAME                 {"gPOptions"}
  ID                        id-at-gPOptions }

-- OID written as MSADat4:814 and expanded with this file's objectidentifier macros.
msiScript ATTRIBUTE ::= {
  WITH SYNTAX               OCTET STRING
  SINGLE VALUE              TRUE
  LDAP-SYNTAX               octetString.&id
  LDAP-NAME                 {"msiScript"}
  ID                        id-at-msiScript }

-- OID written as MSADat4:285 and expanded with this file's objectidentifier macros.
printRate ATTRIBUTE ::= {
  WITH SYNTAX               INTEGER
  SINGLE VALUE              TRUE
  LDAP-SYNTAX               integer.&id
  LDAP-NAME                 {"printRate"}
  ID                        id-at-printRate }

-- OID written as MSADat4:683 and expanded with this file's objectidentifier macros.
cRLPartitionedRevocationList ATTRIBUTE ::= {
  WITH SYNTAX               OCTET STRING
  SINGLE VALUE              TRUE
  LDAP-SYNTAX               octetString.&id
  LDAP-NAME                 {"cRLPartitionedRevocationList"}
  ID                        id-at-cRLPartitionedRevocationList }

-- OID written as MSADat4:652 and expanded with this file's objectidentifier macros.
assistant ATTRIBUTE ::= {
  WITH SYNTAX               DistinguishedName
  SINGLE VALUE              TRUE
  LDAP-SYNTAX               dn.&id
  LDAP-NAME                 {"assistant"}
  ID                        id-at-assistant }

-- OID written as MSADat4:490 and expanded with this file's objectidentifier macros.
fRSDSPoll ATTRIBUTE ::= {
  WITH SYNTAX               INTEGER
  SINGLE VALUE              TRUE
  LDAP-SYNTAX               integer.&id
  LDAP-NAME                 {"fRSDSPoll"}
  ID                        id-at-fRSDSPoll }

-- OID written as MSADat4:663 and expanded with this file's objectidentifier macros.
partialAttributeDeletionList ATTRIBUTE ::= {
  WITH SYNTAX               OCTET STRING
  SINGLE VALUE              TRUE
  NO USER MODIFICATION      TRUE
  LDAP-SYNTAX               octetString.&id
  LDAP-NAME                 {"partialAttributeDeletionList"}
  ID                        id-at-partialAttributeDeletionList }

-- OID written as MSADat4:52 and expanded with this file's objectidentifier macros.
-- SYNTAX MSADlargeInteger expanded to 1.3.6.1.4.1.1466.115.121.1.27 through an objectidentifier macro.
lastLogon ATTRIBUTE ::= {
  WITH SYNTAX               INTEGER
  SINGLE VALUE              TRUE
  LDAP-SYNTAX               integer.&id
  LDAP-NAME                 {"lastLogon"}
  ID                        id-at-lastLogon }

-- OID written as MSADat2:22 and expanded with this file's objectidentifier macros.
governsID ATTRIBUTE ::= {
  WITH SYNTAX               OBJECT IDENTIFIER
  SINGLE VALUE              TRUE
  NO USER MODIFICATION      TRUE
  LDAP-SYNTAX               oid.&id
  LDAP-NAME                 {"governsID"}
  ID                        id-at-governsID }

-- OID written as MSADat4:341 and expanded with this file's objectidentifier macros.
appliesTo ATTRIBUTE ::= {
  WITH SYNTAX               UnboundedDirectoryString
  LDAP-SYNTAX               directoryString.&id
  LDAP-NAME                 {"appliesTo"}
  ID                        id-at-appliesTo }

-- OID written as MSADat4:268 and expanded with this file's objectidentifier macros.
eFSPolicy ATTRIBUTE ::= {
  WITH SYNTAX               OCTET STRING
  LDAP-SYNTAX               octetString.&id
  LDAP-NAME                 {"eFSPolicy"}
  ID                        id-at-eFSPolicy }

-- OID written as MSADat4:155 and expanded with this file's objectidentifier macros.
uASCompat ATTRIBUTE ::= {
  WITH SYNTAX               INTEGER
  SINGLE VALUE              TRUE
  LDAP-SYNTAX               integer.&id
  LDAP-NAME                 {"uASCompat"}
  ID                        id-at-uASCompat }

-- OID written as MSADat4:538 and expanded with this file's objectidentifier macros.
prefixMap ATTRIBUTE ::= {
  WITH SYNTAX               OCTET STRING
  SINGLE VALUE              TRUE
  NO USER MODIFICATION      TRUE
  LDAP-SYNTAX               octetString.&id
  LDAP-NAME                 {"prefixMap"}
  ID                        id-at-prefixMap }

-- OID written as MSADat4:661 and expanded with this file's objectidentifier macros.
isDefunct ATTRIBUTE ::= {
  WITH SYNTAX               BOOLEAN
  SINGLE VALUE              TRUE
  LDAP-SYNTAX               boolean.&id
  LDAP-NAME                 {"isDefunct"}
  ID                        id-at-isDefunct }

-- OID written as MSADat4:708 and expanded with this file's objectidentifier macros.
dhcpSites ATTRIBUTE ::= {
  WITH SYNTAX               PrintableString
  LDAP-SYNTAX               printableString.&id
  LDAP-NAME                 {"dhcpSites"}
  ID                        id-at-dhcpSites }

-- OID written as MSADat4:888 and expanded with this file's objectidentifier macros.
iPSECNegotiationPolicyAction ATTRIBUTE ::= {
  WITH SYNTAX               UnboundedDirectoryString
  SINGLE VALUE              TRUE
  LDAP-SYNTAX               directoryString.&id
  LDAP-NAME                 {"iPSECNegotiationPolicyAction"}
  ID                        id-at-iPSECNegotiationPolicyAction }

-- OID written as MSADat4:382 and expanded with this file's objectidentifier macros.
dnsRecord ATTRIBUTE ::= {
  WITH SYNTAX               OCTET STRING
  LDAP-SYNTAX               octetString.&id
  LDAP-NAME                 {"dnsRecord"}
  ID                        id-at-dnsRecord }

-- OID written as MSADat4:21 and expanded with this file's objectidentifier macros.
cOMProgID ATTRIBUTE ::= {
  WITH SYNTAX               UnboundedDirectoryString
  LDAP-SYNTAX               directoryString.&id
  LDAP-NAME                 {"cOMProgID"}
  ID                        id-at-cOMProgID }

-- OID written as MSADat4:45 and expanded with this file's objectidentifier macros.
homeDrive ATTRIBUTE ::= {
  WITH SYNTAX               UnboundedDirectoryString
  SINGLE VALUE              TRUE
  LDAP-SYNTAX               directoryString.&id
  LDAP-NAME                 {"homeDrive"}
  ID                        id-at-homeDrive }

-- OID written as MSADat4:580 and expanded with this file's objectidentifier macros.
meetingIP ATTRIBUTE ::= {
  WITH SYNTAX               UnboundedDirectoryString
  SINGLE VALUE              TRUE
  LDAP-SYNTAX               directoryString.&id
  LDAP-NAME                 {"meetingIP"}
  ID                        id-at-meetingIP }

-- OID written as MSADat4:1321 and expanded with this file's objectidentifier macros.
-- SYNTAX MSADlargeInteger expanded to 1.3.6.1.4.1.1466.115.121.1.27 through an objectidentifier macro.
aCSNonReservedMinPolicedSize ATTRIBUTE ::= {
  WITH SYNTAX               INTEGER
  SINGLE VALUE              TRUE
  LDAP-SYNTAX               integer.&id
  LDAP-NAME                 {"aCSNonReservedMinPolicedSize"}
  ID                        id-at-aCSNonReservedMinPolicedSize }

-- OID written as MSADat4:717 and expanded with this file's objectidentifier macros.
dhcpState ATTRIBUTE ::= {
  WITH SYNTAX               PrintableString
  LDAP-SYNTAX               printableString.&id
  LDAP-NAME                 {"dhcpState"}
  ID                        id-at-dhcpState }

-- OID written as MSADat4:922 and expanded with this file's objectidentifier macros.
-- SYNTAX MSADtelex expanded to 1.3.6.1.4.1.1466.115.121.1.44 through an objectidentifier macro.
mSMQLabel ATTRIBUTE ::= {
  WITH SYNTAX               PrintableString
  SINGLE VALUE              TRUE
  LDAP-SYNTAX               printableString.&id
  LDAP-NAME                 {"mSMQLabel"}
  ID                        id-at-mSMQLabel }

-- OID written as MSADat4:74 and expanded with this file's objectidentifier macros.
-- SYNTAX MSADlargeInteger expanded to 1.3.6.1.4.1.1466.115.121.1.27 through an objectidentifier macro.
maxPwdAge ATTRIBUTE ::= {
  WITH SYNTAX               INTEGER
  SINGLE VALUE              TRUE
  LDAP-SYNTAX               integer.&id
  LDAP-NAME                 {"maxPwdAge"}
  ID                        id-at-maxPwdAge }

-- OID written as MSADat4:78 and expanded with this file's objectidentifier macros.
-- SYNTAX MSADlargeInteger expanded to 1.3.6.1.4.1.1466.115.121.1.27 through an objectidentifier macro.
minPwdAge ATTRIBUTE ::= {
  WITH SYNTAX               INTEGER
  SINGLE VALUE              TRUE
  LDAP-SYNTAX               integer.&id
  LDAP-NAME                 {"minPwdAge"}
  ID                        id-at-minPwdAge }

-- OID written as MSADat4:689 and expanded with this file's objectidentifier macros.
cRLObject ATTRIBUTE ::= {
  WITH SYNTAX               DistinguishedName
  SINGLE VALUE              TRUE
  LDAP-SYNTAX               dn.&id
  LDAP-NAME                 {"cRLObject"}
  ID                        id-at-cRLObject }

-- OID written as MSADat4:146 and expanded with this file's objectidentifier macros.
objectSid ATTRIBUTE ::= {
  WITH SYNTAX               OCTET STRING
  SINGLE VALUE              TRUE
  LDAP-SYNTAX               octetString.&id
  LDAP-NAME                 {"objectSid"}
  ID                        id-at-objectSid }

-- OID written as MSADat4:565 and expanded with this file's objectidentifier macros.
meetingID ATTRIBUTE ::= {
  WITH SYNTAX               UnboundedDirectoryString
  SINGLE VALUE              TRUE
  LDAP-SYNTAX               directoryString.&id
  LDAP-NAME                 {"meetingID"}
  ID                        id-at-meetingID }

-- OID written as MSADat4:620 and expanded with this file's objectidentifier macros.
ipsecName ATTRIBUTE ::= {
  WITH SYNTAX               UnboundedDirectoryString
  SINGLE VALUE              TRUE
  LDAP-SYNTAX               directoryString.&id
  LDAP-NAME                 {"ipsecName"}
  ID                        id-at-ipsecName }

-- OID written as MSADat2:48 and expanded with this file's objectidentifier macros.
isDeleted ATTRIBUTE ::= {
  WITH SYNTAX               BOOLEAN
  SINGLE VALUE              TRUE
  NO USER MODIFICATION      TRUE
  LDAP-SYNTAX               boolean.&id
  LDAP-NAME                 {"isDeleted"}
  ID                        id-at-isDeleted }

-- OID written as MSADat4:760 and expanded with this file's objectidentifier macros.
-- SYNTAX MSADlargeInteger expanded to 1.3.6.1.4.1.1466.115.121.1.27 through an objectidentifier macro.
aCSAggregateTokenRatePerUser ATTRIBUTE ::= {
  WITH SYNTAX               INTEGER
  SINGLE VALUE              TRUE
  LDAP-SYNTAX               integer.&id
  LDAP-NAME                 {"aCSAggregateTokenRatePerUser"}
  ID                        id-at-aCSAggregateTokenRatePerUser }

-- OID written as MSADat4:623 and expanded with this file's objectidentifier macros.
ipsecData ATTRIBUTE ::= {
  WITH SYNTAX               OCTET STRING
  SINGLE VALUE              TRUE
  LDAP-SYNTAX               octetString.&id
  LDAP-NAME                 {"ipsecData"}
  ID                        id-at-ipsecData }

-- OID written as MSADat4:668 and expanded with this file's objectidentifier macros.
domainCAs ATTRIBUTE ::= {
  WITH SYNTAX               DistinguishedName
  LDAP-SYNTAX               dn.&id
  LDAP-NAME                 {"domainCAs"}
  ID                        id-at-domainCAs }

-- OID written as MSADat4:687 and expanded with this file's objectidentifier macros.
cAConnect ATTRIBUTE ::= {
  WITH SYNTAX               UnboundedDirectoryString
  SINGLE VALUE              TRUE
  LDAP-SYNTAX               directoryString.&id
  LDAP-NAME                 {"cAConnect"}
  ID                        id-at-cAConnect }

-- OID written as MSADat4:238 and expanded with this file's objectidentifier macros.
printMaxResolutionSupported ATTRIBUTE ::= {
  WITH SYNTAX               INTEGER
  SINGLE VALUE              TRUE
  LDAP-SYNTAX               integer.&id
  LDAP-NAME                 {"printMaxResolutionSupported"}
  ID                        id-at-printMaxResolutionSupported }

-- OID written as MSADat4:700 and expanded with this file's objectidentifier macros.
-- SYNTAX MSADlargeInteger expanded to 1.3.6.1.4.1.1466.115.121.1.27 through an objectidentifier macro.
dhcpFlags ATTRIBUTE ::= {
  WITH SYNTAX               INTEGER
  SINGLE VALUE              TRUE
  LDAP-SYNTAX               integer.&id
  LDAP-NAME                 {"dhcpFlags"}
  ID                        id-at-dhcpFlags }

-- OID written as MSADat2:402 and expanded with this file's objectidentifier macros.
helpData16 ATTRIBUTE ::= {
  WITH SYNTAX               OCTET STRING
  SINGLE VALUE              TRUE
  LDAP-SYNTAX               octetString.&id
  LDAP-NAME                 {"helpData16"}
  ID                        id-at-helpData16 }

-- OID written as MSADat4:653 and expanded with this file's objectidentifier macros.
managedBy ATTRIBUTE ::= {
  WITH SYNTAX               DistinguishedName
  SINGLE VALUE              TRUE
  LDAP-SYNTAX               dn.&id
  LDAP-NAME                 {"managedBy"}
  ID                        id-at-managedBy }

-- OID written as MSADat2:9 and expanded with this file's objectidentifier macros.
helpData32 ATTRIBUTE ::= {
  WITH SYNTAX               OCTET STRING
  SINGLE VALUE              TRUE
  LDAP-SYNTAX               octetString.&id
  LDAP-NAME                 {"helpData32"}
  ID                        id-at-helpData32 }

-- OID written as MSADat4:944 and expanded with this file's objectidentifier macros.
mSMQSite2 ATTRIBUTE ::= {
  WITH SYNTAX               DistinguishedName
  SINGLE VALUE              TRUE
  LDAP-SYNTAX               dn.&id
  LDAP-NAME                 {"mSMQSite2"}
  ID                        id-at-mSMQSite2 }

-- OID written as MSADat4:943 and expanded with this file's objectidentifier macros.
mSMQSite1 ATTRIBUTE ::= {
  WITH SYNTAX               DistinguishedName
  SINGLE VALUE              TRUE
  LDAP-SYNTAX               dn.&id
  LDAP-NAME                 {"mSMQSite1"}
  ID                        id-at-mSMQSite1 }

-- OID written as MSADat4:677 and expanded with this file's objectidentifier macros.
replTopologyStayOfExecution ATTRIBUTE ::= {
  WITH SYNTAX               INTEGER
  SINGLE VALUE              TRUE
  LDAP-SYNTAX               integer.&id
  LDAP-NAME                 {"replTopologyStayOfExecution"}
  ID                        id-at-replTopologyStayOfExecution }

-- OID written as MSADat4:912 and expanded with this file's objectidentifier macros.
allowedChildClassesEffective ATTRIBUTE ::= {
  WITH SYNTAX               OBJECT IDENTIFIER
  NO USER MODIFICATION      TRUE
  LDAP-SYNTAX               oid.&id
  LDAP-NAME                 {"allowedChildClassesEffective"}
  ID                        id-at-allowedChildClassesEffective }

-- OID written as MSADat2:231 and expanded with this file's objectidentifier macros.
oMSyntax ATTRIBUTE ::= {
  WITH SYNTAX               INTEGER
  SINGLE VALUE              TRUE
  NO USER MODIFICATION      TRUE
  LDAP-SYNTAX               integer.&id
  LDAP-NAME                 {"oMSyntax"}
  ID                        id-at-oMSyntax }

-- OID written as MSADat4:231 and expanded with this file's objectidentifier macros.
priority ATTRIBUTE ::= {
  WITH SYNTAX               INTEGER
  SINGLE VALUE              TRUE
  LDAP-SYNTAX               integer.&id
  LDAP-NAME                 {"priority"}
  ID                        id-at-priority }

-- OID written as MSADat4:48 and expanded with this file's objectidentifier macros.
keywords ATTRIBUTE ::= {
  WITH SYNTAX               UnboundedDirectoryString
  LDAP-SYNTAX               directoryString.&id
  LDAP-NAME                 {"keywords"}
  ID                        id-at-keywords }

-- OID written as MSADat4:946 and expanded with this file's objectidentifier macros.
mSMQCost ATTRIBUTE ::= {
  WITH SYNTAX               INTEGER
  SINGLE VALUE              TRUE
  LDAP-SYNTAX               integer.&id
  LDAP-NAME                 {"mSMQCost"}
  ID                        id-at-mSMQCost }

-- OID written as MSADat4:821 and expanded with this file's objectidentifier macros.
siteList ATTRIBUTE ::= {
  WITH SYNTAX               DistinguishedName
  LDAP-SYNTAX               dn.&id
  LDAP-NAME                 {"siteList"}
  ID                        id-at-siteList }

-- OID written as MSADat4:145 and expanded with this file's objectidentifier macros.
revision ATTRIBUTE ::= {
  WITH SYNTAX               INTEGER
  SINGLE VALUE              TRUE
  LDAP-SYNTAX               integer.&id
  LDAP-NAME                 {"revision"}
  ID                        id-at-revision }

-- OID written as MSADat2:91 and expanded with this file's objectidentifier macros.
repsFrom ATTRIBUTE ::= {
  WITH SYNTAX               OCTET STRING
  NO USER MODIFICATION      TRUE
  LDAP-SYNTAX               octetString.&id
  LDAP-NAME                 {"repsFrom"}
  ID                        id-at-repsFrom }

-- OID written as MSADat4:645 and expanded with this file's objectidentifier macros.
userCert ATTRIBUTE ::= {
  WITH SYNTAX               OCTET STRING
  SINGLE VALUE              TRUE
  LDAP-SYNTAX               octetString.&id
  LDAP-NAME                 {"userCert"}
  ID                        id-at-userCert }

-- OID written as MSADat4:951 and expanded with this file's objectidentifier macros.
mSMQQMID ATTRIBUTE ::= {
  WITH SYNTAX               OCTET STRING
  SINGLE VALUE              TRUE
  LDAP-SYNTAX               octetString.&id
  LDAP-NAME                 {"mSMQQMID"}
  ID                        id-at-mSMQQMID }

-- OID written as MSADat4:228 and expanded with this file's objectidentifier macros.
portName ATTRIBUTE ::= {
  WITH SYNTAX               UnboundedDirectoryString
  LDAP-SYNTAX               directoryString.&id
  LDAP-NAME                 {"portName"}
  ID                        id-at-portName }

-- OID written as MSADat4:859 and expanded with this file's objectidentifier macros.
netbootLocallyInstalledOSes ATTRIBUTE ::= {
  WITH SYNTAX               UnboundedDirectoryString
  LDAP-SYNTAX               directoryString.&id
  LDAP-NAME                 {"netbootLocallyInstalledOSes"}
  ID                        id-at-netbootLocallyInstalledOSes }

-- OID written as MSADat4:261 and expanded with this file's objectidentifier macros.
division ATTRIBUTE ::= {
  WITH SYNTAX               UnboundedDirectoryString
  SINGLE VALUE              TRUE
  LDAP-SYNTAX               directoryString.&id
  LDAP-NAME                 {"division"}
  ID                        id-at-division }

-- OID written as MSADat4:902 and expanded with this file's objectidentifier macros.
aCSMaxSizeOfRSVPAccountFile ATTRIBUTE ::= {
  WITH SYNTAX               INTEGER
  SINGLE VALUE              TRUE
  LDAP-SYNTAX               integer.&id
  LDAP-NAME                 {"aCSMaxSizeOfRSVPAccountFile"}
  ID                        id-at-aCSMaxSizeOfRSVPAccountFile }

-- OID written as MSADat4:699 and expanded with this file's objectidentifier macros.
dhcpType ATTRIBUTE ::= {
  WITH SYNTAX               INTEGER
  SINGLE VALUE              TRUE
  LDAP-SYNTAX               integer.&id
  LDAP-NAME                 {"dhcpType"}
  ID                        id-at-dhcpType }

-- OID written as MSADat4:301 and expanded with this file's objectidentifier macros.
wbemPath ATTRIBUTE ::= {
  WITH SYNTAX               UnboundedDirectoryString
  LDAP-SYNTAX               directoryString.&id
  LDAP-NAME                 {"wbemPath"}
  ID                        id-at-wbemPath }

-- OID written as MSADat4:362 and expanded with this file's objectidentifier macros.
siteGUID ATTRIBUTE ::= {
  WITH SYNTAX               OCTET STRING
  SINGLE VALUE              TRUE
  LDAP-SYNTAX               octetString.&id
  LDAP-NAME                 {"siteGUID"}
  ID                        id-at-siteGUID }

-- OID written as MSADat2:26 and expanded with this file's objectidentifier macros.
rDNAttID ATTRIBUTE ::= {
  WITH SYNTAX               OBJECT IDENTIFIER
  SINGLE VALUE              TRUE
  NO USER MODIFICATION      TRUE
  LDAP-SYNTAX               oid.&id
  LDAP-NAME                 {"rDNAttID"}
  ID                        id-at-rDNAttID }

-- OID written as MSADat4:900 and expanded with this file's objectidentifier macros.
aCSRSVPAccountFilesLocation ATTRIBUTE ::= {
  WITH SYNTAX               UnboundedDirectoryString
  SINGLE VALUE              TRUE
  LDAP-SYNTAX               directoryString.&id
  LDAP-NAME                 {"aCSRSVPAccountFilesLocation"}
  ID                        id-at-aCSRSVPAccountFilesLocation }

-- OID written as MSADat4:1226 and expanded with this file's objectidentifier macros.
mSMQDependentClientServices ATTRIBUTE ::= {
  WITH SYNTAX               BOOLEAN
  SINGLE VALUE              TRUE
  LDAP-SYNTAX               boolean.&id
  LDAP-NAME                 {"mSMQDependentClientServices"}
  ID                        id-at-mSMQDependentClientServices }

-- OID written as MSADat4:222 and expanded with this file's objectidentifier macros.
location ATTRIBUTE ::= {
  WITH SYNTAX               UnboundedDirectoryString
  SINGLE VALUE              TRUE
  LDAP-SYNTAX               directoryString.&id
  LDAP-NAME                 {"location"}
  ID                        id-at-location }

-- OID written as MSADat4:874 and expanded with this file's objectidentifier macros.
fRSFlags ATTRIBUTE ::= {
  WITH SYNTAX               INTEGER
  SINGLE VALUE              TRUE
  LDAP-SYNTAX               integer.&id
  LDAP-NAME                 {"fRSFlags"}
  ID                        id-at-fRSFlags }

-- OID written as MSADat4:219 and expanded with this file's objectidentifier macros.
iconPath ATTRIBUTE ::= {
  WITH SYNTAX               UnboundedDirectoryString
  LDAP-SYNTAX               directoryString.&id
  LDAP-NAME                 {"iconPath"}
  ID                        id-at-iconPath }

-- OID written as MSADat4:688 and expanded with this file's objectidentifier macros.
cAWEBURL ATTRIBUTE ::= {
  WITH SYNTAX               UnboundedDirectoryString
  SINGLE VALUE              TRUE
  LDAP-SYNTAX               directoryString.&id
  LDAP-NAME                 {"cAWEBURL"}
  ID                        id-at-cAWEBURL }

-- OID written as MSADat4:716 and expanded with this file's objectidentifier macros.
mscopeId ATTRIBUTE ::= {
  WITH SYNTAX               PrintableString
  SINGLE VALUE              TRUE
  LDAP-SYNTAX               printableString.&id
  LDAP-NAME                 {"mscopeId"}
  ID                        id-at-mscopeId }

-- OID written as MSADat4:660 and expanded with this file's objectidentifier macros.
treeName ATTRIBUTE ::= {
  WITH SYNTAX               UnboundedDirectoryString
  SINGLE VALUE              TRUE
  NO USER MODIFICATION      TRUE
  LDAP-SYNTAX               directoryString.&id
  LDAP-NAME                 {"treeName"}
  ID                        id-at-treeName }

-- OID written as MSADat4:211 and expanded with this file's objectidentifier macros.
schedule ATTRIBUTE ::= {
  WITH SYNTAX               OCTET STRING
  SINGLE VALUE              TRUE
  LDAP-SYNTAX               octetString.&id
  LDAP-NAME                 {"schedule"}
  ID                        id-at-schedule }

-- OID written as MSADat4:557 and expanded with this file's objectidentifier macros.
parentCA ATTRIBUTE ::= {
  WITH SYNTAX               DistinguishedName
  SINGLE VALUE              TRUE
  LDAP-SYNTAX               dn.&id
  LDAP-NAME                 {"parentCA"}
  ID                        id-at-parentCA }

-- OID written as MSADat4:249 and expanded with this file's objectidentifier macros.
cOMCLSID ATTRIBUTE ::= {
  WITH SYNTAX               UnboundedDirectoryString
  SINGLE VALUE              TRUE
  LDAP-SYNTAX               directoryString.&id
  LDAP-NAME                 {"cOMCLSID"}
  ID                        id-at-cOMCLSID }

-- OID written as MSADat4:675 and expanded with this file's objectidentifier macros.
catalogs ATTRIBUTE ::= {
  WITH SYNTAX               UnboundedDirectoryString
  LDAP-SYNTAX               directoryString.&id
  LDAP-NAME                 {"catalogs"}
  ID                        id-at-catalogs }

-- OID written as MSADat2:102 and expanded with this file's objectidentifier macros.
memberOf ATTRIBUTE ::= {
  WITH SYNTAX               DistinguishedName
  NO USER MODIFICATION      TRUE
  LDAP-SYNTAX               dn.&id
  LDAP-NAME                 {"memberOf"}
  ID                        id-at-memberOf }

-- OID written as MSADat4:690 and expanded with this file's objectidentifier macros.
cAUsages ATTRIBUTE ::= {
  WITH SYNTAX               UnboundedDirectoryString
  LDAP-SYNTAX               directoryString.&id
  LDAP-NAME                 {"cAUsages"}
  ID                        id-at-cAUsages }

-- OID written as MSADat4:706 and expanded with this file's objectidentifier macros.
dhcpMask ATTRIBUTE ::= {
  WITH SYNTAX               PrintableString
  LDAP-SYNTAX               printableString.&id
  LDAP-NAME                 {"dhcpMask"}
  ID                        id-at-dhcpMask }

-- OID written as MSADat4:511 and expanded with this file's objectidentifier macros.
flatName ATTRIBUTE ::= {
  WITH SYNTAX               UnboundedDirectoryString
  SINGLE VALUE              TRUE
  LDAP-SYNTAX               directoryString.&id
  LDAP-NAME                 {"flatName"}
  ID                        id-at-flatName }

-- OID written as MSADat4:686 and expanded with this file's objectidentifier macros.
domainID ATTRIBUTE ::= {
  WITH SYNTAX               DistinguishedName
  SINGLE VALUE              TRUE
  LDAP-SYNTAX               dn.&id
  LDAP-NAME                 {"domainID"}
  ID                        id-at-domainID }

-- OID written as MSADat4:58 and expanded with this file's objectidentifier macros.
localeID ATTRIBUTE ::= {
  WITH SYNTAX               INTEGER
  LDAP-SYNTAX               integer.&id
  LDAP-NAME                 {"localeID"}
  ID                        id-at-localeID }

-- OID written as MSADat4:16 and expanded with this file's objectidentifier macros.
codePage ATTRIBUTE ::= {
  WITH SYNTAX               INTEGER
  SINGLE VALUE              TRUE
  LDAP-SYNTAX               integer.&id
  LDAP-NAME                 {"codePage"}
  ID                        id-at-codePage }

-- OID written as MSADat4:768 and expanded with this file's objectidentifier macros.
aCSEnableRSVPMessageLogging ATTRIBUTE ::= {
  WITH SYNTAX               BOOLEAN
  SINGLE VALUE              TRUE
  LDAP-SYNTAX               boolean.&id
  LDAP-NAME                 {"aCSEnableRSVPMessageLogging"}
  ID                        id-at-aCSEnableRSVPMessageLogging }

-- OID written as MSADat4:240 and expanded with this file's objectidentifier macros.
printOrientationsSupported ATTRIBUTE ::= {
  WITH SYNTAX               UnboundedDirectoryString
  LDAP-SYNTAX               directoryString.&id
  LDAP-NAME                 {"printOrientationsSupported"}
  ID                        id-at-printOrientationsSupported }

-- OID written as MSADat4:883 and expanded with this file's objectidentifier macros.
msRRASVendorAttributeEntry ATTRIBUTE ::= {
  WITH SYNTAX               UnboundedDirectoryString
  LDAP-SYNTAX               directoryString.&id
  LDAP-NAME                 {"msRRASVendorAttributeEntry"}
  ID                        id-at-msRRASVendorAttributeEntry }

-- OID written as MSADat4:1246 and expanded with this file's objectidentifier macros.
interSiteTopologyGenerator ATTRIBUTE ::= {
  WITH SYNTAX               DistinguishedName
  SINGLE VALUE              TRUE
  LDAP-SYNTAX               dn.&id
  LDAP-NAME                 {"interSiteTopologyGenerator"}
  ID                        id-at-interSiteTopologyGenerator }

-- OID written as MSADat4:307 and expanded with this file's objectidentifier macros.
options ATTRIBUTE ::= {
  WITH SYNTAX               INTEGER
  SINGLE VALUE              TRUE
  LDAP-SYNTAX               integer.&id
  LDAP-NAME                 {"options"}
  ID                        id-at-options }

-- OID written as MSADat4:28 and expanded with this file's objectidentifier macros.
dnsRoot ATTRIBUTE ::= {
  WITH SYNTAX               UnboundedDirectoryString
  LDAP-SYNTAX               directoryString.&id
  LDAP-NAME                 {"dnsRoot"}
  ID                        id-at-dnsRoot }

-- OID written as MSADat4:887 and expanded with this file's objectidentifier macros.
iPSECNegotiationPolicyType ATTRIBUTE ::= {
  WITH SYNTAX               UnboundedDirectoryString
  SINGLE VALUE              TRUE
  LDAP-SYNTAX               directoryString.&id
  LDAP-NAME                 {"iPSECNegotiationPolicyType"}
  ID                        id-at-iPSECNegotiationPolicyType }

-- OID written as MSADat4:1392 and expanded with this file's objectidentifier macros.
mS-SQL-InformationDirectory ATTRIBUTE ::= {
  WITH SYNTAX               BOOLEAN
  SINGLE VALUE              TRUE
  LDAP-SYNTAX               boolean.&id
  LDAP-NAME                 {"mS-SQL-InformationDirectory"}
  ID                        id-at-mS-SQL-InformationDirectory }

-- OID written as MSADat4:365 and expanded with this file's objectidentifier macros.
operatingSystemServicePack ATTRIBUTE ::= {
  WITH SYNTAX               UnboundedDirectoryString
  SINGLE VALUE              TRUE
  LDAP-SYNTAX               directoryString.&id
  LDAP-NAME                 {"operatingSystemServicePack"}
  ID                        id-at-operatingSystemServicePack }

-- OID written as MSADat4:88 and expanded with this file's objectidentifier macros.
nextRid ATTRIBUTE ::= {
  WITH SYNTAX               INTEGER
  SINGLE VALUE              TRUE
  LDAP-SYNTAX               integer.&id
  LDAP-NAME                 {"nextRid"}
  ID                        id-at-nextRid }

-- OID written as MSADat4:865 and expanded with this file's objectidentifier macros.
pekList ATTRIBUTE ::= {
  WITH SYNTAX               OCTET STRING
  SINGLE VALUE              TRUE
  LDAP-SYNTAX               octetString.&id
  LDAP-NAME                 {"pekList"}
  ID                        id-at-pekList }

-- OID written as MSADat2:7 and expanded with this file's objectidentifier macros.
subRefs ATTRIBUTE ::= {
  WITH SYNTAX               DistinguishedName
  NO USER MODIFICATION      TRUE
  LDAP-SYNTAX               dn.&id
  LDAP-NAME                 {"subRefs"}
  ID                        id-at-subRefs }

-- OID written as MSADat4:505 and expanded with this file's objectidentifier macros.
oMTGuid ATTRIBUTE ::= {
  WITH SYNTAX               OCTET STRING
  SINGLE VALUE              TRUE
  LDAP-SYNTAX               octetString.&id
  LDAP-NAME                 {"oMTGuid"}
  ID                        id-at-oMTGuid }

-- OID written as MSADat4:205 and expanded with this file's objectidentifier macros.
pKTGuid ATTRIBUTE ::= {
  WITH SYNTAX               OCTET STRING
  SINGLE VALUE              TRUE
  LDAP-SYNTAX               octetString.&id
  LDAP-NAME                 {"pKTGuid"}
  ID                        id-at-pKTGuid }

-- OID written as MSADat2:146 and expanded with this file's objectidentifier macros.
company ATTRIBUTE ::= {
  WITH SYNTAX               UnboundedDirectoryString
  SINGLE VALUE              TRUE
  LDAP-SYNTAX               directoryString.&id
  LDAP-NAME                 {"company"}
  ID                        id-at-company }

-- OID written as MSADat4:82 and expanded with this file's objectidentifier macros.
moniker ATTRIBUTE ::= {
  WITH SYNTAX               OCTET STRING
  LDAP-SYNTAX               octetString.&id
  LDAP-NAME                 {"moniker"}
  ID                        id-at-moniker }

-- OID written as MSADat4:156 and expanded with this file's objectidentifier macros.
comment ATTRIBUTE ::= {
  WITH SYNTAX               UnboundedDirectoryString
  SINGLE VALUE              TRUE
  LDAP-SYNTAX               directoryString.&id
  LDAP-NAME                 {"comment"}
  ID                        id-at-comment }

-- OID written as MSADat4:721 and expanded with this file's objectidentifier macros.
ipPhone ATTRIBUTE ::= {
  WITH SYNTAX               UnboundedDirectoryString
  SINGLE VALUE              TRUE
  LDAP-SYNTAX               directoryString.&id
  LDAP-NAME                 {"ipPhone"}
  ID                        id-at-ipPhone }

-- OID written as MSADat4:1361 and expanded with this file's objectidentifier macros.
mS-DS-ConsistencyChildCount ATTRIBUTE ::= {
  WITH SYNTAX               INTEGER
  SINGLE VALUE              TRUE
  LDAP-SYNTAX               integer.&id
  LDAP-NAME                 {"mS-DS-ConsistencyChildCount"}
  ID                        id-at-mS-DS-ConsistencyChildCount }

-- OID written as MSADat4:679 and expanded with this file's objectidentifier macros.
creator ATTRIBUTE ::= {
  WITH SYNTAX               UnboundedDirectoryString
  SINGLE VALUE              TRUE
  LDAP-SYNTAX               directoryString.&id
  LDAP-NAME                 {"creator"}
  ID                        id-at-creator }

-- OID written as MSADat4:137 and expanded with this file's objectidentifier macros.
uNCName ATTRIBUTE ::= {
  WITH SYNTAX               UnboundedDirectoryString
  SINGLE VALUE              TRUE
  LDAP-SYNTAX               directoryString.&id
  LDAP-NAME                 {"uNCName"}
  ID                        id-at-uNCName }

-- OID written as MSADat4:55 and expanded with this file's objectidentifier macros.
dBCSPwd ATTRIBUTE ::= {
  WITH SYNTAX               OCTET STRING
  SINGLE VALUE              TRUE
  LDAP-SYNTAX               octetString.&id
  LDAP-NAME                 {"dBCSPwd"}
  ID                        id-at-dBCSPwd }

-- OID written as MSADat4:1239 and expanded with this file's objectidentifier macros.
mSMQDependentClientService ATTRIBUTE ::= {
  WITH SYNTAX               BOOLEAN
  SINGLE VALUE              TRUE
  LDAP-SYNTAX               boolean.&id
  LDAP-NAME                 {"mSMQDependentClientService"}
  ID                        id-at-mSMQDependentClientService }

-- OID written as MSADat4:684 and expanded with this file's objectidentifier macros.
certificateAuthorityObject ATTRIBUTE ::= {
  WITH SYNTAX               DistinguishedName
  SINGLE VALUE              TRUE
  LDAP-SYNTAX               dn.&id
  LDAP-NAME                 {"certificateAuthorityObject"}
  ID                        id-at-certificateAuthorityObject }

-- OID written as MSADat4:621 and expanded with this file's objectidentifier macros.
ipsecID ATTRIBUTE ::= {
  WITH SYNTAX               UnboundedDirectoryString
  SINGLE VALUE              TRUE
  LDAP-SYNTAX               directoryString.&id
  LDAP-NAME                 {"ipsecID"}
  ID                        id-at-ipsecID }

-- OID written as MSADat4:914 and expanded with this file's objectidentifier macros.
allowedAttributesEffective ATTRIBUTE ::= {
  WITH SYNTAX               OBJECT IDENTIFIER
  NO USER MODIFICATION      TRUE
  LDAP-SYNTAX               oid.&id
  LDAP-NAME                 {"allowedAttributesEffective"}
  ID                        id-at-allowedAttributesEffective }

-- OID written as MSADat4:759 and expanded with this file's objectidentifier macros.
-- SYNTAX MSADlargeInteger expanded to 1.3.6.1.4.1.1466.115.121.1.27 through an objectidentifier macro.
aCSMaxPeakBandwidthPerFlow ATTRIBUTE ::= {
  WITH SYNTAX               INTEGER
  SINGLE VALUE              TRUE
  LDAP-SYNTAX               integer.&id
  LDAP-NAME                 {"aCSMaxPeakBandwidthPerFlow"}
  ID                        id-at-aCSMaxPeakBandwidthPerFlow }

-- initial capital of "Enabled" lowercased so the assignment is a valuereference.
-- OID written as MSADat2:557 and expanded with this file's objectidentifier macros.
enabled ATTRIBUTE ::= {
  WITH SYNTAX               BOOLEAN
  SINGLE VALUE              TRUE
  LDAP-SYNTAX               boolean.&id
  LDAP-NAME                 {"Enabled"}
  ID                        id-at-enabled }

-- OID written as MSADat2:326 and expanded with this file's objectidentifier macros.
perRecipDialogDisplayTable ATTRIBUTE ::= {
  WITH SYNTAX               OCTET STRING
  SINGLE VALUE              TRUE
  LDAP-SYNTAX               octetString.&id
  LDAP-NAME                 {"perRecipDialogDisplayTable"}
  ID                        id-at-perRecipDialogDisplayTable }

-- OID written as MSADat4:1248 and expanded with this file's objectidentifier macros.
interSiteTopologyFailover ATTRIBUTE ::= {
  WITH SYNTAX               INTEGER
  SINGLE VALUE              TRUE
  LDAP-SYNTAX               integer.&id
  LDAP-NAME                 {"interSiteTopologyFailover"}
  ID                        id-at-interSiteTopologyFailover }

-- OID written as MSADat4:895 and expanded with this file's objectidentifier macros.
transportAddressAttribute ATTRIBUTE ::= {
  WITH SYNTAX               OBJECT IDENTIFIER
  SINGLE VALUE              TRUE
  LDAP-SYNTAX               oid.&id
  LDAP-NAME                 {"transportAddressAttribute"}
  ID                        id-at-transportAddressAttribute }

-- OID written as MSADat4:852 and expanded with this file's objectidentifier macros.
netbootCurrentClientCount ATTRIBUTE ::= {
  WITH SYNTAX               INTEGER
  SINGLE VALUE              TRUE
  LDAP-SYNTAX               integer.&id
  LDAP-NAME                 {"netbootCurrentClientCount"}
  ID                        id-at-netbootCurrentClientCount }

-- OID written as MSADat4:372 and expanded with this file's objectidentifier macros.
-- SYNTAX MSADlargeInteger expanded to 1.3.6.1.4.1.1466.115.121.1.27 through an objectidentifier macro.
rIDPreviousAllocationPool ATTRIBUTE ::= {
  WITH SYNTAX               INTEGER
  SINGLE VALUE              TRUE
  NO USER MODIFICATION      TRUE
  LDAP-SYNTAX               integer.&id
  LDAP-NAME                 {"rIDPreviousAllocationPool"}
  ID                        id-at-rIDPreviousAllocationPool }

-- OID written as MSADat2:83 and expanded with this file's objectidentifier macros.
repsTo ATTRIBUTE ::= {
  WITH SYNTAX               OCTET STRING
  NO USER MODIFICATION      TRUE
  LDAP-SYNTAX               octetString.&id
  LDAP-NAME                 {"repsTo"}
  ID                        id-at-repsTo }

-- OID written as MSADat4:224 and expanded with this file's objectidentifier macros.
-- SYNTAX MSADsecDesc expanded to 1.3.6.1.4.1.1466.115.121.1.40 through an objectidentifier macro.
defaultSecurityDescriptor ATTRIBUTE ::= {
  WITH SYNTAX               OCTET STRING
  SINGLE VALUE              TRUE
  LDAP-SYNTAX               octetString.&id
  LDAP-NAME                 {"defaultSecurityDescriptor"}
  ID                        id-at-defaultSecurityDescriptor }

-- OID written as MSADat4:519 and expanded with this file's objectidentifier macros.
-- SYNTAX MSADlargeInteger expanded to 1.3.6.1.4.1.1466.115.121.1.27 through an objectidentifier macro.
lastBackupRestorationTime ATTRIBUTE ::= {
  WITH SYNTAX               INTEGER
  SINGLE VALUE              TRUE
  LDAP-SYNTAX               integer.&id
  LDAP-NAME                 {"lastBackupRestorationTime"}
  ID                        id-at-lastBackupRestorationTime }

-- OID written as MSADat4:873 and expanded with this file's objectidentifier macros.
fRSControlOutboundBacklog ATTRIBUTE ::= {
  WITH SYNTAX               UnboundedDirectoryString
  SINGLE VALUE              TRUE
  LDAP-SYNTAX               directoryString.&id
  LDAP-NAME                 {"fRSControlOutboundBacklog"}
  ID                        id-at-fRSControlOutboundBacklog }

-- OID written as MSADat4:255 and expanded with this file's objectidentifier macros.
vendor ATTRIBUTE ::= {
  WITH SYNTAX               UnboundedDirectoryString
  SINGLE VALUE              TRUE
  LDAP-SYNTAX               directoryString.&id
  LDAP-NAME                 {"vendor"}
  ID                        id-at-vendor }

-- OID written as MSADat4:891 and expanded with this file's objectidentifier macros.
gPLink ATTRIBUTE ::= {
  WITH SYNTAX               UnboundedDirectoryString
  SINGLE VALUE              TRUE
  LDAP-SYNTAX               directoryString.&id
  LDAP-NAME                 {"gPLink"}
  ID                        id-at-gPLink }

-- OID written as MSADat2:214 and expanded with this file's objectidentifier macros.
originalDisplayTableMSDOS ATTRIBUTE ::= {
  WITH SYNTAX               OCTET STRING
  SINGLE VALUE              TRUE
  LDAP-SYNTAX               octetString.&id
  LDAP-NAME                 {"originalDisplayTableMSDOS"}
  ID                        id-at-originalDisplayTableMSDOS }

-- OID written as MSADat2:50 and expanded with this file's objectidentifier macros.
linkID ATTRIBUTE ::= {
  WITH SYNTAX               INTEGER
  SINGLE VALUE              TRUE
  NO USER MODIFICATION      TRUE
  LDAP-SYNTAX               integer.&id
  LDAP-NAME                 {"linkID"}
  ID                        id-at-linkID }

-- OID written as MSADat4:1130 and expanded with this file's objectidentifier macros.
msNPSavedCallingStationID ATTRIBUTE ::= {
  WITH SYNTAX               IA5String
  LDAP-SYNTAX               ia5String.&id
  LDAP-NAME                 {"msNPSavedCallingStationID"}
  ID                        id-at-msNPSavedCallingStationID }

-- OID written as MSADat2:49 and expanded with this file's objectidentifier macros.
mAPIID ATTRIBUTE ::= {
  WITH SYNTAX               INTEGER
  SINGLE VALUE              TRUE
  NO USER MODIFICATION      TRUE
  LDAP-SYNTAX               integer.&id
  LDAP-NAME                 {"mAPIID"}
  ID                        id-at-mAPIID }

-- OID written as MSADat4:510 and expanded with this file's objectidentifier macros.
serviceBindingInformation ATTRIBUTE ::= {
  WITH SYNTAX               UnboundedDirectoryString
  LDAP-SYNTAX               directoryString.&id
  LDAP-NAME                 {"serviceBindingInformation"}
  ID                        id-at-serviceBindingInformation }

-- OID written as MSADat2:16 and expanded with this file's objectidentifier macros.
nCName ATTRIBUTE ::= {
  WITH SYNTAX               DistinguishedName
  SINGLE VALUE              TRUE
  NO USER MODIFICATION      TRUE
  LDAP-SYNTAX               dn.&id
  LDAP-NAME                 {"nCName"}
  ID                        id-at-nCName }

-- OID written as MSADat4:1303 and expanded with this file's objectidentifier macros.
tokenGroupsNoGCAcceptable ATTRIBUTE ::= {
  WITH SYNTAX               OCTET STRING
  LDAP-SYNTAX               octetString.&id
  LDAP-NAME                 {"tokenGroupsNoGCAcceptable"}
  ID                        id-at-tokenGroupsNoGCAcceptable }

-- OID written as MSADat4:1418 and expanded with this file's objectidentifier macros.
tokenGroupsGlobalAndUniversal ATTRIBUTE ::= {
  WITH SYNTAX               OCTET STRING
  LDAP-SYNTAX               octetString.&id
  LDAP-NAME                 {"tokenGroupsGlobalAndUniversal"}
  ID                        id-at-tokenGroupsGlobalAndUniversal }

-- OID written as MSADat4:1190 and expanded with this file's objectidentifier macros.
msRASSavedFramedIPAddress ATTRIBUTE ::= {
  WITH SYNTAX               INTEGER
  SINGLE VALUE              TRUE
  LDAP-SYNTAX               integer.&id
  LDAP-NAME                 {"msRASSavedFramedIPAddress"}
  ID                        id-at-msRASSavedFramedIPAddress }

-- OID written as MSADat4:766 and expanded with this file's objectidentifier macros.
-- SYNTAX MSADlargeInteger expanded to 1.3.6.1.4.1.1466.115.121.1.27 through an objectidentifier macro.
aCSAllocableRSVPBandwidth ATTRIBUTE ::= {
  WITH SYNTAX               INTEGER
  SINGLE VALUE              TRUE
  LDAP-SYNTAX               integer.&id
  LDAP-NAME                 {"aCSAllocableRSVPBandwidth"}
  ID                        id-at-aCSAllocableRSVPBandwidth }

-- OID written as MSADat4:61 and expanded with this file's objectidentifier macros.
-- SYNTAX MSADlargeInteger expanded to 1.3.6.1.4.1.1466.115.121.1.27 through an objectidentifier macro.
lockOutObservationWindow ATTRIBUTE ::= {
  WITH SYNTAX               INTEGER
  SINGLE VALUE              TRUE
  LDAP-SYNTAX               integer.&id
  LDAP-NAME                 {"lockOutObservationWindow"}
  ID                        id-at-lockOutObservationWindow }

-- OID written as MSADat4:857 and expanded with this file's objectidentifier macros.
netbootIntelliMirrorOSes ATTRIBUTE ::= {
  WITH SYNTAX               UnboundedDirectoryString
  LDAP-SYNTAX               directoryString.&id
  LDAP-NAME                 {"netbootIntelliMirrorOSes"}
  ID                        id-at-netbootIntelliMirrorOSes }

-- OID written as MSADat4:1320 and expanded with this file's objectidentifier macros.
-- SYNTAX MSADlargeInteger expanded to 1.3.6.1.4.1.1466.115.121.1.27 through an objectidentifier macro.
aCSNonReservedMaxSDUSize ATTRIBUTE ::= {
  WITH SYNTAX               INTEGER
  SINGLE VALUE              TRUE
  LDAP-SYNTAX               integer.&id
  LDAP-NAME                 {"aCSNonReservedMaxSDUSize"}
  ID                        id-at-aCSNonReservedMaxSDUSize }

-- OID written as MSADat4:265 and expanded with this file's objectidentifier macros.
notes ATTRIBUTE ::= {
  WITH SYNTAX               UnboundedDirectoryString
  SINGLE VALUE              TRUE
  LDAP-SYNTAX               directoryString.&id
  LDAP-NAME                 {"notes"}
  ID                        id-at-notes }

-- OID written as MSADat4:673 and expanded with this file's objectidentifier macros.
retiredReplDSASignatures ATTRIBUTE ::= {
  WITH SYNTAX               OCTET STRING
  SINGLE VALUE              TRUE
  NO USER MODIFICATION      TRUE
  LDAP-SYNTAX               octetString.&id
  LDAP-NAME                 {"retiredReplDSASignatures"}
  ID                        id-at-retiredReplDSASignatures }

-- OID written as MSADat4:1313 and expanded with this file's objectidentifier macros.
-- SYNTAX MSADlargeInteger expanded to 1.3.6.1.4.1.1466.115.121.1.27 through an objectidentifier macro.
aCSMaxTokenBucketPerFlow ATTRIBUTE ::= {
  WITH SYNTAX               INTEGER
  SINGLE VALUE              TRUE
  LDAP-SYNTAX               integer.&id
  LDAP-NAME                 {"aCSMaxTokenBucketPerFlow"}
  ID                        id-at-aCSMaxTokenBucketPerFlow }

-- OID written as MSADat2:324 and expanded with this file's objectidentifier macros.
addressEntryDisplayTable ATTRIBUTE ::= {
  WITH SYNTAX               OCTET STRING
  SINGLE VALUE              TRUE
  LDAP-SYNTAX               octetString.&id
  LDAP-NAME                 {"addressEntryDisplayTable"}
  ID                        id-at-addressEntryDisplayTable }

-- OID written as MSADat4:1317 and expanded with this file's objectidentifier macros.
-- SYNTAX MSADlargeInteger expanded to 1.3.6.1.4.1.1466.115.121.1.27 through an objectidentifier macro.
aCSMinimumDelayVariation ATTRIBUTE ::= {
  WITH SYNTAX               INTEGER
  SINGLE VALUE              TRUE
  LDAP-SYNTAX               integer.&id
  LDAP-NAME                 {"aCSMinimumDelayVariation"}
  ID                        id-at-aCSMinimumDelayVariation }

-- OID written as MSADat4:872 and expanded with this file's objectidentifier macros.
fRSControlInboundBacklog ATTRIBUTE ::= {
  WITH SYNTAX               UnboundedDirectoryString
  SINGLE VALUE              TRUE
  LDAP-SYNTAX               directoryString.&id
  LDAP-NAME                 {"fRSControlInboundBacklog"}
  ID                        id-at-fRSControlInboundBacklog }

-- OID written as MSADat4:38 and expanded with this file's objectidentifier macros.
flags ATTRIBUTE ::= {
  WITH SYNTAX               INTEGER
  SINGLE VALUE              TRUE
  LDAP-SYNTAX               integer.&id
  LDAP-NAME                 {"flags"}
  ID                        id-at-flags }

-- OID written as MSADat4:1399 and expanded with this file's objectidentifier macros.
mS-SQL-LastDiagnosticDate ATTRIBUTE ::= {
  WITH SYNTAX               UnboundedDirectoryString
  SINGLE VALUE              TRUE
  LDAP-SYNTAX               directoryString.&id
  LDAP-NAME                 {"mS-SQL-LastDiagnosticDate"}
  ID                        id-at-mS-SQL-LastDiagnosticDate }

-- OID written as MSADat4:1348 and expanded with this file's objectidentifier macros.
gPCMachineExtensionNames ATTRIBUTE ::= {
  WITH SYNTAX               UnboundedDirectoryString
  SINGLE VALUE              TRUE
  LDAP-SYNTAX               directoryString.&id
  LDAP-NAME                 {"gPCMachineExtensionNames"}
  ID                        id-at-gPCMachineExtensionNames }

-- OID written as MSADat4:1411 and expanded with this file's objectidentifier macros.
ms-DS-MachineAccountQuota ATTRIBUTE ::= {
  WITH SYNTAX               INTEGER
  SINGLE VALUE              TRUE
  LDAP-SYNTAX               integer.&id
  LDAP-NAME                 {"ms-DS-MachineAccountQuota"}
  ID                        id-at-ms-DS-MachineAccountQuota }

-- OID written as MSADat2:325 and expanded with this file's objectidentifier macros.
perMsgDialogDisplayTable ATTRIBUTE ::= {
  WITH SYNTAX               OCTET STRING
  SINGLE VALUE              TRUE
  LDAP-SYNTAX               octetString.&id
  LDAP-NAME                 {"perMsgDialogDisplayTable"}
  ID                        id-at-perMsgDialogDisplayTable }

-- OID written as MSADat4:57 and expanded with this file's objectidentifier macros.
defaultLocalPolicyObject ATTRIBUTE ::= {
  WITH SYNTAX               DistinguishedName
  SINGLE VALUE              TRUE
  LDAP-SYNTAX               dn.&id
  LDAP-NAME                 {"defaultLocalPolicyObject"}
  ID                        id-at-defaultLocalPolicyObject }

-- OID written as MSADat4:1189 and expanded with this file's objectidentifier macros.
msRASSavedCallbackNumber ATTRIBUTE ::= {
  WITH SYNTAX               IA5String
  SINGLE VALUE              TRUE
  LDAP-SYNTAX               ia5String.&id
  LDAP-NAME                 {"msRASSavedCallbackNumber"}
  ID                        id-at-msRASSavedCallbackNumber }

-- OID written as MSADat4:685 and expanded with this file's objectidentifier macros.
parentCACertificateChain ATTRIBUTE ::= {
  WITH SYNTAX               OCTET STRING
  SINGLE VALUE              TRUE
  LDAP-SYNTAX               octetString.&id
  LDAP-NAME                 {"parentCACertificateChain"}
  ID                        id-at-parentCACertificateChain }

-- OID written as MSADat4:893 and expanded with this file's objectidentifier macros.
gPCFunctionalityVersion ATTRIBUTE ::= {
  WITH SYNTAX               INTEGER
  SINGLE VALUE              TRUE
  LDAP-SYNTAX               integer.&id
  LDAP-NAME                 {"gPCFunctionalityVersion"}
  ID                        id-at-gPCFunctionalityVersion }

-- OID written as MSADat4:879 and expanded with this file's objectidentifier macros.
fRSServiceCommandStatus ATTRIBUTE ::= {
  WITH SYNTAX               UnboundedDirectoryString
  SINGLE VALUE              TRUE
  LDAP-SYNTAX               directoryString.&id
  LDAP-NAME                 {"fRSServiceCommandStatus"}
  ID                        id-at-fRSServiceCommandStatus }

-- OID written as MSADat4:1319 and expanded with this file's objectidentifier macros.
-- SYNTAX MSADlargeInteger expanded to 1.3.6.1.4.1.1466.115.121.1.27 through an objectidentifier macro.
aCSNonReservedTokenSize ATTRIBUTE ::= {
  WITH SYNTAX               INTEGER
  SINGLE VALUE              TRUE
  LDAP-SYNTAX               integer.&id
  LDAP-NAME                 {"aCSNonReservedTokenSize"}
  ID                        id-at-aCSNonReservedTokenSize }

-- OID written as MSADat4:775 and expanded with this file's objectidentifier macros.
aCSMaxSizeOfRSVPLogFile ATTRIBUTE ::= {
  WITH SYNTAX               INTEGER
  SINGLE VALUE              TRUE
  LDAP-SYNTAX               integer.&id
  LDAP-NAME                 {"aCSMaxSizeOfRSVPLogFile"}
  ID                        id-at-aCSMaxSizeOfRSVPLogFile }

-- OID written as MSADat2:135 and expanded with this file's objectidentifier macros.
cost ATTRIBUTE ::= {
  WITH SYNTAX               INTEGER
  SINGLE VALUE              TRUE
  LDAP-SYNTAX               integer.&id
  LDAP-NAME                 {"cost"}
  ID                        id-at-cost }

-- OID written as MSADat4:81 and expanded with this file's objectidentifier macros.
-- SYNTAX MSADlargeInteger expanded to 1.3.6.1.4.1.1466.115.121.1.27 through an objectidentifier macro.
modifiedCountAtLastProm ATTRIBUTE ::= {
  WITH SYNTAX               INTEGER
  SINGLE VALUE              TRUE
  LDAP-SYNTAX               integer.&id
  LDAP-NAME                 {"modifiedCountAtLastProm"}
  ID                        id-at-modifiedCountAtLastProm }

-- OID written as MSADat4:773 and expanded with this file's objectidentifier macros.
aCSRSVPLogFilesLocation ATTRIBUTE ::= {
  WITH SYNTAX               UnboundedDirectoryString
  SINGLE VALUE              TRUE
  LDAP-SYNTAX               directoryString.&id
  LDAP-NAME                 {"aCSRSVPLogFilesLocation"}
  ID                        id-at-aCSRSVPLogFilesLocation }

-- OID written as MSADat4:125 and expanded with this file's objectidentifier macros.
supplementalCredentials ATTRIBUTE ::= {
  WITH SYNTAX               OCTET STRING
  LDAP-SYNTAX               octetString.&id
  LDAP-NAME                 {"supplementalCredentials"}
  ID                        id-at-supplementalCredentials }

-- OID written as MSADat4:819 and expanded with this file's objectidentifier macros.
bridgeheadTransportList ATTRIBUTE ::= {
  WITH SYNTAX               DistinguishedName
  LDAP-SYNTAX               dn.&id
  LDAP-NAME                 {"bridgeheadTransportList"}
  ID                        id-at-bridgeheadTransportList }

-- OID written as MSADat4:967 and expanded with this file's objectidentifier macros.
mSMQSignCertificatesMig ATTRIBUTE ::= {
  WITH SYNTAX               OCTET STRING
  SINGLE VALUE              TRUE
  LDAP-SYNTAX               octetString.&id
  LDAP-NAME                 {"mSMQSignCertificatesMig"}
  ID                        id-at-mSMQSignCertificatesMig }

-- OID written as MSADat4:1153 and expanded with this file's objectidentifier macros.
msRADIUSFramedIPAddress ATTRIBUTE ::= {
  WITH SYNTAX               INTEGER
  SINGLE VALUE              TRUE
  LDAP-SYNTAX               integer.&id
  LDAP-NAME                 {"msRADIUSFramedIPAddress"}
  ID                        id-at-msRADIUSFramedIPAddress }

-- OID written as MSADat4:1408 and expanded with this file's objectidentifier macros.
-- SYNTAX MSADdnWithOctetString expanded to 1.3.6.1.4.1.1466.115.121.1.40 through an objectidentifier macro.
mS-DS-ReplicatesNCReason ATTRIBUTE ::= {
  WITH SYNTAX               OCTET STRING
  LDAP-SYNTAX               octetString.&id
  LDAP-NAME                 {"mS-DS-ReplicatesNCReason"}
  ID                        id-at-mS-DS-ReplicatesNCReason }

-- OID written as MSADat4:899 and expanded with this file's objectidentifier macros.
aCSEnableRSVPAccounting ATTRIBUTE ::= {
  WITH SYNTAX               BOOLEAN
  SINGLE VALUE              TRUE
  LDAP-SYNTAX               boolean.&id
  LDAP-NAME                 {"aCSEnableRSVPAccounting"}
  ID                        id-at-aCSEnableRSVPAccounting }

-- OID written as MSADat4:281 and expanded with this file's objectidentifier macros.
printStaplingSupported ATTRIBUTE ::= {
  WITH SYNTAX               BOOLEAN
  SINGLE VALUE              TRUE
  LDAP-SYNTAX               boolean.&id
  LDAP-NAME                 {"printStaplingSupported"}
  ID                        id-at-printStaplingSupported }

-- OID written as MSADat4:1247 and expanded with this file's objectidentifier macros.
interSiteTopologyRenew ATTRIBUTE ::= {
  WITH SYNTAX               INTEGER
  SINGLE VALUE              TRUE
  LDAP-SYNTAX               integer.&id
  LDAP-NAME                 {"interSiteTopologyRenew"}
  ID                        id-at-interSiteTopologyRenew }

-- OID written as MSADat4:364 and expanded with this file's objectidentifier macros.
operatingSystemVersion ATTRIBUTE ::= {
  WITH SYNTAX               UnboundedDirectoryString
  SINGLE VALUE              TRUE
  LDAP-SYNTAX               directoryString.&id
  LDAP-NAME                 {"operatingSystemVersion"}
  ID                        id-at-operatingSystemVersion }

-- OID written as MSADat4:91 and expanded with this file's objectidentifier macros.
otherLoginWorkstations ATTRIBUTE ::= {
  WITH SYNTAX               UnboundedDirectoryString
  LDAP-SYNTAX               directoryString.&id
  LDAP-NAME                 {"otherLoginWorkstations"}
  ID                        id-at-otherLoginWorkstations }

-- OID written as MSADat4:849 and expanded with this file's objectidentifier macros.
netbootAllowNewClients ATTRIBUTE ::= {
  WITH SYNTAX               BOOLEAN
  SINGLE VALUE              TRUE
  LDAP-SYNTAX               boolean.&id
  LDAP-NAME                 {"netbootAllowNewClients"}
  ID                        id-at-netbootAllowNewClients }

-- OID written as MSADat4:1372 and expanded with this file's objectidentifier macros.
mS-SQL-UnicodeSortOrder ATTRIBUTE ::= {
  WITH SYNTAX               INTEGER
  SINGLE VALUE              TRUE
  LDAP-SYNTAX               integer.&id
  LDAP-NAME                 {"mS-SQL-UnicodeSortOrder"}
  ID                        id-at-mS-SQL-UnicodeSortOrder }

-- OID written as MSADat4:749 and expanded with this file's objectidentifier macros.
url ATTRIBUTE ::= {
  WITH SYNTAX               UnboundedDirectoryString
  LDAP-SYNTAX               directoryString.&id
  LDAP-NAME                 {"url"}
  ID                        id-at-url }

-- OID written as MSADat4:206 and expanded with this file's objectidentifier macros.
pKT ATTRIBUTE ::= {
  WITH SYNTAX               OCTET STRING
  SINGLE VALUE              TRUE
  LDAP-SYNTAX               octetString.&id
  LDAP-NAME                 {"pKT"}
  ID                        id-at-pKT }

-- OID written as MSADat4:199 and expanded with this file's objectidentifier macros.
serviceInstanceVersion ATTRIBUTE ::= {
  WITH SYNTAX               OCTET STRING
  SINGLE VALUE              TRUE
  LDAP-SYNTAX               octetString.&id
  LDAP-NAME                 {"serviceInstanceVersion"}
  ID                        id-at-serviceInstanceVersion }

-- OID written as MSADat2:169 and expanded with this file's objectidentifier macros.
showInAdvancedViewOnly ATTRIBUTE ::= {
  WITH SYNTAX               BOOLEAN
  SINGLE VALUE              TRUE
  LDAP-SYNTAX               boolean.&id
  LDAP-NAME                 {"showInAdvancedViewOnly"}
  ID                        id-at-showInAdvancedViewOnly }

-- OID written as MSADat4:758 and expanded with this file's objectidentifier macros.
-- SYNTAX MSADlargeInteger expanded to 1.3.6.1.4.1.1466.115.121.1.27 through an objectidentifier macro.
aCSMaxTokenRatePerFlow ATTRIBUTE ::= {
  WITH SYNTAX               INTEGER
  SINGLE VALUE              TRUE
  LDAP-SYNTAX               integer.&id
  LDAP-NAME                 {"aCSMaxTokenRatePerFlow"}
  ID                        id-at-aCSMaxTokenRatePerFlow }

-- OID written as MSADat4:868 and expanded with this file's objectidentifier macros.
isCriticalSystemObject ATTRIBUTE ::= {
  WITH SYNTAX               BOOLEAN
  SINGLE VALUE              TRUE
  LDAP-SYNTAX               boolean.&id
  LDAP-NAME                 {"isCriticalSystemObject"}
  ID                        id-at-isCriticalSystemObject }

-- OID written as MSADat4:576 and expanded with this file's objectidentifier macros.
meetingMaxParticipants ATTRIBUTE ::= {
  WITH SYNTAX               INTEGER
  SINGLE VALUE              TRUE
  LDAP-SYNTAX               integer.&id
  LDAP-NAME                 {"meetingMaxParticipants"}
  ID                        id-at-meetingMaxParticipants }

-- OID written as MSADat4:1208 and expanded with this file's objectidentifier macros.
aNR ATTRIBUTE ::= {
  WITH SYNTAX               UnboundedDirectoryString
  SINGLE VALUE              TRUE
  LDAP-SYNTAX               directoryString.&id
  LDAP-NAME                 {"aNR"}
  ID                        id-at-aNR }

-- OID written as MSADat4:153 and expanded with this file's objectidentifier macros.
rid ATTRIBUTE ::= {
  WITH SYNTAX               INTEGER
  SINGLE VALUE              TRUE
  LDAP-SYNTAX               integer.&id
  LDAP-NAME                 {"rid"}
  ID                        id-at-rid }

-- OID written as MSADat2:523 and expanded with this file's objectidentifier macros.
proxyGenerationEnabled ATTRIBUTE ::= {
  WITH SYNTAX               BOOLEAN
  SINGLE VALUE              TRUE
  LDAP-SYNTAX               boolean.&id
  LDAP-NAME                 {"proxyGenerationEnabled"}
  ID                        id-at-proxyGenerationEnabled }

-- OID written as MSADat4:871 and expanded with this file's objectidentifier macros.
fRSControlDataCreation ATTRIBUTE ::= {
  WITH SYNTAX               UnboundedDirectoryString
  SINGLE VALUE              TRUE
  LDAP-SYNTAX               directoryString.&id
  LDAP-NAME                 {"fRSControlDataCreation"}
  ID                        id-at-fRSControlDataCreation }

-- OID written as MSADat4:692 and expanded with this file's objectidentifier macros.
previousCACertificates ATTRIBUTE ::= {
  WITH SYNTAX               OCTET STRING
  SINGLE VALUE              TRUE
  LDAP-SYNTAX               octetString.&id
  LDAP-NAME                 {"previousCACertificates"}
  ID                        id-at-previousCACertificates }

-- OID written as MSADat4:24 and expanded with this file's objectidentifier macros.
contentIndexingAllowed ATTRIBUTE ::= {
  WITH SYNTAX               BOOLEAN
  SINGLE VALUE              TRUE
  LDAP-SYNTAX               boolean.&id
  LDAP-NAME                 {"contentIndexingAllowed"}
  ID                        id-at-contentIndexingAllowed }

-- OID written as MSADat4:633 and expanded with this file's objectidentifier macros.
policyReplicationFlags ATTRIBUTE ::= {
  WITH SYNTAX               INTEGER
  SINGLE VALUE              TRUE
  LDAP-SYNTAX               integer.&id
  LDAP-NAME                 {"policyReplicationFlags"}
  ID                        id-at-policyReplicationFlags }

-- OID written as MSADat4:870 and expanded with this file's objectidentifier macros.
frsComputerReferenceBL ATTRIBUTE ::= {
  WITH SYNTAX               DistinguishedName
  NO USER MODIFICATION      TRUE
  LDAP-SYNTAX               dn.&id
  LDAP-NAME                 {"frsComputerReferenceBL"}
  ID                        id-at-frsComputerReferenceBL }

-- OID written as MSADat4:1318 and expanded with this file's objectidentifier macros.
-- SYNTAX MSADlargeInteger expanded to 1.3.6.1.4.1.1466.115.121.1.27 through an objectidentifier macro.
aCSNonReservedPeakRate ATTRIBUTE ::= {
  WITH SYNTAX               INTEGER
  SINGLE VALUE              TRUE
  LDAP-SYNTAX               integer.&id
  LDAP-NAME                 {"aCSNonReservedPeakRate"}
  ID                        id-at-aCSNonReservedPeakRate }

-- OID written as MSADat4:901 and expanded with this file's objectidentifier macros.
aCSMaxNoOfAccountFiles ATTRIBUTE ::= {
  WITH SYNTAX               INTEGER
  SINGLE VALUE              TRUE
  LDAP-SYNTAX               integer.&id
  LDAP-NAME                 {"aCSMaxNoOfAccountFiles"}
  ID                        id-at-aCSMaxNoOfAccountFiles }

-- OID written as MSADat4:514 and expanded with this file's objectidentifier macros.
physicalLocationObject ATTRIBUTE ::= {
  WITH SYNTAX               DistinguishedName
  SINGLE VALUE              TRUE
  LDAP-SYNTAX               dn.&id
  LDAP-NAME                 {"physicalLocationObject"}
  ID                        id-at-physicalLocationObject }

-- OID written as MSADat4:928 and expanded with this file's objectidentifier macros.
mSMQOutRoutingServers ATTRIBUTE ::= {
  WITH SYNTAX               DistinguishedName
  LDAP-SYNTAX               dn.&id
  LDAP-NAME                 {"mSMQOutRoutingServers"}
  ID                        id-at-mSMQOutRoutingServers }

-- OID written as MSADat4:820 and expanded with this file's objectidentifier macros.
bridgeheadServerListBL ATTRIBUTE ::= {
  WITH SYNTAX               DistinguishedName
  NO USER MODIFICATION      TRUE
  LDAP-SYNTAX               dn.&id
  LDAP-NAME                 {"bridgeheadServerListBL"}
  ID                        id-at-bridgeheadServerListBL }

-- OID written as MSADat4:1145 and expanded with this file's objectidentifier macros.
msRADIUSCallbackNumber ATTRIBUTE ::= {
  WITH SYNTAX               IA5String
  SINGLE VALUE              TRUE
  LDAP-SYNTAX               ia5String.&id
  LDAP-NAME                 {"msRADIUSCallbackNumber"}
  ID                        id-at-msRADIUSCallbackNumber }

-- OID written as MSADat4:361 and expanded with this file's objectidentifier macros.
netbootMachineFilePath ATTRIBUTE ::= {
  WITH SYNTAX               UnboundedDirectoryString
  SINGLE VALUE              TRUE
  LDAP-SYNTAX               directoryString.&id
  LDAP-NAME                 {"netbootMachineFilePath"}
  ID                        id-at-netbootMachineFilePath }

-- OID written as MSADat4:963 and expanded with this file's objectidentifier macros.
mSMQQueueJournalQuota ATTRIBUTE ::= {
  WITH SYNTAX               INTEGER
  SINGLE VALUE              TRUE
  LDAP-SYNTAX               integer.&id
  LDAP-NAME                 {"mSMQQueueJournalQuota"}
  ID                        id-at-mSMQQueueJournalQuota }

-- OID written as MSADat4:853 and expanded with this file's objectidentifier macros.
netbootAnswerRequests ATTRIBUTE ::= {
  WITH SYNTAX               BOOLEAN
  SINGLE VALUE              TRUE
  LDAP-SYNTAX               boolean.&id
  LDAP-NAME                 {"netbootAnswerRequests"}
  ID                        id-at-netbootAnswerRequests }

-- OID written as MSADat4:415 and expanded with this file's objectidentifier macros.
operatingSystemHotfix ATTRIBUTE ::= {
  WITH SYNTAX               UnboundedDirectoryString
  SINGLE VALUE              TRUE
  LDAP-SYNTAX               directoryString.&id
  LDAP-NAME                 {"operatingSystemHotfix"}
  ID                        id-at-operatingSystemHotfix }

-- OID written as MSADat4:149 and expanded with this file's objectidentifier macros.
attributeSecurityGUID ATTRIBUTE ::= {
  WITH SYNTAX               OCTET STRING
  SINGLE VALUE              TRUE
  LDAP-SYNTAX               octetString.&id
  LDAP-NAME                 {"attributeSecurityGUID"}
  ID                        id-at-attributeSecurityGUID }

-- OID written as MSADat4:711 and expanded with this file's objectidentifier macros.
superScopeDescription ATTRIBUTE ::= {
  WITH SYNTAX               UnboundedDirectoryString
  LDAP-SYNTAX               directoryString.&id
  LDAP-NAME                 {"superScopeDescription"}
  ID                        id-at-superScopeDescription }

-- OID written as MSADat4:1359 and expanded with this file's objectidentifier macros.
-- SYNTAX MSADdnWithOctetString expanded to 1.3.6.1.4.1.1466.115.121.1.40 through an objectidentifier macro.
otherWellKnownObjects ATTRIBUTE ::= {
  WITH SYNTAX               OCTET STRING
  LDAP-SYNTAX               octetString.&id
  LDAP-NAME                 {"otherWellKnownObjects"}
  ID                        id-at-otherWellKnownObjects }

-- OID written as MSADat4:780 and expanded with this file's objectidentifier macros.
-- SYNTAX MSADlargeInteger expanded to 1.3.6.1.4.1.1466.115.121.1.27 through an objectidentifier macro.
aCSNonReservedTxLimit ATTRIBUTE ::= {
  WITH SYNTAX               INTEGER
  SINGLE VALUE              TRUE
  LDAP-SYNTAX               integer.&id
  LDAP-NAME                 {"aCSNonReservedTxLimit"}
  ID                        id-at-aCSNonReservedTxLimit }

-- OID written as MSADat4:11 and expanded with this file's objectidentifier macros.
authenticationOptions ATTRIBUTE ::= {
  WITH SYNTAX               INTEGER
  SINGLE VALUE              TRUE
  LDAP-SYNTAX               integer.&id
  LDAP-NAME                 {"authenticationOptions"}
  ID                        id-at-authenticationOptions }

-- OID written as MSADat4:867 and expanded with this file's objectidentifier macros.
altSecurityIdentities ATTRIBUTE ::= {
  WITH SYNTAX               UnboundedDirectoryString
  LDAP-SYNTAX               directoryString.&id
  LDAP-NAME                 {"altSecurityIdentities"}
  ID                        id-at-altSecurityIdentities }

-- OID written as MSADat4:1349 and expanded with this file's objectidentifier macros.
gPCUserExtensionNames ATTRIBUTE ::= {
  WITH SYNTAX               UnboundedDirectoryString
  SINGLE VALUE              TRUE
  LDAP-SYNTAX               directoryString.&id
  LDAP-NAME                 {"gPCUserExtensionNames"}
  ID                        id-at-gPCUserExtensionNames }

-- OID written as MSADat4:358 and expanded with this file's objectidentifier macros.
netbootInitialization ATTRIBUTE ::= {
  WITH SYNTAX               UnboundedDirectoryString
  SINGLE VALUE              TRUE
  LDAP-SYNTAX               directoryString.&id
  LDAP-NAME                 {"netbootInitialization"}
  ID                        id-at-netbootInitialization }

-- OID written as MSADat4:1364 and expanded with this file's objectidentifier macros.
mS-SQL-RegisteredOwner ATTRIBUTE ::= {
  WITH SYNTAX               UnboundedDirectoryString
  SINGLE VALUE              TRUE
  LDAP-SYNTAX               directoryString.&id
  LDAP-NAME                 {"mS-SQL-RegisteredOwner"}
  ID                        id-at-mS-SQL-RegisteredOwner }

-- OID written as MSADat4:761 and expanded with this file's objectidentifier macros.
aCSMaxDurationPerFlow ATTRIBUTE ::= {
  WITH SYNTAX               INTEGER
  SINGLE VALUE              TRUE
  LDAP-SYNTAX               integer.&id
  LDAP-NAME                 {"aCSMaxDurationPerFlow"}
  ID                        id-at-aCSMaxDurationPerFlow }

-- OID written as MSADat4:1330 and expanded with this file's objectidentifier macros.
pKICriticalExtensions ATTRIBUTE ::= {
  WITH SYNTAX               UnboundedDirectoryString
  LDAP-SYNTAX               directoryString.&id
  LDAP-NAME                 {"pKICriticalExtensions"}
  ID                        id-at-pKICriticalExtensions }

-- OID written as MSADat4:748 and expanded with this file's objectidentifier macros.
attributeDisplayNames ATTRIBUTE ::= {
  WITH SYNTAX               UnboundedDirectoryString
  LDAP-SYNTAX               directoryString.&id
  LDAP-NAME                 {"attributeDisplayNames"}
  ID                        id-at-attributeDisplayNames }

-- OID written as MSADat4:1404 and expanded with this file's objectidentifier macros.
mS-SQL-AllowImmediateUpdatingSubscription ATTRIBUTE ::= {
  WITH SYNTAX               BOOLEAN
  SINGLE VALUE              TRUE
  LDAP-SYNTAX               boolean.&id
  LDAP-NAME                 {"mS-SQL-AllowImmediateUpdatingSubscription"}
  ID                        id-at-mS-SQL-AllowImmediateUpdatingSubscription }

-- OID written as MSADat4:1191 and expanded with this file's objectidentifier macros.
msRASSavedFramedRoute ATTRIBUTE ::= {
  WITH SYNTAX               IA5String
  LDAP-SYNTAX               ia5String.&id
  LDAP-NAME                 {"msRASSavedFramedRoute"}
  ID                        id-at-msRASSavedFramedRoute }

-- OID written as MSADat4:752 and expanded with this file's objectidentifier macros.
userSharedFolderOther ATTRIBUTE ::= {
  WITH SYNTAX               UnboundedDirectoryString
  LDAP-SYNTAX               directoryString.&id
  LDAP-NAME                 {"userSharedFolderOther"}
  ID                        id-at-userSharedFolderOther }

-- OID written as MSADat4:909 and expanded with this file's objectidentifier macros.
extendedAttributeInfo ATTRIBUTE ::= {
  WITH SYNTAX               UnboundedDirectoryString
  NO USER MODIFICATION      TRUE
  LDAP-SYNTAX               directoryString.&id
  LDAP-NAME                 {"extendedAttributeInfo"}
  ID                        id-at-extendedAttributeInfo }

-- OID written as MSADat4:1241 and expanded with this file's objectidentifier macros.
netbootMirrorDataFile ATTRIBUTE ::= {
  WITH SYNTAX               UnboundedDirectoryString
  LDAP-SYNTAX               directoryString.&id
  LDAP-NAME                 {"netbootMirrorDataFile"}
  ID                        id-at-netbootMirrorDataFile }

-- OID written as MSADat4:1315 and expanded with this file's objectidentifier macros.
-- SYNTAX MSADlargeInteger expanded to 1.3.6.1.4.1.1466.115.121.1.27 through an objectidentifier macro.
aCSMinimumPolicedSize ATTRIBUTE ::= {
  WITH SYNTAX               INTEGER
  SINGLE VALUE              TRUE
  LDAP-SYNTAX               integer.&id
  LDAP-NAME                 {"aCSMinimumPolicedSize"}
  ID                        id-at-aCSMinimumPolicedSize }

-- OID written as MSADat4:1353 and expanded with this file's objectidentifier macros.
localizationDisplayId ATTRIBUTE ::= {
  WITH SYNTAX               INTEGER
  SINGLE VALUE              TRUE
  LDAP-SYNTAX               integer.&id
  LDAP-NAME                 {"localizationDisplayId"}
  ID                        id-at-localizationDisplayId }

-- OID written as MSADat4:582 and expanded with this file's objectidentifier macros.
meetingAdvertiseScope ATTRIBUTE ::= {
  WITH SYNTAX               UnboundedDirectoryString
  SINGLE VALUE              TRUE
  LDAP-SYNTAX               directoryString.&id
  LDAP-NAME                 {"meetingAdvertiseScope"}
  ID                        id-at-meetingAdvertiseScope }

-- OID written as MSADat4:1343 and expanded with this file's objectidentifier macros.
dSUIAdminNotification ATTRIBUTE ::= {
  WITH SYNTAX               UnboundedDirectoryString
  LDAP-SYNTAX               directoryString.&id
  LDAP-NAME                 {"dSUIAdminNotification"}
  ID                        id-at-dSUIAdminNotification }

-- OID written as MSADat4:1381 and expanded with this file's objectidentifier macros.
mS-SQL-LastUpdatedDate ATTRIBUTE ::= {
  WITH SYNTAX               UnboundedDirectoryString
  SINGLE VALUE              TRUE
  LDAP-SYNTAX               directoryString.&id
  LDAP-NAME                 {"mS-SQL-LastUpdatedDate"}
  ID                        id-at-mS-SQL-LastUpdatedDate }

-- OID written as MSADat4:1357 and expanded with this file's objectidentifier macros.
dSCorePropagationData ATTRIBUTE ::= {
  WITH SYNTAX               GeneralizedTime
  NO USER MODIFICATION      TRUE
  LDAP-SYNTAX               generalizedTime.&id
  LDAP-NAME                 {"dSCorePropagationData"}
  ID                        id-at-dSCorePropagationData }

-- OID written as MSADat4:320 and expanded with this file's objectidentifier macros.
implementedCategories ATTRIBUTE ::= {
  WITH SYNTAX               OCTET STRING
  LDAP-SYNTAX               octetString.&id
  LDAP-NAME                 {"implementedCategories"}
  ID                        id-at-implementedCategories }

-- OID written as MSADat4:783 and expanded with this file's objectidentifier macros.
defaultObjectCategory ATTRIBUTE ::= {
  WITH SYNTAX               DistinguishedName
  SINGLE VALUE              TRUE
  LDAP-SYNTAX               dn.&id
  LDAP-NAME                 {"defaultObjectCategory"}
  ID                        id-at-defaultObjectCategory }

-- OID written as MSADat4:422 and expanded with this file's objectidentifier macros.
domainPolicyReference ATTRIBUTE ::= {
  WITH SYNTAX               DistinguishedName
  SINGLE VALUE              TRUE
  LDAP-SYNTAX               dn.&id
  LDAP-NAME                 {"domainPolicyReference"}
  ID                        id-at-domainPolicyReference }

-- OID written as MSADat4:929 and expanded with this file's objectidentifier macros.
mSMQInRoutingServers ATTRIBUTE ::= {
  WITH SYNTAX               DistinguishedName
  LDAP-SYNTAX               dn.&id
  LDAP-NAME                 {"mSMQInRoutingServers"}
  ID                        id-at-mSMQInRoutingServers }

-- OID written as MSADat4:1311 and expanded with this file's objectidentifier macros.
printDuplexSupported ATTRIBUTE ::= {
  WITH SYNTAX               BOOLEAN
  SINGLE VALUE              TRUE
  LDAP-SYNTAX               boolean.&id
  LDAP-NAME                 {"printDuplexSupported"}
  ID                        id-at-printDuplexSupported }

-- OID written as MSADat4:693 and expanded with this file's objectidentifier macros.
pendingCACertificates ATTRIBUTE ::= {
  WITH SYNTAX               OCTET STRING
  SINGLE VALUE              TRUE
  LDAP-SYNTAX               octetString.&id
  LDAP-NAME                 {"pendingCACertificates"}
  ID                        id-at-pendingCACertificates }

-- OID written as MSADat2:281 and expanded with this file's objectidentifier macros.
-- SYNTAX MSADsecDesc expanded to 1.3.6.1.4.1.1466.115.121.1.40 through an objectidentifier macro.
nTSecurityDescriptor ATTRIBUTE ::= {
  WITH SYNTAX               OCTET STRING
  SINGLE VALUE              TRUE
  LDAP-SYNTAX               octetString.&id
  LDAP-NAME                 {"nTSecurityDescriptor"}
  ID                        id-at-nTSecurityDescriptor }

-- OID written as MSADat4:198 and expanded with this file's objectidentifier macros.
systemAuxiliaryClass ATTRIBUTE ::= {
  WITH SYNTAX               OBJECT IDENTIFIER
  NO USER MODIFICATION      TRUE
  LDAP-SYNTAX               oid.&id
  LDAP-NAME                 {"systemAuxiliaryClass"}
  ID                        id-at-systemAuxiliaryClass }

-- OID written as MSADat4:898 and expanded with this file's objectidentifier macros.
-- SYNTAX MSADlargeInteger expanded to 1.3.6.1.4.1.1466.115.121.1.27 through an objectidentifier macro.
aCSNonReservedTxSize ATTRIBUTE ::= {
  WITH SYNTAX               INTEGER
  SINGLE VALUE              TRUE
  LDAP-SYNTAX               integer.&id
  LDAP-NAME                 {"aCSNonReservedTxSize"}
  ID                        id-at-aCSNonReservedTxSize }

-- OID written as MSADat4:1382 and expanded with this file's objectidentifier macros.
mS-SQL-InformationURL ATTRIBUTE ::= {
  WITH SYNTAX               UnboundedDirectoryString
  SINGLE VALUE              TRUE
  LDAP-SYNTAX               directoryString.&id
  LDAP-NAME                 {"mS-SQL-InformationURL"}
  ID                        id-at-mS-SQL-InformationURL }

-- OID written as MSADat4:3 and expanded with this file's objectidentifier macros.
replPropertyMetaData ATTRIBUTE ::= {
  WITH SYNTAX               OCTET STRING
  SINGLE VALUE              TRUE
  NO USER MODIFICATION      TRUE
  LDAP-SYNTAX               octetString.&id
  LDAP-NAME                 {"replPropertyMetaData"}
  ID                        id-at-replPropertyMetaData }

-- OID written as MSADat4:1384 and expanded with this file's objectidentifier macros.
mS-SQL-PublicationURL ATTRIBUTE ::= {
  WITH SYNTAX               UnboundedDirectoryString
  SINGLE VALUE              TRUE
  LDAP-SYNTAX               directoryString.&id
  LDAP-NAME                 {"mS-SQL-PublicationURL"}
  ID                        id-at-mS-SQL-PublicationURL }

-- OID written as MSADat4:275 and expanded with this file's objectidentifier macros.
printKeepPrintedJobs ATTRIBUTE ::= {
  WITH SYNTAX               BOOLEAN
  SINGLE VALUE              TRUE
  LDAP-SYNTAX               boolean.&id
  LDAP-NAME                 {"printKeepPrintedJobs"}
  ID                        id-at-printKeepPrintedJobs }

-- OID written as MSADat2:267 and expanded with this file's objectidentifier macros.
-- SYNTAX MSADlargeInteger expanded to 1.3.6.1.4.1.1466.115.121.1.27 through an objectidentifier macro.
uSNDSALastObjRemoved ATTRIBUTE ::= {
  WITH SYNTAX               INTEGER
  SINGLE VALUE              TRUE
  NO USER MODIFICATION      TRUE
  LDAP-SYNTAX               integer.&id
  LDAP-NAME                 {"uSNDSALastObjRemoved"}
  ID                        id-at-uSNDSALastObjRemoved }

-- OID written as MSADat4:381 and expanded with this file's objectidentifier macros.
dnsNotifySecondaries ATTRIBUTE ::= {
  WITH SYNTAX               INTEGER
  LDAP-SYNTAX               integer.&id
  LDAP-NAME                 {"dnsNotifySecondaries"}
  ID                        id-at-dnsNotifySecondaries }

-- OID written as MSADat4:1360 and expanded with this file's objectidentifier macros.
mS-DS-ConsistencyGuid ATTRIBUTE ::= {
  WITH SYNTAX               OCTET STRING
  SINGLE VALUE              TRUE
  LDAP-SYNTAX               octetString.&id
  LDAP-NAME                 {"mS-DS-ConsistencyGuid"}
  ID                        id-at-mS-DS-ConsistencyGuid }

-- OID written as MSADat4:869 and expanded with this file's objectidentifier macros.
frsComputerReference ATTRIBUTE ::= {
  WITH SYNTAX               DistinguishedName
  SINGLE VALUE              TRUE
  LDAP-SYNTAX               dn.&id
  LDAP-NAME                 {"frsComputerReference"}
  ID                        id-at-frsComputerReference }

-- OID written as MSADat4:1369 and expanded with this file's objectidentifier macros.
mS-SQL-ServiceAccount ATTRIBUTE ::= {
  WITH SYNTAX               UnboundedDirectoryString
  SINGLE VALUE              TRUE
  LDAP-SYNTAX               directoryString.&id
  LDAP-NAME                 {"mS-SQL-ServiceAccount"}
  ID                        id-at-mS-SQL-ServiceAccount }

-- OID written as MSADat4:1124 and expanded with this file's objectidentifier macros.
msNPCallingStationID ATTRIBUTE ::= {
  WITH SYNTAX               IA5String
  LDAP-SYNTAX               ia5String.&id
  LDAP-NAME                 {"msNPCallingStationID"}
  ID                        id-at-msNPCallingStationID }

-- OID written as MSADat4:947 and expanded with this file's objectidentifier macros.
mSMQSignCertificates ATTRIBUTE ::= {
  WITH SYNTAX               OCTET STRING
  SINGLE VALUE              TRUE
  LDAP-SYNTAX               octetString.&id
  LDAP-NAME                 {"mSMQSignCertificates"}
  ID                        id-at-mSMQSignCertificates }

-- OID written as MSADat4:624 and expanded with this file's objectidentifier macros.
ipsecOwnersReference ATTRIBUTE ::= {
  WITH SYNTAX               DistinguishedName
  LDAP-SYNTAX               dn.&id
  LDAP-NAME                 {"ipsecOwnersReference"}
  ID                        id-at-ipsecOwnersReference }

-- OID written as MSADat4:14 and expanded with this file's objectidentifier macros.
-- SYNTAX MSADlargeInteger expanded to 1.3.6.1.4.1.1466.115.121.1.27 through an objectidentifier macro.
builtinModifiedCount ATTRIBUTE ::= {
  WITH SYNTAX               INTEGER
  SINGLE VALUE              TRUE
  LDAP-SYNTAX               integer.&id
  LDAP-NAME                 {"builtinModifiedCount"}
  ID                        id-at-builtinModifiedCount }

-- OID written as MSADat4:634 and expanded with this file's objectidentifier macros.
privilegeDisplayName ATTRIBUTE ::= {
  WITH SYNTAX               UnboundedDirectoryString
  SINGLE VALUE              TRUE
  LDAP-SYNTAX               directoryString.&id
  LDAP-NAME                 {"privilegeDisplayName"}
  ID                        id-at-privilegeDisplayName }

-- OID written as MSADat4:380 and expanded with this file's objectidentifier macros.
dnsSecureSecondaries ATTRIBUTE ::= {
  WITH SYNTAX               INTEGER
  LDAP-SYNTAX               integer.&id
  LDAP-NAME                 {"dnsSecureSecondaries"}
  ID                        id-at-dnsSecureSecondaries }

-- OID written as MSADat4:817 and expanded with this file's objectidentifier macros.
localizedDescription ATTRIBUTE ::= {
  WITH SYNTAX               UnboundedDirectoryString
  LDAP-SYNTAX               directoryString.&id
  LDAP-NAME                 {"localizedDescription"}
  ID                        id-at-localizedDescription }

-- OID written as MSADat4:195 and expanded with this file's objectidentifier macros.
systemPossSuperiors ATTRIBUTE ::= {
  WITH SYNTAX               OBJECT IDENTIFIER
  NO USER MODIFICATION      TRUE
  LDAP-SYNTAX               oid.&id
  LDAP-NAME                 {"systemPossSuperiors"}
  ID                        id-at-systemPossSuperiors }

-- OID written as MSADat2:353 and expanded with this file's objectidentifier macros.
displayNamePrintable ATTRIBUTE ::= {
  WITH SYNTAX               PrintableString
  SINGLE VALUE              TRUE
  LDAP-SYNTAX               printableString.&id
  LDAP-NAME                 {"displayNamePrintable"}
  ID                        id-at-displayNamePrintable }

-- OID written as MSADat4:771 and expanded with this file's objectidentifier macros.
servicePrincipalName ATTRIBUTE ::= {
  WITH SYNTAX               UnboundedDirectoryString
  LDAP-SYNTAX               directoryString.&id
  LDAP-NAME                 {"servicePrincipalName"}
  ID                        id-at-servicePrincipalName }

-- OID written as MSADat4:866 and expanded with this file's objectidentifier macros.
-- SYNTAX MSADlargeInteger expanded to 1.3.6.1.4.1.1466.115.121.1.27 through an objectidentifier macro.
pekKeyChangeInterval ATTRIBUTE ::= {
  WITH SYNTAX               INTEGER
  SINGLE VALUE              TRUE
  LDAP-SYNTAX               integer.&id
  LDAP-NAME                 {"pekKeyChangeInterval"}
  ID                        id-at-pekKeyChangeInterval }

-- OID written as MSADat2:445 and expanded with this file's objectidentifier macros.
originalDisplayTable ATTRIBUTE ::= {
  WITH SYNTAX               OCTET STRING
  SINGLE VALUE              TRUE
  LDAP-SYNTAX               octetString.&id
  LDAP-NAME                 {"originalDisplayTable"}
  ID                        id-at-originalDisplayTable }

-- OID written as MSADat4:1398 and expanded with this file's objectidentifier macros.
mS-SQL-LastBackupDate ATTRIBUTE ::= {
  WITH SYNTAX               UnboundedDirectoryString
  SINGLE VALUE              TRUE
  LDAP-SYNTAX               directoryString.&id
  LDAP-NAME                 {"mS-SQL-LastBackupDate"}
  ID                        id-at-mS-SQL-LastBackupDate }

-- OID written as MSADat4:517 and expanded with this file's objectidentifier macros.
ipsecPolicyReference ATTRIBUTE ::= {
  WITH SYNTAX               DistinguishedName
  SINGLE VALUE              TRUE
  LDAP-SYNTAX               dn.&id
  LDAP-NAME                 {"ipsecPolicyReference"}
  ID                        id-at-ipsecPolicyReference }

-- OID written as MSADat4:823 and expanded with this file's objectidentifier macros.
certificateTemplates ATTRIBUTE ::= {
  WITH SYNTAX               UnboundedDirectoryString
  LDAP-SYNTAX               directoryString.&id
  LDAP-NAME                 {"certificateTemplates"}
  ID                        id-at-certificateTemplates }

-- OID written as MSADat2:15 and expanded with this file's objectidentifier macros.
hasPartialReplicaNCs ATTRIBUTE ::= {
  WITH SYNTAX               DistinguishedName
  NO USER MODIFICATION      TRUE
  LDAP-SYNTAX               dn.&id
  LDAP-NAME                 {"hasPartialReplicaNCs"}
  ID                        id-at-hasPartialReplicaNCs }

-- OID written as MSADat4:457 and expanded with this file's objectidentifier macros.
localPolicyReference ATTRIBUTE ::= {
  WITH SYNTAX               DistinguishedName
  SINGLE VALUE              TRUE
  LDAP-SYNTAX               dn.&id
  LDAP-NAME                 {"localPolicyReference"}
  ID                        id-at-localPolicyReference }

-- OID written as MSADat2:380 and expanded with this file's objectidentifier macros.
extendedCharsAllowed ATTRIBUTE ::= {
  WITH SYNTAX               BOOLEAN
  SINGLE VALUE              TRUE
  NO USER MODIFICATION      TRUE
  LDAP-SYNTAX               boolean.&id
  LDAP-NAME                 {"extendedCharsAllowed"}
  ID                        id-at-extendedCharsAllowed }

-- OID written as MSADat4:629 and expanded with this file's objectidentifier macros.
ipsecFilterReference ATTRIBUTE ::= {
  WITH SYNTAX               DistinguishedName
  LDAP-SYNTAX               dn.&id
  LDAP-NAME                 {"ipsecFilterReference"}
  ID                        id-at-ipsecFilterReference }

-- OID written as MSADat4:626 and expanded with this file's objectidentifier macros.
ipsecISAKMPReference ATTRIBUTE ::= {
  WITH SYNTAX               DistinguishedName
  SINGLE VALUE              TRUE
  LDAP-SYNTAX               dn.&id
  LDAP-NAME                 {"ipsecISAKMPReference"}
  ID                        id-at-ipsecISAKMPReference }

-- OID written as MSADat4:876 and expanded with this file's objectidentifier macros.
fRSMemberReferenceBL ATTRIBUTE ::= {
  WITH SYNTAX               DistinguishedName
  NO USER MODIFICATION      TRUE
  LDAP-SYNTAX               dn.&id
  LDAP-NAME                 {"fRSMemberReferenceBL"}
  ID                        id-at-fRSMemberReferenceBL }

-- OID written as MSADat4:314 and expanded with this file's objectidentifier macros.
rpcNsTransferSyntax ATTRIBUTE ::= {
  WITH SYNTAX               UnboundedDirectoryString
  SINGLE VALUE              TRUE
  LDAP-SYNTAX               directoryString.&id
  LDAP-NAME                 {"rpcNsTransferSyntax"}
  ID                        id-at-rpcNsTransferSyntax }

-- OID written as MSADat4:1227 and expanded with this file's objectidentifier macros.
mSMQRoutingServices ATTRIBUTE ::= {
  WITH SYNTAX               BOOLEAN
  SINGLE VALUE              TRUE
  LDAP-SYNTAX               boolean.&id
  LDAP-NAME                 {"mSMQRoutingServices"}
  ID                        id-at-mSMQRoutingServices }

-- OID written as MSADat4:1375 and expanded with this file's objectidentifier macros.
mS-SQL-MultiProtocol ATTRIBUTE ::= {
  WITH SYNTAX               UnboundedDirectoryString
  SINGLE VALUE              TRUE
  LDAP-SYNTAX               directoryString.&id
  LDAP-NAME                 {"mS-SQL-MultiProtocol"}
  ID                        id-at-mS-SQL-MultiProtocol }

-- OID written as MSADat4:825 and expanded with this file's objectidentifier macros.
enrollmentProviders ATTRIBUTE ::= {
  WITH SYNTAX               UnboundedDirectoryString
  SINGLE VALUE              TRUE
  LDAP-SYNTAX               directoryString.&id
  LDAP-NAME                 {"enrollmentProviders"}
  ID                        id-at-enrollmentProviders }

-- OID written as MSADat4:287 and expanded with this file's objectidentifier macros.
printNetworkAddress ATTRIBUTE ::= {
  WITH SYNTAX               UnboundedDirectoryString
  SINGLE VALUE              TRUE
  LDAP-SYNTAX               directoryString.&id
  LDAP-NAME                 {"printNetworkAddress"}
  ID                        id-at-printNetworkAddress }

-- OID written as MSADat4:1171 and expanded with this file's objectidentifier macros.
msRADIUSServiceType ATTRIBUTE ::= {
  WITH SYNTAX               INTEGER
  SINGLE VALUE              TRUE
  LDAP-SYNTAX               integer.&id
  LDAP-NAME                 {"msRADIUSServiceType"}
  ID                        id-at-msRADIUSServiceType }

-- OID written as MSADat4:631 and expanded with this file's objectidentifier macros.
printPagesPerMinute ATTRIBUTE ::= {
  WITH SYNTAX               INTEGER
  SINGLE VALUE              TRUE
  LDAP-SYNTAX               integer.&id
  LDAP-NAME                 {"printPagesPerMinute"}
  ID                        id-at-printPagesPerMinute }

-- OID written as MSADat4:299 and expanded with this file's objectidentifier macros.
printMediaSupported ATTRIBUTE ::= {
  WITH SYNTAX               UnboundedDirectoryString
  LDAP-SYNTAX               directoryString.&id
  LDAP-NAME                 {"printMediaSupported"}
  ID                        id-at-printMediaSupported }

-- OID written as MSADat4:824 and expanded with this file's objectidentifier macros.
signatureAlgorithms ATTRIBUTE ::= {
  WITH SYNTAX               UnboundedDirectoryString
  SINGLE VALUE              TRUE
  LDAP-SYNTAX               directoryString.&id
  LDAP-NAME                 {"signatureAlgorithms"}
  ID                        id-at-signatureAlgorithms }

-- OID written as MSADat4:877 and expanded with this file's objectidentifier macros.
fRSPartnerAuthLevel ATTRIBUTE ::= {
  WITH SYNTAX               INTEGER
  SINGLE VALUE              TRUE
  LDAP-SYNTAX               integer.&id
  LDAP-NAME                 {"fRSPartnerAuthLevel"}
  ID                        id-at-fRSPartnerAuthLevel }

-- OID written as MSADat4:636 and expanded with this file's objectidentifier macros.
privilegeAttributes ATTRIBUTE ::= {
  WITH SYNTAX               INTEGER
  SINGLE VALUE              TRUE
  LDAP-SYNTAX               integer.&id
  LDAP-NAME                 {"privilegeAttributes"}
  ID                        id-at-privilegeAttributes }

-- OID written as MSADat4:640 and expanded with this file's objectidentifier macros.
partialAttributeSet ATTRIBUTE ::= {
  WITH SYNTAX               OCTET STRING
  SINGLE VALUE              TRUE
  NO USER MODIFICATION      TRUE
  LDAP-SYNTAX               octetString.&id
  LDAP-NAME                 {"partialAttributeSet"}
  ID                        id-at-partialAttributeSet }

-- OID written as MSADat4:850 and expanded with this file's objectidentifier macros.
netbootLimitClients ATTRIBUTE ::= {
  WITH SYNTAX               BOOLEAN
  SINGLE VALUE              TRUE
  LDAP-SYNTAX               boolean.&id
  LDAP-NAME                 {"netbootLimitClients"}
  ID                        id-at-netbootLimitClients }

-- OID written as MSADat4:1383 and expanded with this file's objectidentifier macros.
mS-SQL-ConnectionURL ATTRIBUTE ::= {
  WITH SYNTAX               UnboundedDirectoryString
  SINGLE VALUE              TRUE
  LDAP-SYNTAX               directoryString.&id
  LDAP-NAME                 {"mS-SQL-ConnectionURL"}
  ID                        id-at-mS-SQL-ConnectionURL }

-- OID written as MSADat4:1406 and expanded with this file's objectidentifier macros.
mS-SQL-AllowSnapshotFilesFTPDownloading ATTRIBUTE ::= {
  WITH SYNTAX               BOOLEAN
  SINGLE VALUE              TRUE
  LDAP-SYNTAX               boolean.&id
  LDAP-NAME                 {"mS-SQL-AllowSnapshotFilesFTPDownloading"}
  ID                        id-at-mS-SQL-AllowSnapshotFilesFTPDownloading }

-- OID written as MSADat4:1331 and expanded with this file's objectidentifier macros.
pKIExpirationPeriod ATTRIBUTE ::= {
  WITH SYNTAX               OCTET STRING
  SINGLE VALUE              TRUE
  LDAP-SYNTAX               octetString.&id
  LDAP-NAME                 {"pKIExpirationPeriod"}
  ID                        id-at-pKIExpirationPeriod }

-- OID written as MSADat4:531 and expanded with this file's objectidentifier macros.
nonSecurityMemberBL ATTRIBUTE ::= {
  WITH SYNTAX               DistinguishedName
  NO USER MODIFICATION      TRUE
  LDAP-SYNTAX               dn.&id
  LDAP-NAME                 {"nonSecurityMemberBL"}
  ID                        id-at-nonSecurityMemberBL }

-- OID written as MSADat4:540 and expanded with this file's objectidentifier macros.
initialAuthOutgoing ATTRIBUTE ::= {
  WITH SYNTAX               UnboundedDirectoryString
  SINGLE VALUE              TRUE
  LDAP-SYNTAX               directoryString.&id
  LDAP-NAME                 {"initialAuthOutgoing"}
  ID                        id-at-initialAuthOutgoing }

-- OID written as MSADat4:1158 and expanded with this file's objectidentifier macros.
msRADIUSFramedRoute ATTRIBUTE ::= {
  WITH SYNTAX               IA5String
  LDAP-SYNTAX               ia5String.&id
  LDAP-NAME                 {"msRADIUSFramedRoute"}
  ID                        id-at-msRADIUSFramedRoute }

-- OID written as MSADat4:200 and expanded with this file's objectidentifier macros.
controlAccessRights ATTRIBUTE ::= {
  WITH SYNTAX               OCTET STRING
  LDAP-SYNTAX               octetString.&id
  LDAP-NAME                 {"controlAccessRights"}
  ID                        id-at-controlAccessRights }

-- Object classes

-- OID written as MSADoc5:0 and expanded with this file's objectidentifier macros.
mstop OBJECT-CLASS ::= {
  SUBCLASS OF               { top }
  KIND                      abstract
  MUST CONTAIN              { objectClass
                              | instanceType
                              | nTSecurityDescriptor
                              | objectCategory }
  MAY CONTAIN               { commonName
                              | description
                              | distinguishedName
                              | whenCreated
                              | whenChanged
                              | subRefs
                              | displayName
                              | uSNCreated
                              | isDeleted
                              | dSASignature
                              | objectVersion
                              | repsTo
                              | repsFrom
                              | memberOf
                              | ownerBL
                              | uSNChanged
                              | uSNLastObjRem
                              | showInAdvancedViewOnly
                              | adminDisplayName
                              | proxyAddresses
                              | adminDescription
                              | extensionName
                              | uSNDSALastObjRemoved
                              | displayNamePrintable
                              | directReports
                              | wWWHomePage
                              | uSNIntersite
                              | name
                              | objectGUID
                              | replPropertyMetaData
                              | replUpToDateVector
                              | flags
                              | revision
                              | wbemPath
                              | fSMORoleOwner
                              | systemFlags
                              | siteObjectBL
                              | serverReferenceBL
                              | nonSecurityMemberBL
                              | queryPolicyBL
                              | wellKnownObjects
                              | isPrivilegeHolder
                              | partialAttributeSet
                              | managedObjects
                              | partialAttributeDeletionList
                              | url
                              | lastKnownParent
                              | bridgeheadServerListBL
                              | netbootSCPBL
                              | isCriticalSystemObject
                              | frsComputerReferenceBL
                              | fRSMemberReferenceBL
                              | uSNSource
                              | fromEntry
                              | allowedChildClasses
                              | allowedChildClassesEffective
                              | allowedAttributes
                              | allowedAttributesEffective
                              | possibleInferiors
                              | canonicalName
                              | proxiedObjectName
                              | sDRightsEffective
                              | dSCorePropagationData
                              | otherWellKnownObjects
                              | mS-DS-ConsistencyGuid
                              | mS-DS-ConsistencyChildCount
                              | masteredBy
                              | msCOM-PartitionSetLink
                              | msCOM-UserLink
                              | msDS-Approx-Immed-Subordinates
                              | msDS-NCReplCursors
                              | msDS-NCReplInboundNeighbors
                              | msDS-NCReplOutboundNeighbors
                              | msDS-ReplAttributeMetaData
                              | msDS-ReplValueMetaData
                              | msDS-NonMembersBL
                              | msDS-MembersForAzRoleBL
                              | msDS-OperationsForAzTaskBL
                              | msDS-TasksForAzTaskBL
                              | msDS-OperationsForAzRoleBL
                              | msDS-TasksForAzRoleBL
                              | msDs-masteredBy
                              | msDS-ObjectReferenceBL
                              | msDS-PrincipalName
                              | msDS-RevealedDSAs
                              | msDS-KrbTgtLinkBl
                              | msDS-IsFullReplicaFor
                              | msDS-IsDomainFor
                              | msDS-IsPartialReplicaFor
                              | msDS-AuthenticatedToAccountlist
                              | msDS-NC-RO-Replica-Locations-BL
                              | msDS-RevealedListBL
                              | msDS-PSOApplied
                              | msDS-NcType
                              | msDS-OIDToGroupLinkBl
                              | msDS-HostServiceAccountBL
                              | isRecycled
                              | msDS-LocalEffectiveDeletionTime
                              | msDS-LocalEffectiveRecycleTime
                              | msDS-LastKnownRDN
                              | msDS-EnabledFeatureBL
                              | msDS-ClaimSharesPossibleValuesWithBL
                              | msDS-MembersOfResourcePropertyListBL
                              | msDS-IsPrimaryComputerFor
                              | msDS-ValueTypeReferenceBL
                              | msDS-TDOIngressBL
                              | msDS-TDOEgressBL
                              | msDS-parentdistname
                              | msDS-ReplValueMetaDataExt
                              | msds-memberOfTransitive
                              | msds-memberTransitive
                              | msSFU30PosixMemberOf
                              | msDFSR-MemberReferenceBL
                              | msDFSR-ComputerReferenceBL }
  LDAP-NAME                 {"mstop"}
  ID                        id-oc-mstop }

-- OID written as MSADoc5:8 and expanded with this file's objectidentifier macros.
group OBJECT-CLASS ::= {
  SUBCLASS OF               { mstop }
  MUST CONTAIN              { groupType }
  MAY CONTAIN               { member
                              | nTGroupMembers
                              | operatorCount
                              | adminCount
                              | groupAttributes
                              | groupMembershipSAM
                              | controlAccessRights
                              | desktopProfile
                              | nonSecurityMember
                              | managedBy
                              | primaryGroupToken
                              | msDS-AzLDAPQuery
                              | msDS-NonMembers
                              | msDS-AzBizRule
                              | msDS-AzBizRuleLanguage
                              | msDS-AzLastImportedBizRulePath
                              | msDS-AzApplicationData
                              | msDS-AzObjectGuid
                              | msDS-AzGenericData
                              | msDS-PrimaryComputer
                              | mail
                              | msSFU30Name
                              | msSFU30NisDomain
                              | msSFU30PosixMember }
  LDAP-NAME                 {"group"}
  ID                        id-oc-group }

-- OID written as MSADoc5:9 and expanded with this file's objectidentifier macros.
user OBJECT-CLASS ::= {
  SUBCLASS OF               { mstop
                              | organizationalPerson }
  MAY CONTAIN               { organizationName
                              | businessCategory
                              | userCertificate
                              | givenName
                              | initials
                              | uniqueIdentifier
                              | displayName
                              | networkAddress
                              | employeeNumber
                              | employeeType
                              | homePostalAddress
                              | userAccountControl
                              | badPwdCount
                              | codePage
                              | homeDirectory
                              | homeDrive
                              | badPasswordTime
                              | lastLogoff
                              | lastLogon
                              | dBCSPwd
                              | localeID
                              | scriptPath
                              | logonHours
                              | logonWorkstation
                              | maxStorage
                              | userWorkstations
                              | unicodePwd
                              | otherLoginWorkstations
                              | ntPwdHistory
                              | pwdLastSet
                              | preferredOU
                              | primaryGroupID
                              | userParameters
                              | profilePath
                              | operatorCount
                              | adminCount
                              | accountExpires
                              | lmPwdHistory
                              | groupMembershipSAM
                              | logonCount
                              | controlAccessRights
                              | defaultClassStore
                              | groupsToIgnore
                              | groupPriority
                              | desktopProfile
                              | dynamicLDAPServer
                              | userPrincipalName
                              | lockoutTime
                              | userSharedFolder
                              | userSharedFolderOther
                              | servicePrincipalName
                              | aCSPolicyName
                              | terminalServer
                              | mSMQSignCertificates
                              | mSMQDigests
                              | mSMQDigestsMig
                              | mSMQSignCertificatesMig
                              | msNPAllowDialin
                              | msNPCallingStationID
                              | msNPSavedCallingStationID
                              | msRADIUSCallbackNumber
                              | msRADIUSFramedIPAddress
                              | msRADIUSFramedRoute
                              | msRADIUSServiceType
                              | msRASSavedCallbackNumber
                              | msRASSavedFramedIPAddress
                              | msRASSavedFramedRoute
                              | mS-DS-CreatorSID
                              | msCOM-UserPartitionSetLink
                              | msDS-Cached-Membership
                              | msDS-Cached-Membership-Time-Stamp
                              | msDS-Site-Affinity
                              | msDS-User-Account-Control-Computed
                              | lastLogonTimestamp
                              | msIIS-FTPRoot
                              | msIIS-FTPDir
                              | msDRM-IdentityCertificate
                              | msDS-SourceObjectDN
                              | msPKIRoamingTimeStamp
                              | msPKIDPAPIMasterKeys
                              | msPKIAccountCredentials
                              | msRADIUS-FramedInterfaceId
                              | msRADIUS-SavedFramedInterfaceId
                              | msRADIUS-FramedIpv6Prefix
                              | msRADIUS-SavedFramedIpv6Prefix
                              | msRADIUS-FramedIpv6Route
                              | msRADIUS-SavedFramedIpv6Route
                              | msDS-SecondaryKrbTgtNumber
                              | msDS-AuthenticatedAtDC
                              | msDS-SupportedEncryptionTypes
                              | msDS-LastSuccessfulInteractiveLogonTime
                              | msDS-LastFailedInteractiveLogonTime
                              | msDS-FailedInteractiveLogonCount
                              | msDS-FailedInteractiveLogonCountAtLastSuccessfulLogon
                              | msTSProfilePath
                              | msTSHomeDirectory
                              | msTSHomeDrive
                              | msTSAllowLogon
                              | msTSRemoteControl
                              | msTSMaxDisconnectionTime
                              | msTSMaxConnectionTime
                              | msTSMaxIdleTime
                              | msTSReconnectionAction
                              | msTSBrokenConnectionAction
                              | msTSConnectClientDrives
                              | msTSConnectPrinterDrives
                              | msTSDefaultToMainPrinter
                              | msTSWorkDirectory
                              | msTSInitialProgram
                              | msTSProperty01
                              | msTSProperty02
                              | msTSExpireDate
                              | msTSLicenseVersion
                              | msTSManagingLS
                              | msDS-UserPasswordExpiryTimeComputed
                              | msTSExpireDate2
                              | msTSLicenseVersion2
                              | msTSManagingLS2
                              | msTSExpireDate3
                              | msTSLicenseVersion3
                              | msTSManagingLS3
                              | msTSExpireDate4
                              | msTSLicenseVersion4
                              | msTSManagingLS4
                              | msTSLSProperty01
                              | msTSLSProperty02
                              | msDS-ResultantPSO
                              | msPKI-CredentialRoamingTokens
                              | msTSPrimaryDesktop
                              | msTSSecondaryDesktops
                              | msDS-PrimaryComputer
                              | msDS-SyncServerUrl
                              | msDS-AssignedAuthNPolicySilo
                              | msDS-AuthNPolicySiloMembersBL
                              | msDS-AssignedAuthNPolicy
                              | userSMIMECertificate
                              | uid
                              | mail
                              | roomNumber
                              | photo
                              | manager
                              | homePhone
                              | secretary
                              | mobile
                              | pager
                              | audio
                              | jpegPhoto
                              | carLicense
                              | departmentNumber
                              | preferredLanguage
                              | userPKCS12
                              | labeledURI
                              | msSFU30Name
                              | msSFU30NisDomain }
  LDAP-NAME                 {"user"}
  ID                        id-oc-user }

computer OBJECT-CLASS ::= {
  SUBCLASS OF               { user }
  MAY CONTAIN               { commonName
                              | networkAddress
                              | localPolicyFlags
                              | defaultLocalPolicyObject
                              | machineRole
                              | location
                              | netbootInitialization
                              | netbootGUID
                              | netbootMachineFilePath
                              | siteGUID
                              | operatingSystem
                              | operatingSystemVersion
                              | operatingSystemServicePack
                              | operatingSystemHotfix
                              | volumeCount
                              | physicalLocationObject
                              | dNSHostName
                              | policyReplicationFlags
                              | managedBy
                              | rIDSetReferences
                              | catalogs
                              | netbootSIFFile
                              | netbootMirrorDataFile
                              | msDS-AdditionalDnsHostName
                              | msDS-AdditionalSamAccountName
                              | msDS-ExecuteScriptPassword
                              | msDS-KrbTgtLink
                              | msDS-RevealedUsers
                              | msDS-NeverRevealGroup
                              | msDS-RevealOnDemandGroup
                              | msDS-RevealedList
                              | msDS-AuthenticatedAtDC
                              | msDS-isGC
                              | msDS-isRODC
                              | msDS-SiteName
                              | msDS-PromotionSettings
                              | msTPM-OwnerInformation
                              | msTSProperty01
                              | msTSProperty02
                              | msDS-IsUserCachableAtRodc
                              | msDS-HostServiceAccount
                              | msTSEndpointData
                              | msTSEndpointType
                              | msTSEndpointPlugin
                              | msTSPrimaryDesktopBL
                              | msTSSecondaryDesktopBL
                              | msTPM-TpmInformationForComputer
                              | msDS-GenerationId
                              | msImaging-ThumbprintHash
                              | msImaging-HashAlgorithm
                              | netbootDUID
                              | msSFU30Name
                              | msSFU30Aliases
                              | msSFU30NisDomain
                              | nisMapName }
  LDAP-NAME                 {"computer"}
  ID                        id-oc-computer }

END
