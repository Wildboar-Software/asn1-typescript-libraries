-- Derived from data/ldap-schema/ldaptor.schema
-- This module is a container for LDAP schema. It has no module identifier.
-- X- extension fields from the LDAP schema are comments. USAGE userApplications and structural KIND are omitted because they are the defaults.
Ldaptor DEFINITIONS ::=
BEGIN

IMPORTS

  ATTRIBUTE, OBJECT-CLASS, top
    FROM InformationFramework
      {joint-iso-itu-t ds(5) module(1) informationFramework(1) 9} WITH SUCCESSORS

  commonName, generalizedTime, generalizedTimeMatch,
    generalizedTimeOrderingMatch, owner
    FROM SelectedAttributeTypes
      {joint-iso-itu-t ds(5) module(1) selectedAttributeTypes(5) 9} WITH SUCCESSORS

  userPassword
    FROM AuthenticationFramework
      {joint-iso-itu-t ds(5) module(1) authenticationFramework(7) 9} WITH SUCCESSORS ;

-- Object identifiers

id-at-validFrom OBJECT IDENTIFIER ::= { 1 3 6 1 4 1 22024 1 1 1 1 }
id-at-validUntil OBJECT IDENTIFIER ::= { 1 3 6 1 4 1 22024 1 1 1 2 }
id-oc-serviceSecurityObject OBJECT IDENTIFIER ::= { 1 3 6 1 4 1 22024 1 1 2 1 }

-- Attribute types

validFrom ATTRIBUTE ::= {
  WITH SYNTAX               GeneralizedTime
  EQUALITY MATCHING RULE    generalizedTimeMatch
  ORDERING MATCHING RULE    generalizedTimeOrderingMatch
  SINGLE VALUE              TRUE
  LDAP-SYNTAX               generalizedTime.&id
  LDAP-NAME                 {"validFrom"}
  LDAP-DESC                 "Authentication is possible only after this time"
  ID                        id-at-validFrom }

validUntil ATTRIBUTE ::= {
  WITH SYNTAX               GeneralizedTime
  EQUALITY MATCHING RULE    generalizedTimeMatch
  ORDERING MATCHING RULE    generalizedTimeOrderingMatch
  SINGLE VALUE              TRUE
  LDAP-SYNTAX               generalizedTime.&id
  LDAP-NAME                 {"validUntil"}
  LDAP-DESC                 "Authentication is possible only before this time"
  ID                        id-at-validUntil }

-- Object classes

serviceSecurityObject OBJECT-CLASS ::= {
  SUBCLASS OF               { top }
  MUST CONTAIN              { commonName
                              | owner
                              | userPassword }
  MAY CONTAIN               { validFrom
                              | validUntil }
  LDAP-NAME                 {"serviceSecurityObject"}
  LDAP-DESC                 "A service-specific authentication method"
  ID                        id-oc-serviceSecurityObject }
END
