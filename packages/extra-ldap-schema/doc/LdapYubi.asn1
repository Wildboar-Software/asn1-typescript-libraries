-- Derived from data/ldap-schema/yubi.schema
-- This module is a container for LDAP schema. It has no module identifier.
-- X- extension fields from the LDAP schema are comments. USAGE userApplications and structural KIND are omitted because they are the defaults.
-- LDAP {length} bounds on directory strings are DirectoryString{n}. Bounds on IA5String, PrintableString, NumericString, and OCTET STRING are SIZE (1..n). Other bounds stay comments because the LDAP figure is an encoded-length hint.
LdapYubi DEFINITIONS ::=
BEGIN

IMPORTS

  ATTRIBUTE, OBJECT-CLASS, top
    FROM InformationFramework
      {joint-iso-itu-t ds(5) module(1) informationFramework(1) 9} WITH SUCCESSORS

  caseIgnoreMatch, caseIgnoreSubstringsMatch, octetString, octetStringMatch,
    printableString
    FROM SelectedAttributeTypes
      {joint-iso-itu-t ds(5) module(1) selectedAttributeTypes(5) 9} WITH SUCCESSORS ;

-- Object identifiers

id-at-yubikeyID OBJECT IDENTIFIER ::= { 1 3 6 1 4 1 31622 999 1 1 }
id-at-passwordFactor OBJECT IDENTIFIER ::= { 1 3 6 1 4 1 31622 999 1 2 }
id-oc-yubikeyOwner OBJECT IDENTIFIER ::= { 1 3 6 1 4 1 31622 999 2 1 }

-- Attribute types

yubikeyID ATTRIBUTE ::= {
  WITH SYNTAX               PrintableString(SIZE (1..12))
  EQUALITY MATCHING RULE    caseIgnoreMatch
  SUBSTRINGS MATCHING RULE  caseIgnoreSubstringsMatch
  LDAP-SYNTAX               printableString.&id
  LDAP-NAME                 {"yubikeyID"}
  LDAP-DESC                 "Yubikey identifier"
  ID                        id-at-yubikeyID }

passwordFactor ATTRIBUTE ::= {
  WITH SYNTAX               OCTET STRING (SIZE (1..128))
  EQUALITY MATCHING RULE    octetStringMatch
  LDAP-SYNTAX               octetString.&id
  LDAP-NAME                 {"passwordFactor"}
  LDAP-DESC                 "password of user"
  ID                        id-at-passwordFactor }

-- Object classes

yubikeyOwner OBJECT-CLASS ::= {
  SUBCLASS OF               { top }
  KIND                      auxiliary
  MUST CONTAIN              { yubikeyID
                              | passwordFactor }
  LDAP-NAME                 {"yubikeyOwner"}
  LDAP-DESC                 "Object that has a Yubikey"
  ID                        id-oc-yubikeyOwner }
END
