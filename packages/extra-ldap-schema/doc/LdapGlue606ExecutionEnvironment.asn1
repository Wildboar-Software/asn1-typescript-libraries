-- Derived from data/ldap-schema/glue/6-06-ExecutionEnvironment.schema
-- Upstream: http://redmine.ogf.org/projects/glue-wg
-- This module is a container for LDAP schema. It has no module identifier.
-- X- extension fields from the LDAP schema are comments. USAGE userApplications and structural KIND are omitted because they are the defaults.
LdapGlue606ExecutionEnvironment DEFINITIONS ::=
BEGIN

IMPORTS

  ATTRIBUTE, OBJECT-CLASS
    FROM InformationFramework
      {joint-iso-itu-t ds(5) module(1) informationFramework(1) 9} WITH SUCCESSORS

  caseExactMatch, caseExactSubstringsMatch, directoryString, integer,
    integerMatch, integerOrderingMatch, UnboundedDirectoryString
    FROM SelectedAttributeTypes
      {joint-iso-itu-t ds(5) module(1) selectedAttributeTypes(5) 9} WITH SUCCESSORS

  gLUE2Resource
    FROM LdapGlue510Resource ;

-- Object identifiers

id-at-gLUE2ExecutionEnvironmentPlatform OBJECT IDENTIFIER ::= { 1 3 6 1 4 1 6757 100 1 1 22 1 }
id-at-gLUE2ExecutionEnvironmentVirtualMachine OBJECT IDENTIFIER ::= { 1 3 6 1 4 1 6757 100 1 1 22 2 }
id-at-gLUE2ExecutionEnvironmentTotalInstances OBJECT IDENTIFIER ::= { 1 3 6 1 4 1 6757 100 1 1 22 3 }
id-at-gLUE2ExecutionEnvironmentUsedInstances OBJECT IDENTIFIER ::= { 1 3 6 1 4 1 6757 100 1 1 22 4 }
id-at-gLUE2ExecutionEnvironmentUnavailableInstances OBJECT IDENTIFIER ::= { 1 3 6 1 4 1 6757 100 1 1 22 5 }
id-at-gLUE2ExecutionEnvironmentPhysicalCPUs OBJECT IDENTIFIER ::= { 1 3 6 1 4 1 6757 100 1 1 22 6 }
id-at-gLUE2ExecutionEnvironmentLogicalCPUs OBJECT IDENTIFIER ::= { 1 3 6 1 4 1 6757 100 1 1 22 7 }
id-at-gLUE2ExecutionEnvironmentCPUMultiplicity OBJECT IDENTIFIER ::= { 1 3 6 1 4 1 6757 100 1 1 22 8 }
id-at-gLUE2ExecutionEnvironmentCPUVendor OBJECT IDENTIFIER ::= { 1 3 6 1 4 1 6757 100 1 1 22 9 }
id-at-gLUE2ExecutionEnvironmentCPUModel OBJECT IDENTIFIER ::= { 1 3 6 1 4 1 6757 100 1 1 22 10 }
id-at-gLUE2ExecutionEnvironmentCPUVersion OBJECT IDENTIFIER ::= { 1 3 6 1 4 1 6757 100 1 1 22 11 }
id-at-gLUE2ExecutionEnvironmentCPUClockSpeed OBJECT IDENTIFIER ::= { 1 3 6 1 4 1 6757 100 1 1 22 12 }
id-at-gLUE2ExecutionEnvironmentCPUTimeScalingFactor OBJECT IDENTIFIER ::= { 1 3 6 1 4 1 6757 100 1 1 22 13 }
id-at-gLUE2ExecutionEnvironmentWallTimeScalingFactor OBJECT IDENTIFIER ::= { 1 3 6 1 4 1 6757 100 1 1 22 14 }
id-at-gLUE2ExecutionEnvironmentMainMemorySize OBJECT IDENTIFIER ::= { 1 3 6 1 4 1 6757 100 1 1 22 15 }
id-at-gLUE2ExecutionEnvironmentVirtualMemorySize OBJECT IDENTIFIER ::= { 1 3 6 1 4 1 6757 100 1 1 22 16 }
id-at-gLUE2ExecutionEnvironmentOSFamily OBJECT IDENTIFIER ::= { 1 3 6 1 4 1 6757 100 1 1 22 17 }
id-at-gLUE2ExecutionEnvironmentOSName OBJECT IDENTIFIER ::= { 1 3 6 1 4 1 6757 100 1 1 22 18 }
id-at-gLUE2ExecutionEnvironmentOSVersion OBJECT IDENTIFIER ::= { 1 3 6 1 4 1 6757 100 1 1 22 19 }
id-at-gLUE2ExecutionEnvironmentConnectivityIn OBJECT IDENTIFIER ::= { 1 3 6 1 4 1 6757 100 1 1 22 20 }
id-at-gLUE2ExecutionEnvironmentConnectivityOut OBJECT IDENTIFIER ::= { 1 3 6 1 4 1 6757 100 1 1 22 21 }
id-at-gLUE2ExecutionEnvironmentNetworkInfo OBJECT IDENTIFIER ::= { 1 3 6 1 4 1 6757 100 1 1 22 22 }
id-at-gLUE2ExecutionEnvironmentComputingManagerForeignKey OBJECT IDENTIFIER ::= { 1 3 6 1 4 1 6757 100 1 1 22 23 }
id-oc-gLUE2ExecutionEnvironment OBJECT IDENTIFIER ::= { 1 3 6 1 4 1 6757 100 1 1 22 }

-- Attribute types

-- initial capital of "GLUE2ExecutionEnvironmentPlatform" lowercased so the assignment is a valuereference.
gLUE2ExecutionEnvironmentPlatform ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2ExecutionEnvironmentPlatform"}
  LDAP-DESC                 "The architecture platform of this execution environment"
  ID                        id-at-gLUE2ExecutionEnvironmentPlatform }

-- initial capital of "GLUE2ExecutionEnvironmentVirtualMachine" lowercased so the assignment is a valuereference.
gLUE2ExecutionEnvironmentVirtualMachine ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2ExecutionEnvironmentVirtualMachine"}
  LDAP-DESC                 "True if the execution environment is based on a virtual machine (in this case, the values of the other attributes are related to the virtualized environment and not to the hosting environment)"
  ID                        id-at-gLUE2ExecutionEnvironmentVirtualMachine }

-- initial capital of "GLUE2ExecutionEnvironmentTotalInstances" lowercased so the assignment is a valuereference.
gLUE2ExecutionEnvironmentTotalInstances ATTRIBUTE ::= {
  WITH SYNTAX               INTEGER
  EQUALITY MATCHING RULE    integerMatch
  ORDERING MATCHING RULE    integerOrderingMatch
  SINGLE VALUE              TRUE
  LDAP-SYNTAX               integer.&id
  LDAP-NAME                 {"GLUE2ExecutionEnvironmentTotalInstances"}
  LDAP-DESC                 "Number of execution environment instances"
  ID                        id-at-gLUE2ExecutionEnvironmentTotalInstances }

-- initial capital of "GLUE2ExecutionEnvironmentUsedInstances" lowercased so the assignment is a valuereference.
gLUE2ExecutionEnvironmentUsedInstances ATTRIBUTE ::= {
  WITH SYNTAX               INTEGER
  EQUALITY MATCHING RULE    integerMatch
  ORDERING MATCHING RULE    integerOrderingMatch
  SINGLE VALUE              TRUE
  LDAP-SYNTAX               integer.&id
  LDAP-NAME                 {"GLUE2ExecutionEnvironmentUsedInstances"}
  LDAP-DESC                 "Number of used execution environment instances; an instance is used when, according to the policies of the Manager (i.e., LRMS), it cannot accept new jobs because it already runs the maximum number of allowed jobs"
  ID                        id-at-gLUE2ExecutionEnvironmentUsedInstances }

-- initial capital of "GLUE2ExecutionEnvironmentUnavailableInstances" lowercased so the assignment is a valuereference.
gLUE2ExecutionEnvironmentUnavailableInstances ATTRIBUTE ::= {
  WITH SYNTAX               INTEGER
  EQUALITY MATCHING RULE    integerMatch
  ORDERING MATCHING RULE    integerOrderingMatch
  SINGLE VALUE              TRUE
  LDAP-SYNTAX               integer.&id
  LDAP-NAME                 {"GLUE2ExecutionEnvironmentUnavailableInstances"}
  LDAP-DESC                 "Number of unavailable execution environment instances because of failures or maintenance"
  ID                        id-at-gLUE2ExecutionEnvironmentUnavailableInstances }

-- initial capital of "GLUE2ExecutionEnvironmentPhysicalCPUs" lowercased so the assignment is a valuereference.
gLUE2ExecutionEnvironmentPhysicalCPUs ATTRIBUTE ::= {
  WITH SYNTAX               INTEGER
  EQUALITY MATCHING RULE    integerMatch
  ORDERING MATCHING RULE    integerOrderingMatch
  SINGLE VALUE              TRUE
  LDAP-SYNTAX               integer.&id
  LDAP-NAME                 {"GLUE2ExecutionEnvironmentPhysicalCPUs"}
  LDAP-DESC                 "Number of physical CPUs in an execution environment instance"
  ID                        id-at-gLUE2ExecutionEnvironmentPhysicalCPUs }

-- initial capital of "GLUE2ExecutionEnvironmentLogicalCPUs" lowercased so the assignment is a valuereference.
gLUE2ExecutionEnvironmentLogicalCPUs ATTRIBUTE ::= {
  WITH SYNTAX               INTEGER
  EQUALITY MATCHING RULE    integerMatch
  ORDERING MATCHING RULE    integerOrderingMatch
  SINGLE VALUE              TRUE
  LDAP-SYNTAX               integer.&id
  LDAP-NAME                 {"GLUE2ExecutionEnvironmentLogicalCPUs"}
  LDAP-DESC                 "Number of logical CPUs in an execution environment instance"
  ID                        id-at-gLUE2ExecutionEnvironmentLogicalCPUs }

-- initial capital of "GLUE2ExecutionEnvironmentCPUMultiplicity" lowercased so the assignment is a valuereference.
gLUE2ExecutionEnvironmentCPUMultiplicity ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2ExecutionEnvironmentCPUMultiplicity"}
  LDAP-DESC                 "Information about the multiplicity of both physical CPUs and cores available in an execution environment instance"
  ID                        id-at-gLUE2ExecutionEnvironmentCPUMultiplicity }

-- initial capital of "GLUE2ExecutionEnvironmentCPUVendor" lowercased so the assignment is a valuereference.
gLUE2ExecutionEnvironmentCPUVendor ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2ExecutionEnvironmentCPUVendor"}
  LDAP-DESC                 "Name of the physical CPU vendor"
  ID                        id-at-gLUE2ExecutionEnvironmentCPUVendor }

-- initial capital of "GLUE2ExecutionEnvironmentCPUModel" lowercased so the assignment is a valuereference.
gLUE2ExecutionEnvironmentCPUModel ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2ExecutionEnvironmentCPUModel"}
  LDAP-DESC                 "Physical CPU model as defined by the vendor"
  ID                        id-at-gLUE2ExecutionEnvironmentCPUModel }

-- initial capital of "GLUE2ExecutionEnvironmentCPUVersion" lowercased so the assignment is a valuereference.
gLUE2ExecutionEnvironmentCPUVersion ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2ExecutionEnvironmentCPUVersion"}
  LDAP-DESC                 "Physical CPU version as defined by the vendor"
  ID                        id-at-gLUE2ExecutionEnvironmentCPUVersion }

-- initial capital of "GLUE2ExecutionEnvironmentCPUClockSpeed" lowercased so the assignment is a valuereference.
gLUE2ExecutionEnvironmentCPUClockSpeed ATTRIBUTE ::= {
  WITH SYNTAX               INTEGER
  EQUALITY MATCHING RULE    integerMatch
  ORDERING MATCHING RULE    integerOrderingMatch
  SINGLE VALUE              TRUE
  LDAP-SYNTAX               integer.&id
  LDAP-NAME                 {"GLUE2ExecutionEnvironmentCPUClockSpeed"}
  LDAP-DESC                 "Nominal clock speed of the physical CPU"
  ID                        id-at-gLUE2ExecutionEnvironmentCPUClockSpeed }

-- initial capital of "GLUE2ExecutionEnvironmentCPUTimeScalingFactor" lowercased so the assignment is a valuereference.
gLUE2ExecutionEnvironmentCPUTimeScalingFactor ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2ExecutionEnvironmentCPUTimeScalingFactor"}
  LDAP-DESC                 "Factor used by the Manager (i.e., LRMS) to scale the CPU time (CPU Time divided by CPUTimeScalingFactor); for the reference execution environment, this attribute is equal to 1"
  ID                        id-at-gLUE2ExecutionEnvironmentCPUTimeScalingFactor }

-- initial capital of "GLUE2ExecutionEnvironmentWallTimeScalingFactor" lowercased so the assignment is a valuereference.
gLUE2ExecutionEnvironmentWallTimeScalingFactor ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2ExecutionEnvironmentWallTimeScalingFactor"}
  LDAP-DESC                 "Factor used by the Manager (i.e., LRMS) to scale the Wall time (Wall Time divided by WallTimeScalingFactor)"
  ID                        id-at-gLUE2ExecutionEnvironmentWallTimeScalingFactor }

-- initial capital of "GLUE2ExecutionEnvironmentMainMemorySize" lowercased so the assignment is a valuereference.
gLUE2ExecutionEnvironmentMainMemorySize ATTRIBUTE ::= {
  WITH SYNTAX               INTEGER
  EQUALITY MATCHING RULE    integerMatch
  ORDERING MATCHING RULE    integerOrderingMatch
  SINGLE VALUE              TRUE
  LDAP-SYNTAX               integer.&id
  LDAP-NAME                 {"GLUE2ExecutionEnvironmentMainMemorySize"}
  LDAP-DESC                 "Amount of RAM (if many jobs run in the same execution environment, they compete for the total RAM)"
  ID                        id-at-gLUE2ExecutionEnvironmentMainMemorySize }

-- initial capital of "GLUE2ExecutionEnvironmentVirtualMemorySize" lowercased so the assignment is a valuereference.
gLUE2ExecutionEnvironmentVirtualMemorySize ATTRIBUTE ::= {
  WITH SYNTAX               INTEGER
  EQUALITY MATCHING RULE    integerMatch
  ORDERING MATCHING RULE    integerOrderingMatch
  SINGLE VALUE              TRUE
  LDAP-SYNTAX               integer.&id
  LDAP-NAME                 {"GLUE2ExecutionEnvironmentVirtualMemorySize"}
  LDAP-DESC                 "The amount of Virtual Memory (RAM+Swap)"
  ID                        id-at-gLUE2ExecutionEnvironmentVirtualMemorySize }

-- initial capital of "GLUE2ExecutionEnvironmentOSFamily" lowercased so the assignment is a valuereference.
gLUE2ExecutionEnvironmentOSFamily ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2ExecutionEnvironmentOSFamily"}
  LDAP-DESC                 "Family of the operating system"
  ID                        id-at-gLUE2ExecutionEnvironmentOSFamily }

-- initial capital of "GLUE2ExecutionEnvironmentOSName" lowercased so the assignment is a valuereference.
gLUE2ExecutionEnvironmentOSName ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2ExecutionEnvironmentOSName"}
  LDAP-DESC                 "Name of the operating system"
  ID                        id-at-gLUE2ExecutionEnvironmentOSName }

-- initial capital of "GLUE2ExecutionEnvironmentOSVersion" lowercased so the assignment is a valuereference.
gLUE2ExecutionEnvironmentOSVersion ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2ExecutionEnvironmentOSVersion"}
  LDAP-DESC                 "Version of the operating system"
  ID                        id-at-gLUE2ExecutionEnvironmentOSVersion }

-- initial capital of "GLUE2ExecutionEnvironmentConnectivityIn" lowercased so the assignment is a valuereference.
gLUE2ExecutionEnvironmentConnectivityIn ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2ExecutionEnvironmentConnectivityIn"}
  LDAP-DESC                 "Permission for direct inbound connectivity, even if limited"
  ID                        id-at-gLUE2ExecutionEnvironmentConnectivityIn }

-- initial capital of "GLUE2ExecutionEnvironmentConnectivityOut" lowercased so the assignment is a valuereference.
gLUE2ExecutionEnvironmentConnectivityOut ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2ExecutionEnvironmentConnectivityOut"}
  LDAP-DESC                 "Permission for direct outbound connectivity, even if limited"
  ID                        id-at-gLUE2ExecutionEnvironmentConnectivityOut }

-- initial capital of "GLUE2ExecutionEnvironmentNetworkInfo" lowercased so the assignment is a valuereference.
gLUE2ExecutionEnvironmentNetworkInfo ATTRIBUTE ::= {
  WITH SYNTAX               UnboundedDirectoryString
  EQUALITY MATCHING RULE    caseExactMatch
  SUBSTRINGS MATCHING RULE  caseExactSubstringsMatch
  LDAP-SYNTAX               directoryString.&id
  LDAP-NAME                 {"GLUE2ExecutionEnvironmentNetworkInfo"}
  LDAP-DESC                 "Type of internal network available among the execution environment instances"
  ID                        id-at-gLUE2ExecutionEnvironmentNetworkInfo }

-- initial capital of "GLUE2ExecutionEnvironmentComputingManagerForeignKey" lowercased so the assignment is a valuereference.
gLUE2ExecutionEnvironmentComputingManagerForeignKey ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2ExecutionEnvironmentComputingManagerForeignKey"}
  LDAP-DESC                 "ForeignKey"
  ID                        id-at-gLUE2ExecutionEnvironmentComputingManagerForeignKey }

-- Object classes

-- initial capital of "GLUE2ExecutionEnvironment" lowercased so the assignment is a valuereference.
gLUE2ExecutionEnvironment OBJECT-CLASS ::= {
  SUBCLASS OF               { gLUE2Resource }
  MUST CONTAIN              { gLUE2ExecutionEnvironmentPlatform
                              | gLUE2ExecutionEnvironmentMainMemorySize
                              | gLUE2ExecutionEnvironmentOSFamily
                              | gLUE2ExecutionEnvironmentConnectivityIn
                              | gLUE2ExecutionEnvironmentConnectivityOut }
  MAY CONTAIN               { gLUE2ExecutionEnvironmentVirtualMachine
                              | gLUE2ExecutionEnvironmentTotalInstances
                              | gLUE2ExecutionEnvironmentUsedInstances
                              | gLUE2ExecutionEnvironmentUnavailableInstances
                              | gLUE2ExecutionEnvironmentPhysicalCPUs
                              | gLUE2ExecutionEnvironmentLogicalCPUs
                              | gLUE2ExecutionEnvironmentCPUMultiplicity
                              | gLUE2ExecutionEnvironmentCPUVendor
                              | gLUE2ExecutionEnvironmentCPUModel
                              | gLUE2ExecutionEnvironmentCPUVersion
                              | gLUE2ExecutionEnvironmentCPUClockSpeed
                              | gLUE2ExecutionEnvironmentCPUTimeScalingFactor
                              | gLUE2ExecutionEnvironmentWallTimeScalingFactor
                              | gLUE2ExecutionEnvironmentVirtualMemorySize
                              | gLUE2ExecutionEnvironmentOSName
                              | gLUE2ExecutionEnvironmentOSVersion
                              | gLUE2ExecutionEnvironmentNetworkInfo
                              | gLUE2ExecutionEnvironmentComputingManagerForeignKey }
  LDAP-NAME                 {"GLUE2ExecutionEnvironment"}
  LDAP-DESC                 "A description of hardware, operating system and network characteristics that defines the environment available to and requestable by a Grid job when submitted to a Service via a Endpoint; the description also includes information about the total/available/used instances of the execution environment"
  ID                        id-oc-gLUE2ExecutionEnvironment }
END
