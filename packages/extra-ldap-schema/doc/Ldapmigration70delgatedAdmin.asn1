-- Derived from data/ldap-schema/ldapmigration/70delgated-admin.ldif
-- This module is a container for LDAP schema. It has no module identifier.
-- X- extension fields from the LDAP schema are comments. USAGE userApplications and structural KIND are omitted because they are the defaults.
-- 2 elements were omitted because another source file in this corpus defines the same OID.
-- 27 elements were omitted because the OID is invalid or unresolved.
Ldapmigration70delgatedAdmin DEFINITIONS ::=
BEGIN

IMPORTS

  ATTRIBUTE
    FROM InformationFramework
      {joint-iso-itu-t ds(5) module(1) informationFramework(1) 9} WITH SUCCESSORS

  directoryString, UnboundedDirectoryString
    FROM SelectedAttributeTypes
      {joint-iso-itu-t ds(5) module(1) selectedAttributeTypes(5) 9} WITH SUCCESSORS ;

-- Object identifiers

id-at-inetgroupstatus OBJECT IDENTIFIER ::= { 1 3 6 1 4 1 42 2 27 9 1 588 }

-- Attribute types

-- X-ORIGIN: "Sun Java System Identity Management", "user defined"
inetgroupstatus ATTRIBUTE ::= {
  WITH SYNTAX               UnboundedDirectoryString
  SINGLE VALUE              TRUE
  LDAP-SYNTAX               directoryString.&id
  LDAP-NAME                 {"inetgroupstatus"}
  LDAP-DESC                 "Attribute defining the status of a group"
  ID                        id-at-inetgroupstatus }
END
