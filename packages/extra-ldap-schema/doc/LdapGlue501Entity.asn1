-- Derived from data/ldap-schema/glue/5-01-Entity.schema
-- Upstream: http://redmine.ogf.org/projects/glue-wg
-- This module is a container for LDAP schema. It has no module identifier.
-- X- extension fields from the LDAP schema are comments. USAGE userApplications and structural KIND are omitted because they are the defaults.
-- Object classes with no SUP were subclassed from top, the LDAP default (RFC 4512).
LdapGlue501Entity DEFINITIONS ::=
BEGIN

IMPORTS

  ATTRIBUTE, OBJECT-CLASS, top
    FROM InformationFramework
      {joint-iso-itu-t ds(5) module(1) informationFramework(1) 9} WITH SUCCESSORS

  caseExactMatch, caseExactSubstringsMatch, directoryString,
    UnboundedDirectoryString
    FROM SelectedAttributeTypes
      {joint-iso-itu-t ds(5) module(1) selectedAttributeTypes(5) 9} WITH SUCCESSORS ;

-- Object identifiers

id-at-gLUE2EntityName OBJECT IDENTIFIER ::= { 1 3 6 1 4 1 6757 100 1 1 1 2 }
id-at-gLUE2EntityOtherInfo OBJECT IDENTIFIER ::= { 1 3 6 1 4 1 6757 100 1 1 1 3 }
id-at-gLUE2EntityCreationTime OBJECT IDENTIFIER ::= { 1 3 6 1 4 1 6757 100 1 1 1 4 }
id-at-gLUE2EntityValidity OBJECT IDENTIFIER ::= { 1 3 6 1 4 1 6757 100 1 1 1 5 }
id-oc-gLUE2Entity OBJECT IDENTIFIER ::= { 1 3 6 1 4 1 6757 100 1 1 1 }

-- Attribute types

-- initial capital of "GLUE2EntityName" lowercased so the assignment is a valuereference.
gLUE2EntityName ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2EntityName"}
  LDAP-DESC                 "Human-readable name"
  ID                        id-at-gLUE2EntityName }

-- initial capital of "GLUE2EntityOtherInfo" lowercased so the assignment is a valuereference.
gLUE2EntityOtherInfo ATTRIBUTE ::= {
  WITH SYNTAX               UnboundedDirectoryString
  EQUALITY MATCHING RULE    caseExactMatch
  SUBSTRINGS MATCHING RULE  caseExactSubstringsMatch
  LDAP-SYNTAX               directoryString.&id
  LDAP-NAME                 {"GLUE2EntityOtherInfo"}
  LDAP-DESC                 "Placeholder to publish info that does not fit in any other attribute"
  ID                        id-at-gLUE2EntityOtherInfo }

-- initial capital of "GLUE2EntityCreationTime" lowercased so the assignment is a valuereference.
gLUE2EntityCreationTime ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2EntityCreationTime"}
  LDAP-DESC                 "Timestamp describing when the entity instance was generated"
  ID                        id-at-gLUE2EntityCreationTime }

-- initial capital of "GLUE2EntityValidity" lowercased so the assignment is a valuereference.
gLUE2EntityValidity ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2EntityValidity"}
  LDAP-DESC                 "The duration of the information presented in this object after its creation time"
  ID                        id-at-gLUE2EntityValidity }

-- Object classes

-- initial capital of "GLUE2Entity" lowercased so the assignment is a valuereference.
-- SUP was absent. RFC 4512 treats that as a subclass of top, so SUBCLASS OF { top } was added.
gLUE2Entity OBJECT-CLASS ::= {
  SUBCLASS OF               { top }
  KIND                      abstract
  MAY CONTAIN               { gLUE2EntityName
                              | gLUE2EntityOtherInfo
                              | gLUE2EntityCreationTime
                              | gLUE2EntityValidity }
  LDAP-NAME                 {"GLUE2Entity"}
  LDAP-DESC                 "Base class"
  ID                        id-oc-gLUE2Entity }
END
