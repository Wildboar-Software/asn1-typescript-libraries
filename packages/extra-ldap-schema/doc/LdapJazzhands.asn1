-- Derived from data/ldap-schema/jazzhands.schema
-- Upstream: https://github.com/JazzHandsCMDB/jazzhands/blob/0753b69acbb1b1ac4eadaf28fa3899a3e5e06e6e/doc/jazzhands.schema#L33
-- This module is a container for LDAP schema. It has no module identifier.
-- X- extension fields from the LDAP schema are comments. USAGE userApplications and structural KIND are omitted because they are the defaults.
LdapJazzhands DEFINITIONS ::=
BEGIN

IMPORTS

  ATTRIBUTE, OBJECT-CLASS, top
    FROM InformationFramework
      {joint-iso-itu-t ds(5) module(1) informationFramework(1) 9} WITH SUCCESSORS

  integer, integerMatch
    FROM SelectedAttributeTypes
      {joint-iso-itu-t ds(5) module(1) selectedAttributeTypes(5) 9} WITH SUCCESSORS ;

-- Object identifiers

id-at-jazzHandsAccountId OBJECT IDENTIFIER ::= { 1 3 6 1 4 1 39422 1 1 1 1 }
id-at-jazzHandsAccountCollectionId OBJECT IDENTIFIER ::= { 1 3 6 1 4 1 39422 1 1 1 2 }
id-oc-jazzHandsAccountObject OBJECT IDENTIFIER ::= { 1 3 6 1 4 1 39422 1 1 2 1 }
id-oc-jazzHandsAccountCollectionObject OBJECT IDENTIFIER ::= { 1 3 6 1 4 1 39422 1 1 2 2 }

-- Attribute types

-- OID written as JazzHandsIds:1 and expanded with this file's objectidentifier macros.
jazzHandsAccountId ATTRIBUTE ::= {
  WITH SYNTAX               INTEGER
  EQUALITY MATCHING RULE    integerMatch
  SINGLE VALUE              TRUE
  LDAP-SYNTAX               integer.&id
  LDAP-NAME                 {"jazzHandsAccountId"}
  LDAP-DESC                 "jazzhands account table primary key"
  ID                        id-at-jazzHandsAccountId }

-- OID written as JazzHandsIds:2 and expanded with this file's objectidentifier macros.
jazzHandsAccountCollectionId ATTRIBUTE ::= {
  WITH SYNTAX               INTEGER
  EQUALITY MATCHING RULE    integerMatch
  SINGLE VALUE              TRUE
  LDAP-SYNTAX               integer.&id
  LDAP-NAME                 {"jazzHandsAccountCollectionId"}
  LDAP-DESC                 "jazzhands account_collection table primary key"
  ID                        id-at-jazzHandsAccountCollectionId }

-- Object classes

-- OID written as JazzHandsObjects:1 and expanded with this file's objectidentifier macros.
jazzHandsAccountObject OBJECT-CLASS ::= {
  SUBCLASS OF               { top }
  KIND                      auxiliary
  MAY CONTAIN               { jazzHandsAccountId }
  LDAP-NAME                 {"jazzHandsAccountObject"}
  LDAP-DESC                 "jazzHands account object class"
  ID                        id-oc-jazzHandsAccountObject }

-- OID written as JazzHandsObjects:2 and expanded with this file's objectidentifier macros.
jazzHandsAccountCollectionObject OBJECT-CLASS ::= {
  SUBCLASS OF               { top }
  KIND                      auxiliary
  MAY CONTAIN               { jazzHandsAccountCollectionId }
  LDAP-NAME                 {"jazzHandsAccountCollectionObject"}
  LDAP-DESC                 "jazzHands account collection class"
  ID                        id-oc-jazzHandsAccountCollectionObject }
END
