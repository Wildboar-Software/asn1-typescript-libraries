-- Derived from data/ldap-schema/glue/5-10-Resource.schema
-- Upstream: http://redmine.ogf.org/projects/glue-wg
-- This module is a container for LDAP schema. It has no module identifier.
-- X- extension fields from the LDAP schema are comments. USAGE userApplications and structural KIND are omitted because they are the defaults.
LdapGlue510Resource DEFINITIONS ::=
BEGIN

IMPORTS

  ATTRIBUTE, OBJECT-CLASS
    FROM InformationFramework
      {joint-iso-itu-t ds(5) module(1) informationFramework(1) 9} WITH SUCCESSORS

  caseExactMatch, caseExactSubstringsMatch, directoryString,
    UnboundedDirectoryString
    FROM SelectedAttributeTypes
      {joint-iso-itu-t ds(5) module(1) selectedAttributeTypes(5) 9} WITH SUCCESSORS

  gLUE2Entity
    FROM LdapGlue501Entity ;

-- Object identifiers

id-at-gLUE2ResourceID OBJECT IDENTIFIER ::= { 1 3 6 1 4 1 6757 100 1 1 12 1 }
id-at-gLUE2ResourceManagerForeignKey OBJECT IDENTIFIER ::= { 1 3 6 1 4 1 6757 100 1 1 12 2 }
id-oc-gLUE2Resource OBJECT IDENTIFIER ::= { 1 3 6 1 4 1 6757 100 1 1 12 }

-- Attribute types

-- initial capital of "GLUE2ResourceID" lowercased so the assignment is a valuereference.
gLUE2ResourceID ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2ResourceID"}
  LDAP-DESC                 "Globally unique ID"
  ID                        id-at-gLUE2ResourceID }

-- initial capital of "GLUE2ResourceManagerForeignKey" lowercased so the assignment is a valuereference.
gLUE2ResourceManagerForeignKey ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2ResourceManagerForeignKey"}
  LDAP-DESC                 "ForeignKey"
  ID                        id-at-gLUE2ResourceManagerForeignKey }

-- Object classes

-- initial capital of "GLUE2Resource" lowercased so the assignment is a valuereference.
gLUE2Resource OBJECT-CLASS ::= {
  SUBCLASS OF               { gLUE2Entity }
  MUST CONTAIN              { gLUE2ResourceID
                              | gLUE2ResourceManagerForeignKey }
  LDAP-NAME                 {"GLUE2Resource"}
  LDAP-DESC                 "A resource"
  ID                        id-oc-gLUE2Resource }
END
