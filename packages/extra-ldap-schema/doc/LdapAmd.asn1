-- Derived from data/ldap-schema/amd.schema
-- Upstream: https://github.com/nestedkernel/PerspicuOS/blob/aae9a39b7e954c4ef6222af49e722aa5aa50f624/FreeBSD9/contrib/amd/ldap.schema#L44
-- This module is a container for LDAP schema. It has no module identifier.
-- X- extension fields from the LDAP schema are comments. USAGE userApplications and structural KIND are omitted because they are the defaults.
LdapAmd DEFINITIONS ::=
BEGIN

IMPORTS

  ATTRIBUTE, OBJECT-CLASS, top
    FROM InformationFramework
      {joint-iso-itu-t ds(5) module(1) informationFramework(1) 9} WITH SUCCESSORS

  caseIgnoreMatch, commonName, directoryString, integer, integerMatch,
    UnboundedDirectoryString
    FROM SelectedAttributeTypes
      {joint-iso-itu-t ds(5) module(1) selectedAttributeTypes(5) 9} WITH SUCCESSORS ;

-- Object identifiers

id-at-amdmapTimestamp OBJECT IDENTIFIER ::= { 1 3 6 1 4 1 10180 2 175 }
id-at-amdmapName OBJECT IDENTIFIER ::= { 1 3 6 1 4 1 10180 2 176 }
id-at-amdmapKey OBJECT IDENTIFIER ::= { 1 3 6 1 4 1 10180 2 177 }
id-at-amdmapValue OBJECT IDENTIFIER ::= { 1 3 6 1 4 1 10180 2 178 }
id-oc-amdmapTimestamp-2 OBJECT IDENTIFIER ::= { 1 3 6 1 4 1 10180 1 175 }
id-oc-amdmap OBJECT IDENTIFIER ::= { 1 3 6 1 4 1 10180 1 176 }

-- Attribute types

amdmapTimestamp ATTRIBUTE ::= {
  WITH SYNTAX               INTEGER
  EQUALITY MATCHING RULE    integerMatch
  SINGLE VALUE              TRUE
  LDAP-SYNTAX               integer.&id
  LDAP-NAME                 {"amdmapTimestamp"}
  LDAP-DESC                 "Probably the time the map was last modified"
  ID                        id-at-amdmapTimestamp }

amdmapName ATTRIBUTE ::= {
  WITH SYNTAX               UnboundedDirectoryString
  EQUALITY MATCHING RULE    caseIgnoreMatch
  SINGLE VALUE              TRUE
  LDAP-SYNTAX               directoryString.&id
  LDAP-NAME                 {"amdmapName"}
  LDAP-DESC                 "The symbolic name of the map, ie. map_name"
  ID                        id-at-amdmapName }

amdmapKey ATTRIBUTE ::= {
  WITH SYNTAX               UnboundedDirectoryString
  EQUALITY MATCHING RULE    caseIgnoreMatch
  SINGLE VALUE              TRUE
  LDAP-SYNTAX               directoryString.&id
  LDAP-NAME                 {"amdmapKey"}
  LDAP-DESC                 "The key value for this entry"
  ID                        id-at-amdmapKey }

amdmapValue ATTRIBUTE ::= {
  WITH SYNTAX               UnboundedDirectoryString
  EQUALITY MATCHING RULE    caseIgnoreMatch
  SINGLE VALUE              TRUE
  LDAP-SYNTAX               directoryString.&id
  LDAP-NAME                 {"amdmapValue"}
  LDAP-DESC                 "The mount information for this entry"
  ID                        id-at-amdmapValue }

-- Object classes

-- disambiguated amdmapTimestamp to amdmapTimestamp-2 inside LdapAmd.
amdmapTimestamp-2 OBJECT-CLASS ::= {
  SUBCLASS OF               { top }
  MUST CONTAIN              { commonName
                              | amdmapName
                              | amdmapTimestamp }
  LDAP-NAME                 {"amdmapTimestamp"}
  LDAP-DESC                 "Timestamp for an AMD map"
  ID                        id-oc-amdmapTimestamp-2 }

amdmap OBJECT-CLASS ::= {
  SUBCLASS OF               { top }
  MUST CONTAIN              { commonName
                              | amdmapName
                              | amdmapKey
                              | amdmapValue }
  LDAP-NAME                 {"amdmap"}
  LDAP-DESC                 "Defines an AMD map entry"
  ID                        id-oc-amdmap }
END
