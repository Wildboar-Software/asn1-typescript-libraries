-- Derived from data/ldap-schema/gosa-core/goto-mime.schema
-- This module is a container for LDAP schema. It has no module identifier.
-- X- extension fields from the LDAP schema are comments. USAGE userApplications and structural KIND are omitted because they are the defaults.
LdapGosaCoreGotoMime DEFINITIONS ::=
BEGIN

IMPORTS

  ATTRIBUTE, OBJECT-CLASS, top
    FROM InformationFramework
      {joint-iso-itu-t ds(5) module(1) informationFramework(1) 9} WITH SUCCESSORS

  caseIgnoreIA5Match, caseIgnoreIA5SubstringsMatch, commonName, description,
    ia5String, jpeg
    FROM SelectedAttributeTypes
      {joint-iso-itu-t ds(5) module(1) selectedAttributeTypes(5) 9} WITH SUCCESSORS ;

-- Object identifiers

id-at-gotoMimeGroup OBJECT IDENTIFIER ::= { 1 3 6 1 4 1 10098 1 1 14 1 }
id-at-gotoMimeFilePattern OBJECT IDENTIFIER ::= { 1 3 6 1 4 1 10098 1 1 14 2 }
id-at-gotoMimeApplication OBJECT IDENTIFIER ::= { 1 3 6 1 4 1 10098 1 1 14 3 }
id-at-gotoMimeEmbeddedApplication OBJECT IDENTIFIER ::= { 1 3 6 1 4 1 10098 1 1 14 4 }
id-at-gotoMimeLeftClickAction OBJECT IDENTIFIER ::= { 1 3 6 1 4 1 10098 1 1 14 5 }
id-at-gotoMimeIcon OBJECT IDENTIFIER ::= { 1 3 6 1 4 1 10098 1 1 14 6 }
id-oc-gotoMimeType OBJECT IDENTIFIER ::= { 1 3 6 1 4 1 10098 1 2 4 1 }

-- Attribute types

gotoMimeGroup ATTRIBUTE ::= {
  WITH SYNTAX               IA5String
  EQUALITY MATCHING RULE    caseIgnoreIA5Match
  SUBSTRINGS MATCHING RULE  caseIgnoreIA5SubstringsMatch
  SINGLE VALUE              TRUE
  LDAP-SYNTAX               ia5String.&id
  LDAP-NAME                 {"gotoMimeGroup"}
  LDAP-DESC                 "IANA defined mime group"
  ID                        id-at-gotoMimeGroup }

gotoMimeFilePattern ATTRIBUTE ::= {
  WITH SYNTAX               IA5String
  EQUALITY MATCHING RULE    caseIgnoreIA5Match
  SUBSTRINGS MATCHING RULE  caseIgnoreIA5SubstringsMatch
  LDAP-SYNTAX               ia5String.&id
  LDAP-NAME                 {"gotoMimeFilePattern"}
  LDAP-DESC                 "File extensions for mime types"
  ID                        id-at-gotoMimeFilePattern }

gotoMimeApplication ATTRIBUTE ::= {
  WITH SYNTAX               IA5String
  EQUALITY MATCHING RULE    caseIgnoreIA5Match
  SUBSTRINGS MATCHING RULE  caseIgnoreIA5SubstringsMatch
  LDAP-SYNTAX               ia5String.&id
  LDAP-NAME                 {"gotoMimeApplication"}
  LDAP-DESC                 "Assigned application and priority"
  ID                        id-at-gotoMimeApplication }

gotoMimeEmbeddedApplication ATTRIBUTE ::= {
  WITH SYNTAX               IA5String
  EQUALITY MATCHING RULE    caseIgnoreIA5Match
  SUBSTRINGS MATCHING RULE  caseIgnoreIA5SubstringsMatch
  LDAP-SYNTAX               ia5String.&id
  LDAP-NAME                 {"gotoMimeEmbeddedApplication"}
  LDAP-DESC                 "Assigned application and priority for embedded applications"
  ID                        id-at-gotoMimeEmbeddedApplication }

gotoMimeLeftClickAction ATTRIBUTE ::= {
  WITH SYNTAX               IA5String
  EQUALITY MATCHING RULE    caseIgnoreIA5Match
  SUBSTRINGS MATCHING RULE  caseIgnoreIA5SubstringsMatch
  SINGLE VALUE              TRUE
  LDAP-SYNTAX               ia5String.&id
  LDAP-NAME                 {"gotoMimeLeftClickAction"}
  LDAP-DESC                 "GOto - Gonicus Terminal Concept, PPD data"
  ID                        id-at-gotoMimeLeftClickAction }

-- X.520 models the JPEG syntax as NULL. Represented as OCTET STRING. LDAP-SYNTAX remains jpeg.&id.
gotoMimeIcon ATTRIBUTE ::= {
  WITH SYNTAX               OCTET STRING
  SINGLE VALUE              TRUE
  LDAP-SYNTAX               jpeg.&id
  LDAP-NAME                 {"gotoMimeIcon"}
  LDAP-DESC                 "Specify the mime icon"
  ID                        id-at-gotoMimeIcon }

-- Object classes

gotoMimeType OBJECT-CLASS ::= {
  SUBCLASS OF               { top }
  MUST CONTAIN              { commonName
                              | gotoMimeFilePattern
                              | gotoMimeGroup }
  MAY CONTAIN               { description
                              | gotoMimeIcon
                              | gotoMimeApplication
                              | gotoMimeEmbeddedApplication
                              | gotoMimeLeftClickAction }
  LDAP-NAME                 {"gotoMimeType"}
  LDAP-DESC                 "Class to represent global mime types (v2.7)"
  ID                        id-oc-gotoMimeType }
END
