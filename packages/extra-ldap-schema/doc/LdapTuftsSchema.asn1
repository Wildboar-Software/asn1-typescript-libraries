-- Derived from data/ldap-schema/tufts-schema.ldif
-- This module is a container for LDAP schema. It has no module identifier.
-- X- extension fields from the LDAP schema are comments. USAGE userApplications and structural KIND are omitted because they are the defaults.
LdapTuftsSchema DEFINITIONS ::=
BEGIN

IMPORTS

  ATTRIBUTE, OBJECT-CLASS, top
    FROM InformationFramework
      {joint-iso-itu-t ds(5) module(1) informationFramework(1) 9} WITH SUCCESSORS

  directoryString, UnboundedDirectoryString
    FROM SelectedAttributeTypes
      {joint-iso-itu-t ds(5) module(1) selectedAttributeTypes(5) 9} WITH SUCCESSORS ;

-- Object identifiers

id-at-tuftsEduDisplayNameLF OBJECT IDENTIFIER ::= { 1 3 6 1 4 1 6940 1 1 1 1 2 1 1 47 }
id-oc-tuftsEduPerson OBJECT IDENTIFIER ::= { 1 3 6 1 4 1 6940 1 1 1 1 2 1 2 1 }

-- Attribute types

tuftsEduDisplayNameLF ATTRIBUTE ::= {
  WITH SYNTAX               UnboundedDirectoryString
  LDAP-SYNTAX               directoryString.&id
  LDAP-NAME                 {"tuftsEduDisplayNameLF"}
  LDAP-DESC                 "displayName in last, first form"
  ID                        id-at-tuftsEduDisplayNameLF }

-- Object classes

tuftsEduPerson OBJECT-CLASS ::= {
  SUBCLASS OF               { top }
  KIND                      abstract
  MAY CONTAIN               { tuftsEduDisplayNameLF }
  LDAP-NAME                 {"tuftsEduPerson"}
  LDAP-DESC                 "Tufts schema extensions for people directory entries"
  ID                        id-oc-tuftsEduPerson }
END
