-- Derived from data/ldap-schema/schema2ldif/pgp-remte-prefs.schema
-- This module is a container for LDAP schema. It has no module identifier.
-- X- extension fields from the LDAP schema are comments. USAGE userApplications and structural KIND are omitted because they are the defaults.
LdapSchema2ldifPgpRemtePrefs DEFINITIONS ::=
BEGIN

IMPORTS

  ATTRIBUTE, OBJECT-CLASS, objectClass, top
    FROM InformationFramework
      {joint-iso-itu-t ds(5) module(1) informationFramework(1) 9} WITH SUCCESSORS

  caseIgnoreMatch, caseIgnoreSubstringsMatch, commonName, directoryString,
    octetString, owner, UnboundedDirectoryString
    FROM SelectedAttributeTypes
      {joint-iso-itu-t ds(5) module(1) selectedAttributeTypes(5) 9} WITH SUCCESSORS ;

-- Object identifiers

id-at-pgpElementType OBJECT IDENTIFIER ::= { 1 3 6 1 4 1 3401 8 2 2 }
id-at-pgpData OBJECT IDENTIFIER ::= { 1 3 6 1 4 1 3401 8 2 3 }
id-oc-pgpProfile OBJECT IDENTIFIER ::= { 1 3 6 1 4 1 3401 8 2 4 }
id-oc-pgpElement OBJECT IDENTIFIER ::= { 1 3 6 1 4 1 3401 8 2 1 }

-- Attribute types

-- X-ORIGIN: "Pretty Good Privacy (PGP)"
pgpElementType ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"pgpElementType"}
  LDAP-DESC                 "PGP defined attribute containing the type of the pref object"
  ID                        id-at-pgpElementType }

-- X-ORIGIN: "Pretty Good Privacy (PGP)"
pgpData ATTRIBUTE ::= {
  WITH SYNTAX               OCTET STRING
  SINGLE VALUE              TRUE
  LDAP-SYNTAX               octetString.&id
  LDAP-NAME                 {"pgpData"}
  LDAP-DESC                 "PGP defined attribute containing the admin pref data"
  ID                        id-at-pgpData }

-- Object classes

-- X-ORIGIN: "Pretty Good Privacy (PGP)"
pgpProfile OBJECT-CLASS ::= {
  SUBCLASS OF               { top }
  MUST CONTAIN              { objectClass }
  MAY CONTAIN               { commonName
                              | owner }
  LDAP-NAME                 {"pgpProfile"}
  LDAP-DESC                 "PGP defined objectclass of a collection admin prefs"
  ID                        id-oc-pgpProfile }

-- X-ORIGIN: "Pretty Good Privacy (PGP)"
pgpElement OBJECT-CLASS ::= {
  SUBCLASS OF               { top }
  MUST CONTAIN              { objectClass }
  MAY CONTAIN               { pgpElementType
                              | pgpData
                              | owner }
  LDAP-NAME                 {"pgpElement"}
  LDAP-DESC                 "PGP defined objectclass of a single admin pref object"
  ID                        id-oc-pgpElement }
END
