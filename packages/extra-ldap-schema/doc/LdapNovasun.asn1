-- Derived from data/ldap-schema/novasun.ldif
-- Upstream: https://github.com/wikimedia-incubator/operations-puppet/blob/392301bc570b5b61f48eda0cbaa62b8b8ff52f92/files/ldap/nova_sun.ldif#L10
-- This module is a container for LDAP schema. It has no module identifier.
-- X- extension fields from the LDAP schema are comments. USAGE userApplications and structural KIND are omitted because they are the defaults.
LdapNovasun DEFINITIONS ::=
BEGIN

IMPORTS

  ATTRIBUTE, OBJECT-CLASS, top
    FROM InformationFramework
      {joint-iso-itu-t ds(5) module(1) informationFramework(1) 9} WITH SUCCESSORS

  boolean, booleanMatch, caseIgnoreMatch, caseIgnoreSubstringsMatch,
    directoryString, UnboundedDirectoryString
    FROM SelectedAttributeTypes
      {joint-iso-itu-t ds(5) module(1) selectedAttributeTypes(5) 9} WITH SUCCESSORS ;

-- Object identifiers

id-at-accessKey OBJECT IDENTIFIER ::= { 1 3 6 1 3 1 666 666 3 1 }
id-at-secretKey OBJECT IDENTIFIER ::= { 1 3 6 1 3 1 666 666 3 2 }
id-at-isNovaAdmin OBJECT IDENTIFIER ::= { 1 3 6 1 3 1 666 666 3 4 }
id-oc-novaUser OBJECT IDENTIFIER ::= { 1 3 6 1 3 1 666 666 4 1 }

-- Attribute types

accessKey ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"accessKey"}
  LDAP-DESC                 "Key for accessing data"
  ID                        id-at-accessKey }

secretKey ATTRIBUTE ::= {
  WITH SYNTAX               UnboundedDirectoryString
  EQUALITY MATCHING RULE    caseIgnoreMatch
  SUBSTRINGS MATCHING RULE  caseIgnoreSubstringsMatch
  SINGLE VALUE              TRUE
  LDAP-SYNTAX               directoryString.&id
  LDAP-NAME                 {"secretKey"}
  LDAP-DESC                 "Secret key"
  ID                        id-at-secretKey }

isNovaAdmin ATTRIBUTE ::= {
  WITH SYNTAX               BOOLEAN
  EQUALITY MATCHING RULE    booleanMatch
  SINGLE VALUE              TRUE
  LDAP-SYNTAX               boolean.&id
  LDAP-NAME                 {"isNovaAdmin"}
  LDAP-DESC                 "Is user a nova administrator?"
  ID                        id-at-isNovaAdmin }

-- Object classes

novaUser OBJECT-CLASS ::= {
  SUBCLASS OF               { top }
  KIND                      auxiliary
  MAY CONTAIN               { accessKey
                              | secretKey
                              | isNovaAdmin }
  LDAP-NAME                 {"novaUser"}
  LDAP-DESC                 "access and secret keys"
  ID                        id-oc-novaUser }
END
