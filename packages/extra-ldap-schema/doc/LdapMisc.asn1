-- Derived from data/ldap-schema/misc.schema
-- Upstream: https://raw.githubusercontent.com/openshift/openldap/bf6fe685b0a3ebba944b37631a088a58eb49516d/contrib/config/schema/misc.schema
-- This module is a container for LDAP schema. It has no module identifier.
-- X- extension fields from the LDAP schema are comments. USAGE userApplications and structural KIND are omitted because they are the defaults.
-- 4 elements were omitted because their OIDs are already defined. See CONVERSION-REPORT.txt.
LdapMisc DEFINITIONS ::=
BEGIN

IMPORTS

  ATTRIBUTE, OBJECT-CLASS, top
    FROM InformationFramework
      {joint-iso-itu-t ds(5) module(1) informationFramework(1) 9} WITH SUCCESSORS

  caseIgnoreIA5Match, commonName, ia5String
    FROM SelectedAttributeTypes
      {joint-iso-itu-t ds(5) module(1) selectedAttributeTypes(5) 9} WITH SUCCESSORS ;

-- Object identifiers

id-at-rfc822MailMember OBJECT IDENTIFIER ::= { 1 3 6 1 4 1 42 2 27 2 1 15 }
id-oc-nisMailAlias OBJECT IDENTIFIER ::= { 1 3 6 1 4 1 42 2 27 1 2 5 }

-- Attribute types

rfc822MailMember ATTRIBUTE ::= {
  WITH SYNTAX               IA5String
  EQUALITY MATCHING RULE    caseIgnoreIA5Match
  LDAP-SYNTAX               ia5String.&id
  LDAP-NAME                 {"rfc822MailMember"}
  LDAP-DESC                 "rfc822 mail address of group member(s)"
  ID                        id-at-rfc822MailMember }

-- Object classes

nisMailAlias OBJECT-CLASS ::= {
  SUBCLASS OF               { top }
  MUST CONTAIN              { commonName }
  MAY CONTAIN               { rfc822MailMember }
  LDAP-NAME                 {"nisMailAlias"}
  LDAP-DESC                 "NIS mail alias"
  ID                        id-oc-nisMailAlias }
END
