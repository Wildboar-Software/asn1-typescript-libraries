-- Derived from data/ldap-schema/gosa-core/phpscheduleit.schema
-- This module is a container for LDAP schema. It has no module identifier.
-- X- extension fields from the LDAP schema are comments. USAGE userApplications and structural KIND are omitted because they are the defaults.
LdapGosaCorePhpscheduleit DEFINITIONS ::=
BEGIN

IMPORTS

  ATTRIBUTE, OBJECT-CLASS, top
    FROM InformationFramework
      {joint-iso-itu-t ds(5) module(1) informationFramework(1) 9} WITH SUCCESSORS

  caseIgnoreIA5Match, ia5String
    FROM SelectedAttributeTypes
      {joint-iso-itu-t ds(5) module(1) selectedAttributeTypes(5) 9} WITH SUCCESSORS

  caseExactIA5SubstringsMatch
    FROM OpenLDAP
      {iso(1) identified-organization(3) dod(6) internet(1) private(4) enterprise(1) wildboar(56490) module(1) openldap(28)} WITH SUCCESSORS ;

-- Object identifiers

id-at-phpscheduleitAccountLogin OBJECT IDENTIFIER ::= { 1 3 6 1 4 1 22262 1 1 1 3 1 }
id-oc-phpscheduleitAccount OBJECT IDENTIFIER ::= { 1 3 6 1 4 1 22262 1 1 2 3 1 }

-- Attribute types

phpscheduleitAccountLogin ATTRIBUTE ::= {
  WITH SYNTAX               IA5String
  EQUALITY MATCHING RULE    caseIgnoreIA5Match
  SUBSTRINGS MATCHING RULE  caseExactIA5SubstringsMatch
  LDAP-SYNTAX               ia5String.&id
  LDAP-NAME                 {"phpscheduleitAccountLogin"}
  LDAP-DESC                 "PHPscheduleit Account Login"
  ID                        id-at-phpscheduleitAccountLogin }

-- Object classes

phpscheduleitAccount OBJECT-CLASS ::= {
  SUBCLASS OF               { top }
  KIND                      auxiliary
  MAY CONTAIN               { phpscheduleitAccountLogin }
  LDAP-NAME                 {"phpscheduleitAccount"}
  LDAP-DESC                 "PHPscheduleit Account"
  ID                        id-oc-phpscheduleitAccount }
END
