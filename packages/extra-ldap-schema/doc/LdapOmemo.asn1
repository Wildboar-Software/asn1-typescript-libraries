-- Derived from data/ldap-schema/omemo.schema
-- Upstream: https://github.com/freenit-framework/backend/blob/37bbff9d1d5d54643559ec4ecb0e6129b7b6200d/ldap/omemo.schema#L8
-- This module is a container for LDAP schema. It has no module identifier.
-- X- extension fields from the LDAP schema are comments. USAGE userApplications and structural KIND are omitted because they are the defaults.
-- LDAP {length} bounds on directory strings are DirectoryString{n}. Bounds on IA5String, PrintableString, NumericString, and OCTET STRING are SIZE (1..n). Other bounds stay comments because the LDAP figure is an encoded-length hint.
LdapOmemo DEFINITIONS ::=
BEGIN

IMPORTS

  ATTRIBUTE, OBJECT-CLASS, top
    FROM InformationFramework
      {joint-iso-itu-t ds(5) module(1) informationFramework(1) 9} WITH SUCCESSORS

  caseExactMatch, caseExactSubstringsMatch, directoryString, DirectoryString
    FROM SelectedAttributeTypes
      {joint-iso-itu-t ds(5) module(1) selectedAttributeTypes(5) 9} WITH SUCCESSORS ;

-- Object identifiers

id-at-omemoBundle OBJECT IDENTIFIER ::= { 1 3 6 1 4 1 4203 666 1 1 }
id-oc-omemoPerson OBJECT IDENTIFIER ::= { 1 3 6 1 4 1 4203 666 2 1 }

-- Attribute types

-- LDAP syntax length {32768} rendered as DirectoryString{32768}.
omemoBundle ATTRIBUTE ::= {
  WITH SYNTAX               DirectoryString{32768}
  EQUALITY MATCHING RULE    caseExactMatch
  SUBSTRINGS MATCHING RULE  caseExactSubstringsMatch
  SINGLE VALUE              TRUE
  LDAP-SYNTAX               directoryString.&id
  LDAP-NAME                 {"omemoBundle"}
  LDAP-DESC                 "Encrypted OMEMO device bundle"
  ID                        id-at-omemoBundle }

-- Object classes

omemoPerson OBJECT-CLASS ::= {
  SUBCLASS OF               { top }
  KIND                      auxiliary
  MAY CONTAIN               { omemoBundle }
  LDAP-NAME                 {"omemoPerson"}
  LDAP-DESC                 "Person with OMEMO encryption support"
  ID                        id-oc-omemoPerson }
END
