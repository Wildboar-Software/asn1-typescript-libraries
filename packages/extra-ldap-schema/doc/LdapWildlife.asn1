-- Derived from data/ldap-schema/wildlife.ldif
-- Upstream: https://github.com/peterdavidhamilton/rom-ldap/blob/d9cc77fdeff86b34b8e236a869d5bc5804c7d48b/docker/opendj/rom/wildlife.ldif
-- This module is a container for LDAP schema. It has no module identifier.
-- X- extension fields from the LDAP schema are comments. USAGE userApplications and structural KIND are omitted because they are the defaults.
LdapWildlife DEFINITIONS ::=
BEGIN

IMPORTS

  ATTRIBUTE, OBJECT-CLASS, top
    FROM InformationFramework
      {joint-iso-itu-t ds(5) module(1) informationFramework(1) 9} WITH SUCCESSORS

  boolean, booleanMatch, caseIgnoreMatch, caseIgnoreOrderingMatch, commonName,
    directoryString, generalizedTime, generalizedTimeMatch,
    generalizedTimeOrderingMatch, integer, integerMatch, integerOrderingMatch,
    UnboundedDirectoryString
    FROM SelectedAttributeTypes
      {joint-iso-itu-t ds(5) module(1) selectedAttributeTypes(5) 9} WITH SUCCESSORS ;

-- Object identifiers

id-at-species OBJECT IDENTIFIER ::= { 1 3 6 1 4 1 18055 0 4 1 2 1001 }
id-at-genus OBJECT IDENTIFIER ::= { 1 3 6 1 4 1 18055 0 4 1 2 1002 }
id-at-family OBJECT IDENTIFIER ::= { 1 3 6 1 4 1 18055 0 4 1 2 1003 }
id-at-order OBJECT IDENTIFIER ::= { 1 3 6 1 4 1 18055 0 4 1 2 1004 }
id-at-extinct OBJECT IDENTIFIER ::= { 1 3 6 1 4 1 18055 0 4 1 2 1005 }
id-at-endangered OBJECT IDENTIFIER ::= { 1 3 6 1 4 1 18055 0 4 1 2 1006 }
id-at-study OBJECT IDENTIFIER ::= { 1 3 6 1 4 1 18055 0 4 1 2 1007 }
id-at-discoveryDate OBJECT IDENTIFIER ::= { 1 3 6 1 4 1 18055 0 4 1 2 1008 }
id-at-populationCount OBJECT IDENTIFIER ::= { 1 3 6 1 4 1 18055 0 4 1 2 1010 }
id-oc-amphibia OBJECT IDENTIFIER ::= { 1 3 6 1 4 1 18055 0 4 1 3 1000 }
id-oc-reptilia OBJECT IDENTIFIER ::= { 1 3 6 1 4 1 18055 0 4 1 3 1001 }
id-oc-aves OBJECT IDENTIFIER ::= { 1 3 6 1 4 1 18055 0 4 1 3 1002 }
id-oc-mammalia OBJECT IDENTIFIER ::= { 1 3 6 1 4 1 18055 0 4 1 3 1003 }
id-oc-chondrichthyes OBJECT IDENTIFIER ::= { 1 3 6 1 4 1 18055 0 4 1 3 1004 }
id-oc-cephalopoda OBJECT IDENTIFIER ::= { 1 3 6 1 4 1 18055 0 4 1 3 1005 }
id-oc-crustacea OBJECT IDENTIFIER ::= { 1 3 6 1 4 1 18055 0 4 1 3 1006 }

-- Attribute types

-- X-ORIGIN: "rom-ldap taxonomy"
-- X-SCHEMA-FILE: "wildlife.ldif"
species ATTRIBUTE ::= {
  WITH SYNTAX               UnboundedDirectoryString
  EQUALITY MATCHING RULE    caseIgnoreMatch
  ORDERING MATCHING RULE    caseIgnoreOrderingMatch
  SINGLE VALUE              TRUE
  LDAP-SYNTAX               directoryString.&id
  LDAP-NAME                 {"species"}
  LDAP-DESC                 "The scientific name of the animal"
  ID                        id-at-species }

-- X-ORIGIN: "rom-ldap taxonomy"
-- X-SCHEMA-FILE: "wildlife.ldif"
genus ATTRIBUTE ::= {
  WITH SYNTAX               UnboundedDirectoryString
  EQUALITY MATCHING RULE    caseIgnoreMatch
  ORDERING MATCHING RULE    caseIgnoreOrderingMatch
  SINGLE VALUE              TRUE
  LDAP-SYNTAX               directoryString.&id
  LDAP-NAME                 {"genus"}
  LDAP-DESC                 "The first part of the binomial species name of the animal"
  ID                        id-at-genus }

-- X-ORIGIN: "rom-ldap taxonomy"
-- X-SCHEMA-FILE: "wildlife.ldif"
family ATTRIBUTE ::= {
  WITH SYNTAX               UnboundedDirectoryString
  EQUALITY MATCHING RULE    caseIgnoreMatch
  ORDERING MATCHING RULE    caseIgnoreOrderingMatch
  SINGLE VALUE              TRUE
  LDAP-SYNTAX               directoryString.&id
  LDAP-NAME                 {"family"}
  LDAP-DESC                 "The family classification of the animal"
  ID                        id-at-family }

-- X-ORIGIN: "rom-ldap taxonomy"
-- X-SCHEMA-FILE: "wildlife.ldif"
order ATTRIBUTE ::= {
  WITH SYNTAX               UnboundedDirectoryString
  EQUALITY MATCHING RULE    caseIgnoreMatch
  ORDERING MATCHING RULE    caseIgnoreOrderingMatch
  SINGLE VALUE              TRUE
  LDAP-SYNTAX               directoryString.&id
  LDAP-NAME                 {"order"}
  LDAP-DESC                 "The order classification of the animal"
  ID                        id-at-order }

-- X-ORIGIN: "rom-ldap taxonomy"
-- X-SCHEMA-FILE: "wildlife.ldif"
extinct ATTRIBUTE ::= {
  WITH SYNTAX               BOOLEAN
  EQUALITY MATCHING RULE    booleanMatch
  SINGLE VALUE              TRUE
  LDAP-SYNTAX               boolean.&id
  LDAP-NAME                 {"extinct"}
  LDAP-DESC                 "Has the animal died out"
  ID                        id-at-extinct }

-- X-ORIGIN: "rom-ldap taxonomy"
-- X-SCHEMA-FILE: "wildlife.ldif"
endangered ATTRIBUTE ::= {
  WITH SYNTAX               BOOLEAN
  EQUALITY MATCHING RULE    booleanMatch
  SINGLE VALUE              TRUE
  LDAP-SYNTAX               boolean.&id
  LDAP-NAME                 {"endangered"}
  LDAP-DESC                 "The conservation status of the animal"
  ID                        id-at-endangered }

-- X-ORIGIN: "rom-ldap taxonomy"
-- X-SCHEMA-FILE: "wildlife.ldif"
study ATTRIBUTE ::= {
  WITH SYNTAX               UnboundedDirectoryString
  EQUALITY MATCHING RULE    caseIgnoreMatch
  ORDERING MATCHING RULE    caseIgnoreOrderingMatch
  SINGLE VALUE              TRUE
  LDAP-SYNTAX               directoryString.&id
  LDAP-NAME                 {"study"}
  LDAP-DESC                 "The field of study"
  ID                        id-at-study }

-- X-ORIGIN: "rom-ldap taxonomy"
-- X-SCHEMA-FILE: "wildlife.ldif"
discoveryDate ATTRIBUTE ::= {
  WITH SYNTAX               GeneralizedTime
  EQUALITY MATCHING RULE    generalizedTimeMatch
  ORDERING MATCHING RULE    generalizedTimeOrderingMatch
  SINGLE VALUE              TRUE
  LDAP-SYNTAX               generalizedTime.&id
  LDAP-NAME                 {"discoveryDate", "discovery-date"}
  LDAP-DESC                 "The date the animal was discovered"
  ID                        id-at-discoveryDate }

-- X-ORIGIN: "rom-ldap taxonomy"
-- X-SCHEMA-FILE: "wildlife.ldif"
populationCount ATTRIBUTE ::= {
  WITH SYNTAX               INTEGER
  EQUALITY MATCHING RULE    integerMatch
  ORDERING MATCHING RULE    integerOrderingMatch
  SINGLE VALUE              TRUE
  LDAP-SYNTAX               integer.&id
  LDAP-NAME                 {"populationCount", "population-count"}
  LDAP-DESC                 "The estimated number of animals"
  ID                        id-at-populationCount }

-- Object classes

amphibia OBJECT-CLASS ::= {
  SUBCLASS OF               { top }
  MUST CONTAIN              { species }
  MAY CONTAIN               { populationCount
                              | extinct
                              | commonName }
  LDAP-NAME                 {"amphibia"}
  LDAP-DESC                 "Amphibians"
  ID                        id-oc-amphibia }

reptilia OBJECT-CLASS ::= {
  SUBCLASS OF               { top }
  MUST CONTAIN              { species }
  MAY CONTAIN               { populationCount
                              | extinct
                              | commonName }
  LDAP-NAME                 {"reptilia"}
  LDAP-DESC                 "Reptiles"
  ID                        id-oc-reptilia }

aves OBJECT-CLASS ::= {
  SUBCLASS OF               { top }
  MUST CONTAIN              { species }
  MAY CONTAIN               { populationCount
                              | extinct
                              | commonName }
  LDAP-NAME                 {"aves"}
  LDAP-DESC                 "Birds"
  ID                        id-oc-aves }

mammalia OBJECT-CLASS ::= {
  SUBCLASS OF               { top }
  MUST CONTAIN              { species }
  MAY CONTAIN               { populationCount
                              | extinct
                              | commonName }
  LDAP-NAME                 {"mammalia"}
  LDAP-DESC                 "Mammals"
  ID                        id-oc-mammalia }

chondrichthyes OBJECT-CLASS ::= {
  SUBCLASS OF               { top }
  MUST CONTAIN              { species }
  MAY CONTAIN               { populationCount
                              | extinct
                              | commonName }
  LDAP-NAME                 {"chondrichthyes"}
  LDAP-DESC                 "Cartilaginous fishes"
  ID                        id-oc-chondrichthyes }

cephalopoda OBJECT-CLASS ::= {
  SUBCLASS OF               { top }
  MUST CONTAIN              { species }
  MAY CONTAIN               { populationCount
                              | extinct
                              | commonName }
  LDAP-NAME                 {"cephalopoda"}
  LDAP-DESC                 "Marine mollusc"
  ID                        id-oc-cephalopoda }

crustacea OBJECT-CLASS ::= {
  SUBCLASS OF               { top }
  MUST CONTAIN              { species }
  MAY CONTAIN               { populationCount
                              | extinct
                              | commonName }
  LDAP-NAME                 {"crustacea"}
  LDAP-DESC                 "Crustaceans"
  ID                        id-oc-crustacea }
END
