-- Derived from data/ldap-schema/postfix.schema
-- This module is a container for LDAP schema. It has no module identifier.
-- X- extension fields from the LDAP schema are comments. USAGE userApplications and structural KIND are omitted because they are the defaults.
-- 7 elements were omitted because their OIDs are already defined. See CONVERSION-REPORT.txt.
LdapPostfix DEFINITIONS ::=
BEGIN

IMPORTS

  OBJECT-CLASS, top
    FROM InformationFramework
      {joint-iso-itu-t ds(5) module(1) informationFramework(1) 9} WITH SUCCESSORS

  commonName, description, member
    FROM SelectedAttributeTypes
      {joint-iso-itu-t ds(5) module(1) selectedAttributeTypes(5) 9} WITH SUCCESSORS

  mailRoutingAddress
    FROM InetMailSchema
      {iso(1) identified-organization(3) dod(6) internet(1) private(4) enterprise(1) wildboar(56490) module(1) inet-mail-schema(49)} WITH SUCCESSORS

  mail
    FROM LdapSchema2ldifCore ;

-- Object identifiers

id-oc-mailGroup OBJECT IDENTIFIER ::= { 1 3 6 1 4 1 15347 2 2 }

-- Object classes

mailGroup OBJECT-CLASS ::= {
  SUBCLASS OF               { top }
  MUST CONTAIN              { commonName
                              | mail }
  MAY CONTAIN               { mailRoutingAddress
                              | member
                              | description }
  LDAP-NAME                 {"mailGroup"}
  LDAP-DESC                 "E-Mail Group"
  ID                        id-oc-mailGroup }
END
