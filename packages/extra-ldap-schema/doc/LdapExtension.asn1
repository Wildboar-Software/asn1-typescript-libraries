-- Derived from data/ldap-schema/extension.schema
-- Upstream: https://github.com/identityxx/penrose-server/blob/b25edf727f6a26b18842a165b8f55fcdcbb91c9e/schema/extension.schema
-- This module is a container for LDAP schema. It has no module identifier.
-- X- extension fields from the LDAP schema are comments. USAGE userApplications and structural KIND are omitted because they are the defaults.
-- 2 elements share a numeric OID with another element that was also kept. See the comments on those elements.
-- LDAP {length} bounds on directory strings are DirectoryString{n}. Bounds on IA5String, PrintableString, NumericString, and OCTET STRING are SIZE (1..n). Other bounds stay comments because the LDAP figure is an encoded-length hint.
LdapExtension DEFINITIONS ::=
BEGIN

IMPORTS

  ATTRIBUTE, OBJECT-CLASS
    FROM InformationFramework
      {joint-iso-itu-t ds(5) module(1) informationFramework(1) 9} WITH SUCCESSORS

  caseIgnoreMatch, caseIgnoreSubstringsMatch, countryName, description,
    directoryString, DirectoryString, telephoneNumber
    FROM SelectedAttributeTypes
      {joint-iso-itu-t ds(5) module(1) selectedAttributeTypes(5) 9} WITH SUCCESSORS

  inetOrgPerson
    FROM InetOrgPerson
      {iso(1) identified-organization(3) dod(6) internet(1) private(4) enterprise(1) wildboar(56490) module(1) inetorgperson(5)} WITH SUCCESSORS

  manager, mobile, pager
    FROM LdapSchema2ldifCosine ;

-- Object identifiers

id-at-rdn OBJECT IDENTIFIER ::= { 1 3 6 1 4 1 4203 666 100 121 }
id-at-otherFacsimiletelephoneNumber OBJECT IDENTIFIER ::= { 1 3 6 1 4 1 4203 666 100 122 }
id-at-iPPhone OBJECT IDENTIFIER ::= { 1 3 6 1 4 1 4203 666 100 123 }
id-at-uRL OBJECT IDENTIFIER ::= { 1 3 6 1 4 1 4203 666 100 124 }
id-at-comment OBJECT IDENTIFIER ::= { 1 3 6 1 4 1 4203 666 100 125 }
id-at-conferenceInformation OBJECT IDENTIFIER ::= { 1 3 6 1 4 1 4203 666 100 126 }
id-at-reports OBJECT IDENTIFIER ::= { 1 3 6 1 4 1 4203 666 100 127 }
-- OID 1.3.6.1.4.1.4203.666.100.1 is also used by mlidNumber (ATTRIBUTE) in mailinglist.schema. The LDAP names differ, so each definition was kept.
id-oc-officePerson OBJECT IDENTIFIER ::= { 1 3 6 1 4 1 4203 666 100 1 }
id-at-xmozillanickname OBJECT IDENTIFIER ::= { 1 3 6 1 4 1 4203 666 100 151 }
id-at-xmozillausehtmlmail OBJECT IDENTIFIER ::= { 1 3 6 1 4 1 4203 666 100 152 }
-- OID 1.3.6.1.4.1.4203.666.100.5 is also used by mailinglistPublic (ATTRIBUTE) in mailinglist.schema. The LDAP names differ, so each definition was kept.
id-oc-zillaPerson OBJECT IDENTIFIER ::= { 1 3 6 1 4 1 4203 666 100 5 }

-- Attribute types

-- This attribute declares neither a supertype nor a syntax.
rdn ATTRIBUTE ::= {
  LDAP-NAME                 {"rdn"}
  ID                        id-at-rdn }

otherFacsimiletelephoneNumber ATTRIBUTE ::= {
  SUBTYPE OF                telephoneNumber
  LDAP-NAME                 {"otherFacsimiletelephoneNumber"}
  ID                        id-at-otherFacsimiletelephoneNumber }

-- initial capital of "IPPhone" lowercased so the assignment is a valuereference.
iPPhone ATTRIBUTE ::= {
  SUBTYPE OF                telephoneNumber
  LDAP-NAME                 {"IPPhone"}
  ID                        id-at-iPPhone }

-- initial capital of "URL" lowercased so the assignment is a valuereference.
-- This attribute declares neither a supertype nor a syntax.
uRL ATTRIBUTE ::= {
  LDAP-NAME                 {"URL", "homeUrl"}
  ID                        id-at-uRL }

-- This attribute declares neither a supertype nor a syntax.
comment ATTRIBUTE ::= {
  LDAP-NAME                 {"comment"}
  ID                        id-at-comment }

-- This attribute declares neither a supertype nor a syntax.
conferenceInformation ATTRIBUTE ::= {
  LDAP-NAME                 {"conferenceInformation"}
  ID                        id-at-conferenceInformation }

reports ATTRIBUTE ::= {
  SUBTYPE OF                manager
  LDAP-NAME                 {"reports"}
  ID                        id-at-reports }

-- LDAP syntax length {1024} rendered as DirectoryString{1024}.
xmozillanickname ATTRIBUTE ::= {
  WITH SYNTAX               DirectoryString{1024}
  EQUALITY MATCHING RULE    caseIgnoreMatch
  SUBSTRINGS MATCHING RULE  caseIgnoreSubstringsMatch
  LDAP-SYNTAX               directoryString.&id
  LDAP-NAME                 {"xmozillanickname"}
  ID                        id-at-xmozillanickname }

-- LDAP syntax length {64} rendered as DirectoryString{64}.
xmozillausehtmlmail ATTRIBUTE ::= {
  WITH SYNTAX               DirectoryString{64}
  EQUALITY MATCHING RULE    caseIgnoreMatch
  SUBSTRINGS MATCHING RULE  caseIgnoreSubstringsMatch
  LDAP-SYNTAX               directoryString.&id
  LDAP-NAME                 {"xmozillausehtmlmail"}
  ID                        id-at-xmozillausehtmlmail }

-- Object classes

-- OID 1.3.6.1.4.1.4203.666.100.1 is also used by mlidNumber (ATTRIBUTE) in mailinglist.schema. The LDAP names differ, so each definition was kept.
officePerson OBJECT-CLASS ::= {
  SUBCLASS OF               { inetOrgPerson }
  MAY CONTAIN               { countryName
                              | rdn
                              | otherFacsimiletelephoneNumber
                              | iPPhone
                              | uRL
                              | comment
                              | reports
                              | conferenceInformation }
  LDAP-NAME                 {"officePerson"}
  LDAP-DESC                 "Office employee or computer user"
  ID                        id-oc-officePerson }

-- OID 1.3.6.1.4.1.4203.666.100.5 is also used by mailinglistPublic (ATTRIBUTE) in mailinglist.schema. The LDAP names differ, so each definition was kept.
-- MAY cellPhone: LDAP name "cellPhone" was taken as mobile. extension.schema documents cellPhone as the cosine mobile attribute.
-- MAY pagerPhone: LDAP name "pagerPhone" was taken as pager. extension.schema documents pagerPhone as the cosine pager attribute.
-- MAY xmozillaanyphone: LDAP name "xmozillaanyphone" was taken as telephoneNumber. extension.schema documents xmozillaanyphone as core telephoneNumber.
zillaPerson OBJECT-CLASS ::= {
  SUBCLASS OF               { officePerson }
  MAY CONTAIN               { mobile
                              | pager
                              | description
                              | uRL
                              | telephoneNumber
                              | xmozillanickname
                              | xmozillausehtmlmail }
  LDAP-NAME                 {"zillaPerson"}
  LDAP-DESC                 "Netscape Communicator Extensions"
  ID                        id-oc-zillaPerson }
END
