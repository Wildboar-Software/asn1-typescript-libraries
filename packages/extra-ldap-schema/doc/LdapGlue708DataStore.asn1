-- Derived from data/ldap-schema/glue/7-08-DataStore.schema
-- Upstream: http://redmine.ogf.org/projects/glue-wg
-- This module is a container for LDAP schema. It has no module identifier.
-- X- extension fields from the LDAP schema are comments. USAGE userApplications and structural KIND are omitted because they are the defaults.
-- Object classes with no SUP were subclassed from top, the LDAP default (RFC 4512).
LdapGlue708DataStore DEFINITIONS ::=
BEGIN

IMPORTS

  ATTRIBUTE, OBJECT-CLASS, top
    FROM InformationFramework
      {joint-iso-itu-t ds(5) module(1) informationFramework(1) 9} WITH SUCCESSORS

  caseExactMatch, caseExactSubstringsMatch, directoryString, integer,
    integerMatch, integerOrderingMatch, UnboundedDirectoryString
    FROM SelectedAttributeTypes
      {joint-iso-itu-t ds(5) module(1) selectedAttributeTypes(5) 9} WITH SUCCESSORS ;

-- Object identifiers

id-at-gLUE2DataStoreType OBJECT IDENTIFIER ::= { 1 3 6 1 4 1 6757 100 1 1 34 1 }
id-at-gLUE2DataStoreLatency OBJECT IDENTIFIER ::= { 1 3 6 1 4 1 6757 100 1 1 34 2 }
id-at-gLUE2DataStoreTotalSize OBJECT IDENTIFIER ::= { 1 3 6 1 4 1 6757 100 1 1 34 3 }
id-at-gLUE2DataStoreFreeSize OBJECT IDENTIFIER ::= { 1 3 6 1 4 1 6757 100 1 1 34 4 }
id-at-gLUE2DataStoreUsedSize OBJECT IDENTIFIER ::= { 1 3 6 1 4 1 6757 100 1 1 34 5 }
id-at-gLUE2DataStoreStorageManagerForeignKey OBJECT IDENTIFIER ::= { 1 3 6 1 4 1 6757 100 1 1 34 6 }
id-oc-gLUE2DataStore OBJECT IDENTIFIER ::= { 1 3 6 1 4 1 6757 100 1 1 34 }

-- Attribute types

-- initial capital of "GLUE2DataStoreType" lowercased so the assignment is a valuereference.
gLUE2DataStoreType ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2DataStoreType"}
  LDAP-DESC                 "Type of storage resource"
  ID                        id-at-gLUE2DataStoreType }

-- initial capital of "GLUE2DataStoreLatency" lowercased so the assignment is a valuereference.
gLUE2DataStoreLatency ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2DataStoreLatency"}
  LDAP-DESC                 "The maximum latency category for a file stored in this resource to be made available for reading"
  ID                        id-at-gLUE2DataStoreLatency }

-- initial capital of "GLUE2DataStoreTotalSize" lowercased so the assignment is a valuereference.
gLUE2DataStoreTotalSize ATTRIBUTE ::= {
  WITH SYNTAX               INTEGER
  EQUALITY MATCHING RULE    integerMatch
  ORDERING MATCHING RULE    integerOrderingMatch
  SINGLE VALUE              TRUE
  LDAP-SYNTAX               integer.&id
  LDAP-NAME                 {"GLUE2DataStoreTotalSize"}
  LDAP-DESC                 "Size of storage extent"
  ID                        id-at-gLUE2DataStoreTotalSize }

-- initial capital of "GLUE2DataStoreFreeSize" lowercased so the assignment is a valuereference.
gLUE2DataStoreFreeSize ATTRIBUTE ::= {
  WITH SYNTAX               INTEGER
  EQUALITY MATCHING RULE    integerMatch
  ORDERING MATCHING RULE    integerOrderingMatch
  SINGLE VALUE              TRUE
  LDAP-SYNTAX               integer.&id
  LDAP-NAME                 {"GLUE2DataStoreFreeSize"}
  LDAP-DESC                 "Size of free storage extent"
  ID                        id-at-gLUE2DataStoreFreeSize }

-- initial capital of "GLUE2DataStoreUsedSize" lowercased so the assignment is a valuereference.
gLUE2DataStoreUsedSize ATTRIBUTE ::= {
  WITH SYNTAX               INTEGER
  EQUALITY MATCHING RULE    integerMatch
  ORDERING MATCHING RULE    integerOrderingMatch
  SINGLE VALUE              TRUE
  LDAP-SYNTAX               integer.&id
  LDAP-NAME                 {"GLUE2DataStoreUsedSize"}
  LDAP-DESC                 "Size of used storage extent"
  ID                        id-at-gLUE2DataStoreUsedSize }

-- initial capital of "GLUE2DataStoreStorageManagerForeignKey" lowercased so the assignment is a valuereference.
gLUE2DataStoreStorageManagerForeignKey ATTRIBUTE ::= {
  WITH SYNTAX               UnboundedDirectoryString
  EQUALITY MATCHING RULE    caseExactMatch
  SUBSTRINGS MATCHING RULE  caseExactSubstringsMatch
  SINGLE VALUE              TRUE
  LDAP-SYNTAX               directoryString.&id
  LDAP-NAME                 {"GLUE2DataStoreStorageManagerForeignKey"}
  LDAP-DESC                 "ForeignKey"
  ID                        id-at-gLUE2DataStoreStorageManagerForeignKey }

-- Object classes

-- initial capital of "GLUE2DataStore" lowercased so the assignment is a valuereference.
-- SUP was absent. RFC 4512 treats that as a subclass of top, so SUBCLASS OF { top } was added.
gLUE2DataStore OBJECT-CLASS ::= {
  SUBCLASS OF               { top }
  MUST CONTAIN              { gLUE2DataStoreType
                              | gLUE2DataStoreLatency }
  MAY CONTAIN               { gLUE2DataStoreTotalSize
                              | gLUE2DataStoreFreeSize
                              | gLUE2DataStoreUsedSize
                              | gLUE2DataStoreStorageManagerForeignKey }
  LDAP-NAME                 {"GLUE2DataStore"}
  LDAP-DESC                 "Abstraction of a sufficiently homogeneous storage device providing a storage capacity, managed by a local software component (storage manager), part of a storage service, reachable via one or more endpoints and having one or more shares defined on it. A storage resource refers to a category with summary information on the capacity"
  ID                        id-oc-gLUE2DataStore }
END
