-- Derived from data/ldap-schema/excision-mail.schema
-- Upstream: http://www.iana.org/assignments/enterprise-numbers
-- This module is a container for LDAP schema. It has no module identifier.
-- X- extension fields from the LDAP schema are comments. USAGE userApplications and structural KIND are omitted because they are the defaults.
LdapExcisionMail DEFINITIONS ::=
BEGIN

IMPORTS

  ATTRIBUTE, OBJECT-CLASS, top
    FROM InformationFramework
      {joint-iso-itu-t ds(5) module(1) informationFramework(1) 9} WITH SUCCESSORS

  boolean, booleanMatch, caseIgnoreIA5Match, caseIgnoreIA5SubstringsMatch,
    commonName, description, givenName, ia5String, integer, integerMatch,
    integerOrderingMatch, surname
    FROM SelectedAttributeTypes
      {joint-iso-itu-t ds(5) module(1) selectedAttributeTypes(5) 9} WITH SUCCESSORS

  userPassword
    FROM AuthenticationFramework
      {joint-iso-itu-t ds(5) module(1) authenticationFramework(7) 9} WITH SUCCESSORS

  memberURL
    FROM DynGroup
      {iso(1) identified-organization(3) dod(6) internet(1) private(4) enterprise(1) wildboar(56490) module(1) dyngroup(24)} WITH SUCCESSORS

  homeDirectory
    FROM NIS
      {iso(1) identified-organization(3) dod(6) internet(1) private(4) enterprise(1) wildboar(56490) module(1) nis(7)} WITH SUCCESSORS

  mail
    FROM LdapSchema2ldifCore ;

-- Object identifiers

id-at-backupAddress OBJECT IDENTIFIER ::= { 1 3 6 1 4 1 56133 1 100 1 1 }
id-at-aliasAddress OBJECT IDENTIFIER ::= { 1 3 6 1 4 1 56133 1 100 1 2 }
id-at-accountStatus OBJECT IDENTIFIER ::= { 1 3 6 1 4 1 56133 1 100 1 3 }
id-at-allowedNetwork OBJECT IDENTIFIER ::= { 1 3 6 1 4 1 56133 1 100 1 4 }
id-at-blockList OBJECT IDENTIFIER ::= { 1 3 6 1 4 1 56133 1 100 1 5 }
id-at-allowList OBJECT IDENTIFIER ::= { 1 3 6 1 4 1 56133 1 100 1 6 }
id-at-mailUID OBJECT IDENTIFIER ::= { 1 3 6 1 4 1 56133 1 100 2 1 }
id-at-mailGID OBJECT IDENTIFIER ::= { 1 3 6 1 4 1 56133 1 100 2 2 }
id-at-mailQuota OBJECT IDENTIFIER ::= { 1 3 6 1 4 1 56133 1 100 2 3 }
id-at-mailSetting OBJECT IDENTIFIER ::= { 1 3 6 1 4 1 56133 1 100 2 4 }
id-at-domainName OBJECT IDENTIFIER ::= { 1 3 6 1 4 1 56133 1 100 3 1 }
id-at-domainStatus OBJECT IDENTIFIER ::= { 1 3 6 1 4 1 56133 1 100 3 2 }
id-at-domainAdmin OBJECT IDENTIFIER ::= { 1 3 6 1 4 1 56133 1 100 3 3 }
id-at-domainDefaultQuota OBJECT IDENTIFIER ::= { 1 3 6 1 4 1 56133 1 100 3 4 }
id-oc-mailUser OBJECT IDENTIFIER ::= { 1 3 6 1 4 1 56133 1 200 1 }
id-oc-mailAlias OBJECT IDENTIFIER ::= { 1 3 6 1 4 1 56133 1 200 2 }
id-oc-mailList OBJECT IDENTIFIER ::= { 1 3 6 1 4 1 56133 1 200 3 }
id-oc-externalUser OBJECT IDENTIFIER ::= { 1 3 6 1 4 1 56133 1 200 4 }
id-oc-mailDomain OBJECT IDENTIFIER ::= { 1 3 6 1 4 1 56133 1 200 5 }

-- Attribute types

backupAddress ATTRIBUTE ::= {
  WITH SYNTAX               IA5String
  EQUALITY MATCHING RULE    caseIgnoreIA5Match
  SUBSTRINGS MATCHING RULE  caseIgnoreIA5SubstringsMatch
  LDAP-SYNTAX               ia5String.&id
  LDAP-NAME                 {"backupAddress"}
  LDAP-DESC                 "Backup mail address, e.g. used for password reset"
  ID                        id-at-backupAddress }

aliasAddress ATTRIBUTE ::= {
  WITH SYNTAX               IA5String
  EQUALITY MATCHING RULE    caseIgnoreIA5Match
  SUBSTRINGS MATCHING RULE  caseIgnoreIA5SubstringsMatch
  LDAP-SYNTAX               ia5String.&id
  LDAP-NAME                 {"aliasAddress"}
  LDAP-DESC                 "Alias mail addresses allowed for a user"
  ID                        id-at-aliasAddress }

accountStatus ATTRIBUTE ::= {
  WITH SYNTAX               BOOLEAN
  EQUALITY MATCHING RULE    booleanMatch
  LDAP-SYNTAX               boolean.&id
  LDAP-NAME                 {"accountStatus"}
  LDAP-DESC                 "Status of an account: true - enabled, false - disabled"
  ID                        id-at-accountStatus }

allowedNetwork ATTRIBUTE ::= {
  WITH SYNTAX               IA5String
  EQUALITY MATCHING RULE    caseIgnoreIA5Match
  SUBSTRINGS MATCHING RULE  caseIgnoreIA5SubstringsMatch
  LDAP-SYNTAX               ia5String.&id
  LDAP-NAME                 {"allowedNetwork"}
  LDAP-DESC                 "Networks/IPs allowed for a user to connect via"
  ID                        id-at-allowedNetwork }

blockList ATTRIBUTE ::= {
  WITH SYNTAX               IA5String
  EQUALITY MATCHING RULE    caseIgnoreIA5Match
  SUBSTRINGS MATCHING RULE  caseIgnoreIA5SubstringsMatch
  LDAP-SYNTAX               ia5String.&id
  LDAP-NAME                 {"blockList"}
  LDAP-DESC                 "List of sender addresses/IPs from which to block mail"
  ID                        id-at-blockList }

allowList ATTRIBUTE ::= {
  WITH SYNTAX               IA5String
  EQUALITY MATCHING RULE    caseIgnoreIA5Match
  SUBSTRINGS MATCHING RULE  caseIgnoreIA5SubstringsMatch
  LDAP-SYNTAX               ia5String.&id
  LDAP-NAME                 {"allowList"}
  LDAP-DESC                 "List of sender addresses/IPs from which to allow mail"
  ID                        id-at-allowList }

mailUID ATTRIBUTE ::= {
  WITH SYNTAX               INTEGER
  EQUALITY MATCHING RULE    integerMatch
  ORDERING MATCHING RULE    integerOrderingMatch
  LDAP-SYNTAX               integer.&id
  LDAP-NAME                 {"mailUID"}
  LDAP-DESC                 "UID number of a user"
  ID                        id-at-mailUID }

mailGID ATTRIBUTE ::= {
  WITH SYNTAX               INTEGER
  EQUALITY MATCHING RULE    integerMatch
  ORDERING MATCHING RULE    integerOrderingMatch
  LDAP-SYNTAX               integer.&id
  LDAP-NAME                 {"mailGID"}
  LDAP-DESC                 "GID number of a user"
  ID                        id-at-mailGID }

mailQuota ATTRIBUTE ::= {
  WITH SYNTAX               INTEGER
  EQUALITY MATCHING RULE    integerMatch
  ORDERING MATCHING RULE    integerOrderingMatch
  LDAP-SYNTAX               integer.&id
  LDAP-NAME                 {"mailQuota"}
  LDAP-DESC                 "Maximum space allowed for a user"
  ID                        id-at-mailQuota }

mailSetting ATTRIBUTE ::= {
  WITH SYNTAX               IA5String
  EQUALITY MATCHING RULE    caseIgnoreIA5Match
  SUBSTRINGS MATCHING RULE  caseIgnoreIA5SubstringsMatch
  LDAP-SYNTAX               ia5String.&id
  LDAP-NAME                 {"mailSetting"}
  LDAP-DESC                 "Additional settings for a user, format key=val"
  ID                        id-at-mailSetting }

domainName ATTRIBUTE ::= {
  WITH SYNTAX               IA5String
  EQUALITY MATCHING RULE    caseIgnoreIA5Match
  SUBSTRINGS MATCHING RULE  caseIgnoreIA5SubstringsMatch
  LDAP-SYNTAX               ia5String.&id
  LDAP-NAME                 {"domainName"}
  LDAP-DESC                 "Virtual domain name"
  ID                        id-at-domainName }

domainStatus ATTRIBUTE ::= {
  WITH SYNTAX               BOOLEAN
  EQUALITY MATCHING RULE    booleanMatch
  LDAP-SYNTAX               boolean.&id
  LDAP-NAME                 {"domainStatus"}
  LDAP-DESC                 "Status of a virtual domain: true - enabled, false - disabled"
  ID                        id-at-domainStatus }

domainAdmin ATTRIBUTE ::= {
  WITH SYNTAX               IA5String
  EQUALITY MATCHING RULE    caseIgnoreIA5Match
  SUBSTRINGS MATCHING RULE  caseIgnoreIA5SubstringsMatch
  LDAP-SYNTAX               ia5String.&id
  LDAP-NAME                 {"domainAdmin"}
  LDAP-DESC                 "Virtual domain admin"
  ID                        id-at-domainAdmin }

domainDefaultQuota ATTRIBUTE ::= {
  WITH SYNTAX               INTEGER
  EQUALITY MATCHING RULE    integerMatch
  ORDERING MATCHING RULE    integerOrderingMatch
  LDAP-SYNTAX               integer.&id
  LDAP-NAME                 {"domainDefaultQuota"}
  LDAP-DESC                 "Default quota per user for a virtual domain"
  ID                        id-at-domainDefaultQuota }

-- Object classes

-- MAY gn: LDAP name "gn" was taken as givenName. schema2ldif/core.schema lists it on 2.5.4.42, which is already givenName in SelectedAttributeTypes.
mailUser OBJECT-CLASS ::= {
  SUBCLASS OF               { top }
  MUST CONTAIN              { mail }
  MAY CONTAIN               { commonName
                              | givenName
                              | surname
                              | userPassword
                              | homeDirectory
                              | mailUID
                              | mailGID
                              | mailQuota
                              | mailSetting
                              | aliasAddress
                              | backupAddress
                              | accountStatus
                              | allowedNetwork
                              | allowList
                              | blockList }
  LDAP-NAME                 {"mailUser"}
  LDAP-DESC                 "Abstraction of a mail user"
  ID                        id-oc-mailUser }

mailAlias OBJECT-CLASS ::= {
  SUBCLASS OF               { top }
  MUST CONTAIN              { mail }
  MAY CONTAIN               { mailSetting
                              | accountStatus }
  LDAP-NAME                 {"mailAlias"}
  LDAP-DESC                 "Abstraction of a mail alias"
  ID                        id-oc-mailAlias }

mailList OBJECT-CLASS ::= {
  SUBCLASS OF               { top }
  MUST CONTAIN              { mail }
  MAY CONTAIN               { description
                              | memberURL
                              | accountStatus
                              | blockList
                              | allowList
                              | mailSetting }
  LDAP-NAME                 {"mailList"}
  LDAP-DESC                 "Abstraction of a mailing list"
  ID                        id-oc-mailList }

-- MAY gn: LDAP name "gn" was taken as givenName. schema2ldif/core.schema lists it on 2.5.4.42, which is already givenName in SelectedAttributeTypes.
externalUser OBJECT-CLASS ::= {
  SUBCLASS OF               { top }
  MUST CONTAIN              { mail }
  MAY CONTAIN               { commonName
                              | givenName
                              | surname
                              | mailSetting
                              | accountStatus }
  LDAP-NAME                 {"externalUser"}
  LDAP-DESC                 "Abstraction of an external user"
  ID                        id-oc-externalUser }

mailDomain OBJECT-CLASS ::= {
  SUBCLASS OF               { top }
  MUST CONTAIN              { domainName }
  MAY CONTAIN               { blockList
                              | allowList
                              | domainAdmin
                              | domainStatus
                              | domainDefaultQuota }
  LDAP-NAME                 {"mailDomain"}
  LDAP-DESC                 "Virtual mail domain"
  ID                        id-oc-mailDomain }
END
