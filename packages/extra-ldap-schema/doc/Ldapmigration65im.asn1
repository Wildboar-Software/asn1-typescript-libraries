-- Derived from data/ldap-schema/ldapmigration/65im.ldif
-- This module is a container for LDAP schema. It has no module identifier.
-- X- extension fields from the LDAP schema are comments. USAGE userApplications and structural KIND are omitted because they are the defaults.
Ldapmigration65im DEFINITIONS ::=
BEGIN

IMPORTS

  ATTRIBUTE, OBJECT-CLASS, top
    FROM InformationFramework
      {joint-iso-itu-t ds(5) module(1) informationFramework(1) 9} WITH SUCCESSORS

  commonName, directoryString, uid, UnboundedDirectoryString
    FROM SelectedAttributeTypes
      {joint-iso-itu-t ds(5) module(1) selectedAttributeTypes(5) 9} WITH SUCCESSORS ;

-- Object identifiers

id-at-sunPresenceUserPrivacy OBJECT IDENTIFIER ::= { 1 3 6 1 4 1 42 2 27 9 1 753 }
id-at-sunPresenceEntityDefaultAccess OBJECT IDENTIFIER ::= { 1 3 6 1 4 1 42 2 27 9 1 754 }
id-at-sunPresenceEntityAccessDenied OBJECT IDENTIFIER ::= { 1 3 6 1 4 1 42 2 27 9 1 755 }
id-at-sunPresenceEntityAccessPermitted OBJECT IDENTIFIER ::= { 1 3 6 1 4 1 42 2 27 9 1 756 }
id-at-sunPresenceEntityDevices OBJECT IDENTIFIER ::= { 1 3 6 1 4 1 42 2 27 9 1 757 }
id-at-sunPresencePrivacy OBJECT IDENTIFIER ::= { 1 3 6 1 4 1 42 2 27 9 1 758 }
id-at-sunPresenceDefaultAccess OBJECT IDENTIFIER ::= { 1 3 6 1 4 1 42 2 27 9 1 759 }
id-at-sunPresenceAccessDenied OBJECT IDENTIFIER ::= { 1 3 6 1 4 1 42 2 27 9 1 760 }
id-at-sunPresenceAccessPermitted OBJECT IDENTIFIER ::= { 1 3 6 1 4 1 42 2 27 9 1 761 }
id-at-sunPresenceDevices OBJECT IDENTIFIER ::= { 1 3 6 1 4 1 42 2 27 9 1 762 }
id-at-sunIMUserPrivateSettings OBJECT IDENTIFIER ::= { 1 3 6 1 4 1 42 2 27 9 1 763 }
id-at-sunIMUserProperties OBJECT IDENTIFIER ::= { 1 3 6 1 4 1 42 2 27 9 1 764 }
id-at-sunIMUserRoster OBJECT IDENTIFIER ::= { 1 3 6 1 4 1 42 2 27 9 1 765 }
id-at-sunIMUserConferenceRoster OBJECT IDENTIFIER ::= { 1 3 6 1 4 1 42 2 27 9 1 766 }
id-at-sunIMUserNewsRoster OBJECT IDENTIFIER ::= { 1 3 6 1 4 1 42 2 27 9 1 767 }
id-at-sunIMPrivateSettings OBJECT IDENTIFIER ::= { 1 3 6 1 4 1 42 2 27 9 1 768 }
id-at-sunIMProperties OBJECT IDENTIFIER ::= { 1 3 6 1 4 1 42 2 27 9 1 769 }
id-at-sunIMRoster OBJECT IDENTIFIER ::= { 1 3 6 1 4 1 42 2 27 9 1 770 }
id-at-sunIMConferenceRoster OBJECT IDENTIFIER ::= { 1 3 6 1 4 1 42 2 27 9 1 771 }
id-at-sunIMNewsRoster OBJECT IDENTIFIER ::= { 1 3 6 1 4 1 42 2 27 9 1 772 }
id-at-sunIMConferenceAffiliations OBJECT IDENTIFIER ::= { 1 3 6 1 4 1 42 2 27 9 1 773 }
id-at-sunIMConferenceConfiguration OBJECT IDENTIFIER ::= { 1 3 6 1 4 1 42 2 27 9 1 774 }
id-at-sunIMNewsAffiliations OBJECT IDENTIFIER ::= { 1 3 6 1 4 1 42 2 27 9 1 775 }
id-at-sunIMNewsConfiguration OBJECT IDENTIFIER ::= { 1 3 6 1 4 1 42 2 27 9 1 776 }
id-at-sunIMMessageID OBJECT IDENTIFIER ::= { 1 3 6 1 4 1 42 2 27 9 1 777 }
id-at-sunIMMessageContent OBJECT IDENTIFIER ::= { 1 3 6 1 4 1 42 2 27 9 1 778 }
id-at-sunIMNewsMetaData OBJECT IDENTIFIER ::= { 1 3 6 1 4 1 42 2 27 9 1 799 }
id-oc-sunPresenceUser OBJECT IDENTIFIER ::= { 1 3 6 1 4 1 42 2 27 9 2 105 }
id-oc-sunIMUser OBJECT IDENTIFIER ::= { 1 3 6 1 4 1 42 2 27 9 2 106 }
id-oc-sunIMConference OBJECT IDENTIFIER ::= { 1 3 6 1 4 1 42 2 27 9 2 107 }
id-oc-sunIMNews OBJECT IDENTIFIER ::= { 1 3 6 1 4 1 42 2 27 9 2 108 }
id-oc-sunIMStoredMessage OBJECT IDENTIFIER ::= { 1 3 6 1 4 1 42 2 27 9 2 109 }

-- Attribute types

-- X-ORIGIN: "Sun Microsystems"
sunPresenceUserPrivacy ATTRIBUTE ::= {
  WITH SYNTAX               UnboundedDirectoryString
  LDAP-SYNTAX               directoryString.&id
  LDAP-NAME                 {"sunPresenceUserPrivacy"}
  LDAP-DESC                 "XMPP Privacy Profiles"
  OBSOLETE                  TRUE
  ID                        id-at-sunPresenceUserPrivacy }

-- X-ORIGIN: "Sun Microsystems"
sunPresenceEntityDefaultAccess ATTRIBUTE ::= {
  WITH SYNTAX               UnboundedDirectoryString
  LDAP-SYNTAX               directoryString.&id
  LDAP-NAME                 {"sunPresenceEntityDefaultAccess"}
  LDAP-DESC                 "Default Outgoing Presence Access"
  OBSOLETE                  TRUE
  ID                        id-at-sunPresenceEntityDefaultAccess }

-- X-ORIGIN: "Sun Microsystems"
sunPresenceEntityAccessDenied ATTRIBUTE ::= {
  WITH SYNTAX               UnboundedDirectoryString
  LDAP-SYNTAX               directoryString.&id
  LDAP-NAME                 {"sunPresenceEntityAccessDenied"}
  LDAP-DESC                 "Entities Denied Access to Outgoing Presence"
  OBSOLETE                  TRUE
  ID                        id-at-sunPresenceEntityAccessDenied }

-- X-ORIGIN: "Sun Microsystems"
sunPresenceEntityAccessPermitted ATTRIBUTE ::= {
  WITH SYNTAX               UnboundedDirectoryString
  LDAP-SYNTAX               directoryString.&id
  LDAP-NAME                 {"sunPresenceEntityAccessPermitted"}
  LDAP-DESC                 "Entities Permitted Access to Outgoing Presence"
  OBSOLETE                  TRUE
  ID                        id-at-sunPresenceEntityAccessPermitted }

-- X-ORIGIN: "Sun ONE Identity Management"
sunPresenceEntityDevices ATTRIBUTE ::= {
  WITH SYNTAX               UnboundedDirectoryString
  LDAP-SYNTAX               directoryString.&id
  LDAP-NAME                 {"sunPresenceEntityDevices"}
  LDAP-DESC                 "Presence Agent List"
  ID                        id-at-sunPresenceEntityDevices }

-- X-ORIGIN: "Sun Microsystems"
sunPresencePrivacy ATTRIBUTE ::= {
  WITH SYNTAX               UnboundedDirectoryString
  LDAP-SYNTAX               directoryString.&id
  LDAP-NAME                 {"sunPresencePrivacy"}
  LDAP-DESC                 "Admin-Managed XMPP Privacy Profile"
  ID                        id-at-sunPresencePrivacy }

-- X-ORIGIN: "Sun Microsystems"
sunPresenceDefaultAccess ATTRIBUTE ::= {
  WITH SYNTAX               UnboundedDirectoryString
  LDAP-SYNTAX               directoryString.&id
  LDAP-NAME                 {"sunPresenceDefaultAccess"}
  LDAP-DESC                 "Admin-Managed Default Outgoing Presence Access"
  OBSOLETE                  TRUE
  ID                        id-at-sunPresenceDefaultAccess }

-- X-ORIGIN: "Sun Microsystems"
sunPresenceAccessDenied ATTRIBUTE ::= {
  WITH SYNTAX               UnboundedDirectoryString
  LDAP-SYNTAX               directoryString.&id
  LDAP-NAME                 {"sunPresenceAccessDenied"}
  LDAP-DESC                 "Admin-Managed Entities Denied Access to Outgoing Presence"
  OBSOLETE                  TRUE
  ID                        id-at-sunPresenceAccessDenied }

-- X-ORIGIN: "Sun Microsystems"
sunPresenceAccessPermitted ATTRIBUTE ::= {
  WITH SYNTAX               UnboundedDirectoryString
  LDAP-SYNTAX               directoryString.&id
  LDAP-NAME                 {"sunPresenceAccessPermitted"}
  LDAP-DESC                 "Admin-managed Entities Permitted Access to Outgoing Presence"
  OBSOLETE                  TRUE
  ID                        id-at-sunPresenceAccessPermitted }

-- X-ORIGIN: "Sun Microsystems"
sunPresenceDevices ATTRIBUTE ::= {
  WITH SYNTAX               UnboundedDirectoryString
  LDAP-SYNTAX               directoryString.&id
  LDAP-NAME                 {"sunPresenceDevices"}
  LDAP-DESC                 "Admin-managed Presence Agents"
  ID                        id-at-sunPresenceDevices }

-- X-ORIGIN: "Sun Microsystems"
sunIMUserPrivateSettings ATTRIBUTE ::= {
  WITH SYNTAX               UnboundedDirectoryString
  LDAP-SYNTAX               directoryString.&id
  LDAP-NAME                 {"sunIMUserPrivateSettings"}
  LDAP-DESC                 "Instant Messenger properties"
  ID                        id-at-sunIMUserPrivateSettings }

-- X-ORIGIN: "Sun Microsystems"
sunIMUserProperties ATTRIBUTE ::= {
  WITH SYNTAX               UnboundedDirectoryString
  LDAP-SYNTAX               directoryString.&id
  LDAP-NAME                 {"sunIMUserProperties"}
  LDAP-DESC                 "Instant Messenger Properties"
  OBSOLETE                  TRUE
  ID                        id-at-sunIMUserProperties }

-- X-ORIGIN: "Sun Microsystems"
sunIMUserRoster ATTRIBUTE ::= {
  WITH SYNTAX               UnboundedDirectoryString
  LDAP-SYNTAX               directoryString.&id
  LDAP-NAME                 {"sunIMUserRoster"}
  LDAP-DESC                 "XMPP Contact List"
  ID                        id-at-sunIMUserRoster }

-- X-ORIGIN: "Sun Microsystems"
sunIMUserConferenceRoster ATTRIBUTE ::= {
  WITH SYNTAX               UnboundedDirectoryString
  LDAP-SYNTAX               directoryString.&id
  LDAP-NAME                 {"sunIMUserConferenceRoster"}
  LDAP-DESC                 "Conference Subscriptions"
  ID                        id-at-sunIMUserConferenceRoster }

-- X-ORIGIN: "Sun Microsystems"
sunIMUserNewsRoster ATTRIBUTE ::= {
  WITH SYNTAX               UnboundedDirectoryString
  LDAP-SYNTAX               directoryString.&id
  LDAP-NAME                 {"sunIMUserNewsRoster"}
  LDAP-DESC                 "Pubsub Channel Subscriptions"
  ID                        id-at-sunIMUserNewsRoster }

-- X-ORIGIN: "Sun Microsystems"
sunIMPrivateSettings ATTRIBUTE ::= {
  WITH SYNTAX               UnboundedDirectoryString
  LDAP-SYNTAX               directoryString.&id
  LDAP-NAME                 {"sunIMPrivateSettings"}
  LDAP-DESC                 "Admin-managed Instant Messenger properties"
  ID                        id-at-sunIMPrivateSettings }

-- X-ORIGIN: "Sun Microsystems"
sunIMProperties ATTRIBUTE ::= {
  WITH SYNTAX               UnboundedDirectoryString
  LDAP-SYNTAX               directoryString.&id
  LDAP-NAME                 {"sunIMProperties"}
  LDAP-DESC                 "Admin-Managed Instant Messenger Properties"
  OBSOLETE                  TRUE
  ID                        id-at-sunIMProperties }

-- X-ORIGIN: "Sun Microsystems"
sunIMRoster ATTRIBUTE ::= {
  WITH SYNTAX               UnboundedDirectoryString
  LDAP-SYNTAX               directoryString.&id
  LDAP-NAME                 {"sunIMRoster"}
  LDAP-DESC                 "Admin-managed Contact List"
  ID                        id-at-sunIMRoster }

-- X-ORIGIN: "Sun Microsystems"
sunIMConferenceRoster ATTRIBUTE ::= {
  WITH SYNTAX               UnboundedDirectoryString
  LDAP-SYNTAX               directoryString.&id
  LDAP-NAME                 {"sunIMConferenceRoster"}
  LDAP-DESC                 "admin-managed Conference Subscriptions"
  ID                        id-at-sunIMConferenceRoster }

-- X-ORIGIN: "Sun Microsystems"
sunIMNewsRoster ATTRIBUTE ::= {
  WITH SYNTAX               UnboundedDirectoryString
  LDAP-SYNTAX               directoryString.&id
  LDAP-NAME                 {"sunIMNewsRoster"}
  LDAP-DESC                 "Admin-managed Pubsub Channel subscriptions"
  ID                        id-at-sunIMNewsRoster }

-- X-ORIGIN: "Sun Microsystems"
sunIMConferenceAffiliations ATTRIBUTE ::= {
  WITH SYNTAX               UnboundedDirectoryString
  LDAP-SYNTAX               directoryString.&id
  LDAP-NAME                 {"sunIMConferenceAffiliations"}
  LDAP-DESC                 "XMPP Conference Affiliations"
  ID                        id-at-sunIMConferenceAffiliations }

-- X-ORIGIN: "Sun Microsystems"
sunIMConferenceConfiguration ATTRIBUTE ::= {
  WITH SYNTAX               UnboundedDirectoryString
  LDAP-SYNTAX               directoryString.&id
  LDAP-NAME                 {"sunIMConferenceConfiguration"}
  LDAP-DESC                 "XMPP Conference Configuration"
  ID                        id-at-sunIMConferenceConfiguration }

-- X-ORIGIN: "Sun Microsystems"
sunIMNewsAffiliations ATTRIBUTE ::= {
  WITH SYNTAX               UnboundedDirectoryString
  LDAP-SYNTAX               directoryString.&id
  LDAP-NAME                 {"sunIMNewsAffiliations"}
  LDAP-DESC                 "XMPP Pubsub Channel Affiliations"
  ID                        id-at-sunIMNewsAffiliations }

-- X-ORIGIN: "Sun Microsystems"
sunIMNewsConfiguration ATTRIBUTE ::= {
  WITH SYNTAX               UnboundedDirectoryString
  LDAP-SYNTAX               directoryString.&id
  LDAP-NAME                 {"sunIMNewsConfiguration"}
  LDAP-DESC                 "XMPP Pubsub Channel Configuration"
  ID                        id-at-sunIMNewsConfiguration }

-- X-ORIGIN: "Sun Microsystems"
sunIMMessageID ATTRIBUTE ::= {
  WITH SYNTAX               UnboundedDirectoryString
  LDAP-SYNTAX               directoryString.&id
  LDAP-NAME                 {"sunIMMessageID"}
  LDAP-DESC                 "XMPP Message ID"
  ID                        id-at-sunIMMessageID }

-- X-ORIGIN: "Sun Microsystems"
sunIMMessageContent ATTRIBUTE ::= {
  WITH SYNTAX               UnboundedDirectoryString
  LDAP-SYNTAX               directoryString.&id
  LDAP-NAME                 {"sunIMMessageContent"}
  LDAP-DESC                 "XMPP Message Content"
  ID                        id-at-sunIMMessageContent }

-- X-ORIGIN: "Sun Microsystems"
sunIMNewsMetaData ATTRIBUTE ::= {
  WITH SYNTAX               UnboundedDirectoryString
  LDAP-SYNTAX               directoryString.&id
  LDAP-NAME                 {"sunIMNewsMetaData"}
  LDAP-DESC                 "XMPP Pubsub Channel Meta-Data"
  ID                        id-at-sunIMNewsMetaData }

-- Object classes

-- X-ORIGIN: "Sun Microsystems"
sunPresenceUser OBJECT-CLASS ::= {
  SUBCLASS OF               { top }
  KIND                      auxiliary
  MAY CONTAIN               { sunPresenceUserPrivacy
                              | sunPresenceEntityDefaultAccess
                              | sunPresenceEntityAccessDenied
                              | sunPresenceEntityAccessPermitted
                              | sunPresenceEntityDevices
                              | sunPresencePrivacy
                              | sunPresenceDefaultAccess
                              | sunPresenceAccessDenied
                              | sunPresenceAccessPermitted
                              | sunPresenceDevices }
  LDAP-NAME                 {"sunPresenceUser"}
  LDAP-DESC                 "Presence Service User"
  ID                        id-oc-sunPresenceUser }

-- X-ORIGIN: "Sun Microsystems"
sunIMUser OBJECT-CLASS ::= {
  SUBCLASS OF               { top }
  KIND                      auxiliary
  MAY CONTAIN               { sunIMUserPrivateSettings
                              | sunIMUserProperties
                              | sunIMUserRoster
                              | sunIMUserConferenceRoster
                              | sunIMUserNewsRoster
                              | sunIMPrivateSettings
                              | sunIMProperties
                              | sunIMRoster
                              | sunIMConferenceRoster
                              | sunIMNewsRoster }
  LDAP-NAME                 {"sunIMUser"}
  LDAP-DESC                 "Instant Message Service User"
  ID                        id-oc-sunIMUser }

-- X-ORIGIN: "Sun Microsystems"
sunIMConference OBJECT-CLASS ::= {
  SUBCLASS OF               { top }
  KIND                      auxiliary
  MAY CONTAIN               { sunIMConferenceAffiliations
                              | sunIMConferenceConfiguration
                              | commonName
                              | uid }
  LDAP-NAME                 {"sunIMConference"}
  LDAP-DESC                 "Conference Object"
  ID                        id-oc-sunIMConference }

-- X-ORIGIN: "Sun Microsystems"
sunIMNews OBJECT-CLASS ::= {
  SUBCLASS OF               { top }
  KIND                      auxiliary
  MAY CONTAIN               { sunIMNewsAffiliations
                              | sunIMNewsConfiguration
                              | sunIMNewsMetaData
                              | commonName
                              | uid }
  LDAP-NAME                 {"sunIMNews"}
  LDAP-DESC                 "Pubsub Channel Object"
  ID                        id-oc-sunIMNews }

-- X-ORIGIN: "Sun Microsystems"
sunIMStoredMessage OBJECT-CLASS ::= {
  SUBCLASS OF               { top }
  KIND                      auxiliary
  MAY CONTAIN               { sunIMMessageID
                              | sunIMMessageContent }
  LDAP-NAME                 {"sunIMStoredMessage"}
  LDAP-DESC                 "Stored Message Object"
  ID                        id-oc-sunIMStoredMessage }
END
