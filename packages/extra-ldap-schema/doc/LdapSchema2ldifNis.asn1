-- Derived from data/ldap-schema/schema2ldif/nis.schema
-- Upstream: http://www.openldap.org/
-- This module is a container for LDAP schema. It has no module identifier.
-- X- extension fields from the LDAP schema are comments. USAGE userApplications and structural KIND are omitted because they are the defaults.
-- 39 elements were omitted because their OIDs are already defined. See CONVERSION-REPORT.txt.
LdapSchema2ldifNis DEFINITIONS ::=
BEGIN

IMPORTS

  ATTRIBUTE
    FROM InformationFramework
      {joint-iso-itu-t ds(5) module(1) informationFramework(1) 9} WITH SUCCESSORS

  caseExactMatch, directoryString, UnboundedDirectoryString
    FROM SelectedAttributeTypes
      {joint-iso-itu-t ds(5) module(1) selectedAttributeTypes(5) 9} WITH SUCCESSORS ;

-- Object identifiers

id-at-homeDirectory OBJECT IDENTIFIER ::= { 1 3 6 1 4 1 63 1000 1 1 1 1 99 }

-- Attribute types

homeDirectory ATTRIBUTE ::= {
  WITH SYNTAX               UnboundedDirectoryString
  EQUALITY MATCHING RULE    caseExactMatch
  SINGLE VALUE              TRUE
  LDAP-SYNTAX               directoryString.&id
  LDAP-NAME                 {"homeDirectory"}
  LDAP-DESC                 "The absolute path to the home directory"
  ID                        id-at-homeDirectory }
END
