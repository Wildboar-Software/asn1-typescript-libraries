-- Derived from data/ldap-schema/ox.ldif
-- This module is a container for LDAP schema. It has no module identifier.
-- X- extension fields from the LDAP schema are comments. USAGE userApplications and structural KIND are omitted because they are the defaults.
LdapOx DEFINITIONS ::=
BEGIN

IMPORTS

  ATTRIBUTE, DistinguishedName, distinguishedNameMatch, OBJECT-CLASS,
    objectClass, top
    FROM InformationFramework
      {joint-iso-itu-t ds(5) module(1) informationFramework(1) 9} WITH SUCCESSORS

  boolean, booleanMatch, caseExactMatch, caseExactSubstringsMatch,
    caseIgnoreMatch, caseIgnoreSubstringsMatch, commonName, countryName,
    description, directoryString, dn, generalizedTime, generalizedTimeMatch,
    generalizedTimeOrderingMatch, givenName, integer, integerMatch,
    localityName, member, organizationalUnitName, organizationName, owner,
    postalCode, seeAlso, stateOrProvinceName, streetAddress, surname,
    telephoneNumber, title, uid, UnboundedDirectoryString, uniqueIdentifier
    FROM SelectedAttributeTypes
      {joint-iso-itu-t ds(5) module(1) selectedAttributeTypes(5) 9} WITH SUCCESSORS

  userCertificate, userPassword
    FROM AuthenticationFramework
      {joint-iso-itu-t ds(5) module(1) authenticationFramework(7) 9} WITH SUCCESSORS

  displayName, preferredLanguage
    FROM InetOrgPerson
      {iso(1) identified-organization(3) dod(6) internet(1) private(4) enterprise(1) wildboar(56490) module(1) inetorgperson(5)} WITH SUCCESSORS

  mail
    FROM LdapSchema2ldifCore ;

-- Object identifiers

id-at-oxAssociatedClient OBJECT IDENTIFIER ::= { 1 3 6 1 4 1 48710 1 3 1 }
id-at-associatedPerson OBJECT IDENTIFIER ::= { 1 3 6 1 4 1 48710 1 3 2 }
id-at-blowfishPassword OBJECT IDENTIFIER ::= { 1 3 6 1 4 1 48710 1 3 3 }
id-at-county OBJECT IDENTIFIER ::= { 1 3 6 1 4 1 48710 1 3 4 }
id-at-creationDate OBJECT IDENTIFIER ::= { 1 3 6 1 4 1 48710 1 3 5 }
id-at-defaultScope OBJECT IDENTIFIER ::= { 1 3 6 1 4 1 48710 1 3 6 }
id-at-deployedAppliances OBJECT IDENTIFIER ::= { 1 3 6 1 4 1 48710 1 3 7 }
id-at-federationRules OBJECT IDENTIFIER ::= { 1 3 6 1 4 1 48710 1 3 8 }
id-at-gluuAddPersonCapability OBJECT IDENTIFIER ::= { 1 3 6 1 4 1 48710 1 3 9 }
id-at-gluuAdditionalBandwidth OBJECT IDENTIFIER ::= { 1 3 6 1 4 1 48710 1 3 10 }
id-at-gluuAdditionalMemory OBJECT IDENTIFIER ::= { 1 3 6 1 4 1 48710 1 3 11 }
id-at-gluuAdditionalUsers OBJECT IDENTIFIER ::= { 1 3 6 1 4 1 48710 1 3 12 }
id-at-gluuApplianceDnsServer OBJECT IDENTIFIER ::= { 1 3 6 1 4 1 48710 1 3 13 }
id-at-gluuAppliancePollingInterval OBJECT IDENTIFIER ::= { 1 3 6 1 4 1 48710 1 3 14 }
id-at-gluuApplianceUpdateRequestList OBJECT IDENTIFIER ::= { 1 3 6 1 4 1 48710 1 3 15 }
id-at-gluuAttributeViewType OBJECT IDENTIFIER ::= { 1 3 6 1 4 1 48710 1 3 16 }
id-at-gluuAttributeEditType OBJECT IDENTIFIER ::= { 1 3 6 1 4 1 48710 1 3 17 }
id-at-gluuAttributeName OBJECT IDENTIFIER ::= { 1 3 6 1 4 1 48710 1 3 18 }
id-at-gluuAttributeOrigin OBJECT IDENTIFIER ::= { 1 3 6 1 4 1 48710 1 3 19 }
id-at-gluuAttributeSystemEditType OBJECT IDENTIFIER ::= { 1 3 6 1 4 1 48710 1 3 20 }
id-at-gluuAttributeType OBJECT IDENTIFIER ::= { 1 3 6 1 4 1 48710 1 3 21 }
id-at-gluuAttributeUsageType OBJECT IDENTIFIER ::= { 1 3 6 1 4 1 48710 1 3 22 }
id-at-gluuBandwidthRX OBJECT IDENTIFIER ::= { 1 3 6 1 4 1 48710 1 3 23 }
id-at-gluuBandwidthTX OBJECT IDENTIFIER ::= { 1 3 6 1 4 1 48710 1 3 24 }
id-at-gluuCategory OBJECT IDENTIFIER ::= { 1 3 6 1 4 1 48710 1 3 25 }
id-at-gluuContainerFederation OBJECT IDENTIFIER ::= { 1 3 6 1 4 1 48710 1 3 26 }
id-at-gluuCustomMessage OBJECT IDENTIFIER ::= { 1 3 6 1 4 1 48710 1 3 27 }
id-at-gluuDSstatus OBJECT IDENTIFIER ::= { 1 3 6 1 4 1 48710 1 3 28 }
id-at-gluuEntityId OBJECT IDENTIFIER ::= { 1 3 6 1 4 1 48710 1 3 29 }
id-at-gluuFaviconImage OBJECT IDENTIFIER ::= { 1 3 6 1 4 1 48710 1 3 30 }
id-at-gluuFederationHostingEnabled OBJECT IDENTIFIER ::= { 1 3 6 1 4 1 48710 1 3 31 }
id-at-gluuFreeDiskSpace OBJECT IDENTIFIER ::= { 1 3 6 1 4 1 48710 1 3 32 }
id-at-gluuFreeMemory OBJECT IDENTIFIER ::= { 1 3 6 1 4 1 48710 1 3 33 }
id-at-gluuFreeSwap OBJECT IDENTIFIER ::= { 1 3 6 1 4 1 48710 1 3 34 }
id-at-gluuHTTPstatus OBJECT IDENTIFIER ::= { 1 3 6 1 4 1 48710 1 3 35 }
id-at-gluuGroupCount OBJECT IDENTIFIER ::= { 1 3 6 1 4 1 48710 1 3 36 }
id-at-gluuGroupType OBJECT IDENTIFIER ::= { 1 3 6 1 4 1 48710 1 3 37 }
id-at-gluuGroupVisibility OBJECT IDENTIFIER ::= { 1 3 6 1 4 1 48710 1 3 38 }
id-at-gluuHostname OBJECT IDENTIFIER ::= { 1 3 6 1 4 1 48710 1 3 39 }
id-at-gluuInvoiceAmount OBJECT IDENTIFIER ::= { 1 3 6 1 4 1 48710 1 3 40 }
id-at-gluuInvoiceDate OBJECT IDENTIFIER ::= { 1 3 6 1 4 1 48710 1 3 41 }
id-at-gluuInvoiceLineItemName OBJECT IDENTIFIER ::= { 1 3 6 1 4 1 48710 1 3 42 }
id-at-gluuInvoiceNo OBJECT IDENTIFIER ::= { 1 3 6 1 4 1 48710 1 3 43 }
id-at-gluuInvoiceNumber OBJECT IDENTIFIER ::= { 1 3 6 1 4 1 48710 1 3 44 }
id-at-gluuInvoiceProductNumber OBJECT IDENTIFIER ::= { 1 3 6 1 4 1 48710 1 3 45 }
id-at-gluuInvoiceQuantity OBJECT IDENTIFIER ::= { 1 3 6 1 4 1 48710 1 3 46 }
id-at-gluuInvoiceStatus OBJECT IDENTIFIER ::= { 1 3 6 1 4 1 48710 1 3 47 }
id-at-gluuIpAddress OBJECT IDENTIFIER ::= { 1 3 6 1 4 1 48710 1 3 48 }
id-at-gluuIsFederation OBJECT IDENTIFIER ::= { 1 3 6 1 4 1 48710 1 3 49 }
id-at-gluuLastUpdate OBJECT IDENTIFIER ::= { 1 3 6 1 4 1 48710 1 3 50 }
id-at-gluuLifeRay OBJECT IDENTIFIER ::= { 1 3 6 1 4 1 48710 1 3 51 }
id-at-gluuLoadAvg OBJECT IDENTIFIER ::= { 1 3 6 1 4 1 48710 1 3 52 }
id-at-gluuLogoImage OBJECT IDENTIFIER ::= { 1 3 6 1 4 1 48710 1 3 53 }
id-at-gluuManageIdentityPermission OBJECT IDENTIFIER ::= { 1 3 6 1 4 1 48710 1 3 54 }
id-at-gluuManagedOrganizations OBJECT IDENTIFIER ::= { 1 3 6 1 4 1 48710 1 3 55 }
id-at-gluuManager OBJECT IDENTIFIER ::= { 1 3 6 1 4 1 48710 1 3 56 }
id-at-gluuManagerGroup OBJECT IDENTIFIER ::= { 1 3 6 1 4 1 48710 1 3 57 }
id-at-gluuMaxLogSize OBJECT IDENTIFIER ::= { 1 3 6 1 4 1 48710 1 3 58 }
id-at-gluuOptOuts OBJECT IDENTIFIER ::= { 1 3 6 1 4 1 48710 1 3 59 }
id-at-gluuOrgProfileMgt OBJECT IDENTIFIER ::= { 1 3 6 1 4 1 48710 1 3 60 }
id-at-gluuOrgShortName OBJECT IDENTIFIER ::= { 1 3 6 1 4 1 48710 1 3 61 }
id-at-gluuPaidUntil OBJECT IDENTIFIER ::= { 1 3 6 1 4 1 48710 1 3 62 }
id-at-gluuPaymentProcessorTimestamp OBJECT IDENTIFIER ::= { 1 3 6 1 4 1 48710 1 3 63 }
id-at-gluuPersonCount OBJECT IDENTIFIER ::= { 1 3 6 1 4 1 48710 1 3 64 }
id-at-gluuPrivate OBJECT IDENTIFIER ::= { 1 3 6 1 4 1 48710 1 3 65 }
id-at-gluuProStoresUser OBJECT IDENTIFIER ::= { 1 3 6 1 4 1 48710 1 3 66 }
id-at-gluuProfileConfiguration OBJECT IDENTIFIER ::= { 1 3 6 1 4 1 48710 1 3 67 }
id-at-gluuPublishIdpMetadata OBJECT IDENTIFIER ::= { 1 3 6 1 4 1 48710 1 3 68 }
id-at-gluuReleasedAttribute OBJECT IDENTIFIER ::= { 1 3 6 1 4 1 48710 1 3 69 }
id-at-gluuResizeInitiated OBJECT IDENTIFIER ::= { 1 3 6 1 4 1 48710 1 3 70 }
id-at-gluuRulesAccepted OBJECT IDENTIFIER ::= { 1 3 6 1 4 1 48710 1 3 71 }
id-at-gluuSAML1URI OBJECT IDENTIFIER ::= { 1 3 6 1 4 1 48710 1 3 72 }
id-at-gluuSAML2URI OBJECT IDENTIFIER ::= { 1 3 6 1 4 1 48710 1 3 73 }
id-at-gluuSAMLMetaDataFilter OBJECT IDENTIFIER ::= { 1 3 6 1 4 1 48710 1 3 74 }
id-at-gluuSAMLTrustEngine OBJECT IDENTIFIER ::= { 1 3 6 1 4 1 48710 1 3 75 }
id-at-gluuSAMLmaxRefreshDelay OBJECT IDENTIFIER ::= { 1 3 6 1 4 1 48710 1 3 76 }
id-at-gluuSAMLspMetaDataFN OBJECT IDENTIFIER ::= { 1 3 6 1 4 1 48710 1 3 77 }
id-at-gluuSAMLspMetaDataSourceType OBJECT IDENTIFIER ::= { 1 3 6 1 4 1 48710 1 3 78 }
id-at-gluuSAMLspMetaDataURL OBJECT IDENTIFIER ::= { 1 3 6 1 4 1 48710 1 3 79 }
id-at-gluuSLAManager OBJECT IDENTIFIER ::= { 1 3 6 1 4 1 48710 1 3 80 }
id-at-gluuSPTR OBJECT IDENTIFIER ::= { 1 3 6 1 4 1 48710 1 3 81 }
id-at-gluuScimEnabled OBJECT IDENTIFIER ::= { 1 3 6 1 4 1 48710 1 3 82 }
id-at-gluuShibAssertionsIssued OBJECT IDENTIFIER ::= { 1 3 6 1 4 1 48710 1 3 83 }
id-at-gluuShibFailedAuth OBJECT IDENTIFIER ::= { 1 3 6 1 4 1 48710 1 3 84 }
id-at-gluuShibSecurityEvents OBJECT IDENTIFIER ::= { 1 3 6 1 4 1 48710 1 3 85 }
id-at-gluuShibSuccessfulAuths OBJECT IDENTIFIER ::= { 1 3 6 1 4 1 48710 1 3 86 }
id-at-gluuSmtpFromEmailAddress OBJECT IDENTIFIER ::= { 1 3 6 1 4 1 48710 1 3 87 }
id-at-gluuSmtpFromName OBJECT IDENTIFIER ::= { 1 3 6 1 4 1 48710 1 3 88 }
id-at-gluuSmtpHost OBJECT IDENTIFIER ::= { 1 3 6 1 4 1 48710 1 3 89 }
id-at-gluuSmtpPassword OBJECT IDENTIFIER ::= { 1 3 6 1 4 1 48710 1 3 90 }
id-at-gluuSmtpPort OBJECT IDENTIFIER ::= { 1 3 6 1 4 1 48710 1 3 91 }
id-at-gluuSmtpRequiresAuthentication OBJECT IDENTIFIER ::= { 1 3 6 1 4 1 48710 1 3 92 }
id-at-gluuSmtpRequiresSsl OBJECT IDENTIFIER ::= { 1 3 6 1 4 1 48710 1 3 93 }
id-at-gluuSmtpUserName OBJECT IDENTIFIER ::= { 1 3 6 1 4 1 48710 1 3 94 }
id-at-gluuSpecificRelyingPartyConfig OBJECT IDENTIFIER ::= { 1 3 6 1 4 1 48710 1 3 95 }
id-at-gluuSslExpiry OBJECT IDENTIFIER ::= { 1 3 6 1 4 1 48710 1 3 96 }
id-at-gluuStatus OBJECT IDENTIFIER ::= { 1 3 6 1 4 1 48710 1 3 97 }
id-at-gluuSystemUptime OBJECT IDENTIFIER ::= { 1 3 6 1 4 1 48710 1 3 98 }
id-at-gluuTargetRAM OBJECT IDENTIFIER ::= { 1 3 6 1 4 1 48710 1 3 99 }
id-at-gluuTempFaviconImage OBJECT IDENTIFIER ::= { 1 3 6 1 4 1 48710 1 3 100 }
id-at-gluuThemeColor OBJECT IDENTIFIER ::= { 1 3 6 1 4 1 48710 1 3 101 }
id-at-gluuTrustContact OBJECT IDENTIFIER ::= { 1 3 6 1 4 1 48710 1 3 102 }
id-at-gluuTrustDeconstruction OBJECT IDENTIFIER ::= { 1 3 6 1 4 1 48710 1 3 103 }
id-at-gluuUrl OBJECT IDENTIFIER ::= { 1 3 6 1 4 1 48710 1 3 104 }
id-at-gluuVDSenabled OBJECT IDENTIFIER ::= { 1 3 6 1 4 1 48710 1 3 105 }
id-at-gluuVDSstatus OBJECT IDENTIFIER ::= { 1 3 6 1 4 1 48710 1 3 106 }
id-at-gluuValidationLog OBJECT IDENTIFIER ::= { 1 3 6 1 4 1 48710 1 3 107 }
id-at-gluuValidationStatus OBJECT IDENTIFIER ::= { 1 3 6 1 4 1 48710 1 3 108 }
id-at-gluuVdsCacheRefreshEnabled OBJECT IDENTIFIER ::= { 1 3 6 1 4 1 48710 1 3 109 }
id-at-gluuVdsCacheRefreshLastUpdate OBJECT IDENTIFIER ::= { 1 3 6 1 4 1 48710 1 3 110 }
id-at-gluuVdsCacheRefreshLastUpdateCount OBJECT IDENTIFIER ::= { 1 3 6 1 4 1 48710 1 3 111 }
id-at-gluuVdsCacheRefreshPollingInterval OBJECT IDENTIFIER ::= { 1 3 6 1 4 1 48710 1 3 112 }
id-at-gluuVdsCacheRefreshProblemCount OBJECT IDENTIFIER ::= { 1 3 6 1 4 1 48710 1 3 113 }
id-at-gluuWhitePagesEnabled OBJECT IDENTIFIER ::= { 1 3 6 1 4 1 48710 1 3 114 }
id-at-gluuWhitePagesListed OBJECT IDENTIFIER ::= { 1 3 6 1 4 1 48710 1 3 115 }
id-at-iname OBJECT IDENTIFIER ::= { 1 3 6 1 4 1 48710 1 3 116 }
id-at-inum OBJECT IDENTIFIER ::= { 1 3 6 1 4 1 48710 1 3 117 }
id-at-inumFN OBJECT IDENTIFIER ::= { 1 3 6 1 4 1 48710 1 3 118 }
id-at-literalBinaryValue OBJECT IDENTIFIER ::= { 1 3 6 1 4 1 48710 1 3 119 }
id-at-literalValue OBJECT IDENTIFIER ::= { 1 3 6 1 4 1 48710 1 3 120 }
id-at-memberOf OBJECT IDENTIFIER ::= { 1 3 6 1 4 1 48710 1 3 121 }
id-at-nonProfit OBJECT IDENTIFIER ::= { 1 3 6 1 4 1 48710 1 3 122 }
id-at-organizationalOwner OBJECT IDENTIFIER ::= { 1 3 6 1 4 1 48710 1 3 123 }
id-at-oxAmHost OBJECT IDENTIFIER ::= { 1 3 6 1 4 1 48710 1 3 124 }
id-at-oxAuthClaimName OBJECT IDENTIFIER ::= { 1 3 6 1 4 1 48710 1 3 125 }
id-at-oxAuthAppType OBJECT IDENTIFIER ::= { 1 3 6 1 4 1 48710 1 3 126 }
id-at-authnTime OBJECT IDENTIFIER ::= { 1 3 6 1 4 1 48710 1 3 127 }
id-at-authzCode OBJECT IDENTIFIER ::= { 1 3 6 1 4 1 48710 1 3 128 }
id-at-oxAuthClaim OBJECT IDENTIFIER ::= { 1 3 6 1 4 1 48710 1 3 129 }
id-at-oxAuthGroupClaims OBJECT IDENTIFIER ::= { 1 3 6 1 4 1 48710 1 3 130 }
id-at-oxAuthClientId OBJECT IDENTIFIER ::= { 1 3 6 1 4 1 48710 1 3 131 }
id-at-clnId OBJECT IDENTIFIER ::= { 1 3 6 1 4 1 48710 1 3 132 }
id-at-oxAuthClientIdIssuedAt OBJECT IDENTIFIER ::= { 1 3 6 1 4 1 48710 1 3 133 }
id-at-oxAuthClientSecret OBJECT IDENTIFIER ::= { 1 3 6 1 4 1 48710 1 3 134 }
id-at-oxAuthClientSecretExpiresAt OBJECT IDENTIFIER ::= { 1 3 6 1 4 1 48710 1 3 135 }
id-at-oxAuthClientURI OBJECT IDENTIFIER ::= { 1 3 6 1 4 1 48710 1 3 136 }
id-at-oxAuthConfDynamic OBJECT IDENTIFIER ::= { 1 3 6 1 4 1 48710 1 3 137 }
id-at-oxAuthConfErrors OBJECT IDENTIFIER ::= { 1 3 6 1 4 1 48710 1 3 138 }
id-at-oxAuthConfStatic OBJECT IDENTIFIER ::= { 1 3 6 1 4 1 48710 1 3 139 }
id-at-oxAuthConfWebKeys OBJECT IDENTIFIER ::= { 1 3 6 1 4 1 48710 1 3 140 }
id-at-oxAuthContact OBJECT IDENTIFIER ::= { 1 3 6 1 4 1 48710 1 3 141 }
id-at-iat OBJECT IDENTIFIER ::= { 1 3 6 1 4 1 48710 1 3 142 }
id-at-oxAuthDefaultAcrValues OBJECT IDENTIFIER ::= { 1 3 6 1 4 1 48710 1 3 143 }
id-at-oxAuthDefaultMaxAge OBJECT IDENTIFIER ::= { 1 3 6 1 4 1 48710 1 3 144 }
id-at-exp OBJECT IDENTIFIER ::= { 1 3 6 1 4 1 48710 1 3 145 }
id-at-grtId OBJECT IDENTIFIER ::= { 1 3 6 1 4 1 48710 1 3 146 }
id-at-oxAuthGrantType OBJECT IDENTIFIER ::= { 1 3 6 1 4 1 48710 1 3 147 }
id-at-grtTyp OBJECT IDENTIFIER ::= { 1 3 6 1 4 1 48710 1 3 148 }
id-at-oxAuthIdTokenEncryptedResponseAlg OBJECT IDENTIFIER ::= { 1 3 6 1 4 1 48710 1 3 149 }
id-at-oxAuthIdTokenEncryptedResponseEnc OBJECT IDENTIFIER ::= { 1 3 6 1 4 1 48710 1 3 150 }
id-at-oxAuthIdTokenSignedResponseAlg OBJECT IDENTIFIER ::= { 1 3 6 1 4 1 48710 1 3 151 }
id-at-oxAuthInitiateLoginURI OBJECT IDENTIFIER ::= { 1 3 6 1 4 1 48710 1 3 152 }
id-at-oxAuthJwksURI OBJECT IDENTIFIER ::= { 1 3 6 1 4 1 48710 1 3 153 }
id-at-oxAuthJwks OBJECT IDENTIFIER ::= { 1 3 6 1 4 1 48710 1 3 154 }
id-at-jwtReq OBJECT IDENTIFIER ::= { 1 3 6 1 4 1 48710 1 3 155 }
id-at-oxAuthLogoURI OBJECT IDENTIFIER ::= { 1 3 6 1 4 1 48710 1 3 156 }
id-at-nnc OBJECT IDENTIFIER ::= { 1 3 6 1 4 1 48710 1 3 157 }
id-at-oxSessionState OBJECT IDENTIFIER ::= { 1 3 6 1 4 1 48710 1 3 158 }
id-at-oxAuthPermissionGrantedMap OBJECT IDENTIFIER ::= { 1 3 6 1 4 1 48710 1 3 159 }
id-at-oxAuthPersistentJWT OBJECT IDENTIFIER ::= { 1 3 6 1 4 1 48710 1 3 160 }
id-at-oxAuthPolicyURI OBJECT IDENTIFIER ::= { 1 3 6 1 4 1 48710 1 3 161 }
id-at-oxAuthLogoutURI OBJECT IDENTIFIER ::= { 1 3 6 1 4 1 48710 1 3 162 }
id-at-oxAuthLogoutSessionRequired OBJECT IDENTIFIER ::= { 1 3 6 1 4 1 48710 1 3 163 }
id-at-oxAuthPostLogoutRedirectURI OBJECT IDENTIFIER ::= { 1 3 6 1 4 1 48710 1 3 164 }
id-at-oxAuthRedirectURI OBJECT IDENTIFIER ::= { 1 3 6 1 4 1 48710 1 3 165 }
id-at-oxAuthRegistrationAccessToken OBJECT IDENTIFIER ::= { 1 3 6 1 4 1 48710 1 3 166 }
id-at-oxAuthReleasedScope OBJECT IDENTIFIER ::= { 1 3 6 1 4 1 48710 1 3 167 }
id-at-oxAuthRequestObjectSigningAlg OBJECT IDENTIFIER ::= { 1 3 6 1 4 1 48710 1 3 168 }
id-at-oxAuthRequestObjectEncryptionAlg OBJECT IDENTIFIER ::= { 1 3 6 1 4 1 48710 1 3 169 }
id-at-oxAuthRequestObjectEncryptionEnc OBJECT IDENTIFIER ::= { 1 3 6 1 4 1 48710 1 3 170 }
id-at-oxAuthRequestURI OBJECT IDENTIFIER ::= { 1 3 6 1 4 1 48710 1 3 171 }
id-at-oxAuthRequireAuthTime OBJECT IDENTIFIER ::= { 1 3 6 1 4 1 48710 1 3 172 }
id-at-oxAuthResponseType OBJECT IDENTIFIER ::= { 1 3 6 1 4 1 48710 1 3 173 }
id-at-oxAuthScope OBJECT IDENTIFIER ::= { 1 3 6 1 4 1 48710 1 3 174 }
id-at-scp OBJECT IDENTIFIER ::= { 1 3 6 1 4 1 48710 1 3 175 }
id-at-oxScopeType OBJECT IDENTIFIER ::= { 1 3 6 1 4 1 48710 1 3 176 }
id-at-oxAuthSectorIdentifierURI OBJECT IDENTIFIER ::= { 1 3 6 1 4 1 48710 1 3 177 }
id-at-oxAuthSignedResponseAlg OBJECT IDENTIFIER ::= { 1 3 6 1 4 1 48710 1 3 178 }
id-at-oxAuthSkipAuthorization OBJECT IDENTIFIER ::= { 1 3 6 1 4 1 48710 1 3 179 }
id-at-oxAuthSubjectType OBJECT IDENTIFIER ::= { 1 3 6 1 4 1 48710 1 3 180 }
id-at-tknCde OBJECT IDENTIFIER ::= { 1 3 6 1 4 1 48710 1 3 181 }
id-at-oxAuthTokenEndpointAuthMethod OBJECT IDENTIFIER ::= { 1 3 6 1 4 1 48710 1 3 182 }
id-at-oxAuthTokenEndpointAuthSigningAlg OBJECT IDENTIFIER ::= { 1 3 6 1 4 1 48710 1 3 183 }
id-at-tknTyp OBJECT IDENTIFIER ::= { 1 3 6 1 4 1 48710 1 3 184 }
id-at-oxAuthTosURI OBJECT IDENTIFIER ::= { 1 3 6 1 4 1 48710 1 3 185 }
id-at-oxAuthTrustedClient OBJECT IDENTIFIER ::= { 1 3 6 1 4 1 48710 1 3 186 }
id-at-oxAuthUmaScope OBJECT IDENTIFIER ::= { 1 3 6 1 4 1 48710 1 3 187 }
id-at-oxAuthUserDN OBJECT IDENTIFIER ::= { 1 3 6 1 4 1 48710 1 3 188 }
id-at-oxAuthUserId OBJECT IDENTIFIER ::= { 1 3 6 1 4 1 48710 1 3 189 }
id-at-oxAuthUserInfoEncryptedResponseAlg OBJECT IDENTIFIER ::= { 1 3 6 1 4 1 48710 1 3 190 }
id-at-oxAuthUserInfoEncryptedResponseEnc OBJECT IDENTIFIER ::= { 1 3 6 1 4 1 48710 1 3 191 }
id-at-oxAuthExtraConf OBJECT IDENTIFIER ::= { 1 3 6 1 4 1 48710 1 3 192 }
id-at-oxAuthX509PEM OBJECT IDENTIFIER ::= { 1 3 6 1 4 1 48710 1 3 193 }
id-at-oxAuthX509URL OBJECT IDENTIFIER ::= { 1 3 6 1 4 1 48710 1 3 194 }
id-at-oxAuthenticationMode OBJECT IDENTIFIER ::= { 1 3 6 1 4 1 48710 1 3 195 }
id-at-acr OBJECT IDENTIFIER ::= { 1 3 6 1 4 1 48710 1 3 196 }
id-at-oxTrustAuthenticationMode OBJECT IDENTIFIER ::= { 1 3 6 1 4 1 48710 1 3 197 }
id-at-oxConfigurationCode OBJECT IDENTIFIER ::= { 1 3 6 1 4 1 48710 1 3 198 }
id-at-oxCreationTimestamp OBJECT IDENTIFIER ::= { 1 3 6 1 4 1 48710 1 3 199 }
id-at-oxDomain OBJECT IDENTIFIER ::= { 1 3 6 1 4 1 48710 1 3 200 }
id-at-oxExternalUid OBJECT IDENTIFIER ::= { 1 3 6 1 4 1 48710 1 3 201 }
id-at-oxOTPCache OBJECT IDENTIFIER ::= { 1 3 6 1 4 1 48710 1 3 202 }
id-at-oxFaviconImage OBJECT IDENTIFIER ::= { 1 3 6 1 4 1 48710 1 3 203 }
id-at-oxGroup OBJECT IDENTIFIER ::= { 1 3 6 1 4 1 48710 1 3 204 }
id-at-oxGuid OBJECT IDENTIFIER ::= { 1 3 6 1 4 1 48710 1 3 205 }
id-at-uuid OBJECT IDENTIFIER ::= { 1 3 6 1 4 1 48710 1 3 206 }
id-at-oxHost OBJECT IDENTIFIER ::= { 1 3 6 1 4 1 48710 1 3 207 }
id-at-oxIDPAuthentication OBJECT IDENTIFIER ::= { 1 3 6 1 4 1 48710 1 3 208 }
id-at-oxIconUrl OBJECT IDENTIFIER ::= { 1 3 6 1 4 1 48710 1 3 209 }
id-at-oxId OBJECT IDENTIFIER ::= { 1 3 6 1 4 1 48710 1 3 210 }
id-at-oxAsJwt OBJECT IDENTIFIER ::= { 1 3 6 1 4 1 48710 1 3 211 }
id-at-oxJwt OBJECT IDENTIFIER ::= { 1 3 6 1 4 1 48710 1 3 212 }
id-at-oxInvolvedClients OBJECT IDENTIFIER ::= { 1 3 6 1 4 1 48710 1 3 213 }
id-at-oxLastAccessTime OBJECT IDENTIFIER ::= { 1 3 6 1 4 1 48710 1 3 214 }
id-at-oxLastLogonTime OBJECT IDENTIFIER ::= { 1 3 6 1 4 1 48710 1 3 215 }
id-at-oxLinkCreator OBJECT IDENTIFIER ::= { 1 3 6 1 4 1 48710 1 3 216 }
id-at-oxLinkExpirationDate OBJECT IDENTIFIER ::= { 1 3 6 1 4 1 48710 1 3 217 }
id-at-oxLinkLinktrack OBJECT IDENTIFIER ::= { 1 3 6 1 4 1 48710 1 3 218 }
id-at-oxLinkModerated OBJECT IDENTIFIER ::= { 1 3 6 1 4 1 48710 1 3 219 }
id-at-oxLinkModerators OBJECT IDENTIFIER ::= { 1 3 6 1 4 1 48710 1 3 220 }
id-at-oxLinkPending OBJECT IDENTIFIER ::= { 1 3 6 1 4 1 48710 1 3 221 }
id-at-oxLinktrackEnabled OBJECT IDENTIFIER ::= { 1 3 6 1 4 1 48710 1 3 222 }
id-at-oxLinktrackLogin OBJECT IDENTIFIER ::= { 1 3 6 1 4 1 48710 1 3 223 }
id-at-oxLinktrackPassword OBJECT IDENTIFIER ::= { 1 3 6 1 4 1 48710 1 3 224 }
id-at-oxLogViewerConfig OBJECT IDENTIFIER ::= { 1 3 6 1 4 1 48710 1 3 225 }
id-at-oxMultivaluedAttribute OBJECT IDENTIFIER ::= { 1 3 6 1 4 1 48710 1 3 226 }
id-at-oxName OBJECT IDENTIFIER ::= { 1 3 6 1 4 1 48710 1 3 227 }
id-at-oxNameIdType OBJECT IDENTIFIER ::= { 1 3 6 1 4 1 48710 1 3 228 }
id-at-oxPolicyRule OBJECT IDENTIFIER ::= { 1 3 6 1 4 1 48710 1 3 229 }
id-at-oxUmaPolicyScriptDn OBJECT IDENTIFIER ::= { 1 3 6 1 4 1 48710 1 3 230 }
id-at-oxProxConf OBJECT IDENTIFIER ::= { 1 3 6 1 4 1 48710 1 3 231 }
id-at-oxProxyAccessToken OBJECT IDENTIFIER ::= { 1 3 6 1 4 1 48710 1 3 232 }
id-at-oxProxyClaimMapping OBJECT IDENTIFIER ::= { 1 3 6 1 4 1 48710 1 3 233 }
id-at-oxState OBJECT IDENTIFIER ::= { 1 3 6 1 4 1 48710 1 3 234 }
id-at-oxCounter OBJECT IDENTIFIER ::= { 1 3 6 1 4 1 48710 1 3 235 }
id-at-oxStatus OBJECT IDENTIFIER ::= { 1 3 6 1 4 1 48710 1 3 236 }
id-at-oxApplication OBJECT IDENTIFIER ::= { 1 3 6 1 4 1 48710 1 3 237 }
id-at-oxDeviceRegistrationConf OBJECT IDENTIFIER ::= { 1 3 6 1 4 1 48710 1 3 238 }
id-at-oxDeviceKeyHandle OBJECT IDENTIFIER ::= { 1 3 6 1 4 1 48710 1 3 239 }
id-at-oxDeviceHashCode OBJECT IDENTIFIER ::= { 1 3 6 1 4 1 48710 1 3 240 }
id-at-oxRequest OBJECT IDENTIFIER ::= { 1 3 6 1 4 1 48710 1 3 241 }
id-at-oxRequestId OBJECT IDENTIFIER ::= { 1 3 6 1 4 1 48710 1 3 242 }
id-at-oxDeviceData OBJECT IDENTIFIER ::= { 1 3 6 1 4 1 48710 1 3 243 }
id-at-oxEnrollmentCode OBJECT IDENTIFIER ::= { 1 3 6 1 4 1 48710 1 3 244 }
id-at-oxProxyClientId OBJECT IDENTIFIER ::= { 1 3 6 1 4 1 48710 1 3 245 }
id-at-oxProxyScope OBJECT IDENTIFIER ::= { 1 3 6 1 4 1 48710 1 3 246 }
id-at-oxProxyToOpClientMapping OBJECT IDENTIFIER ::= { 1 3 6 1 4 1 48710 1 3 247 }
id-at-oxPushApplication OBJECT IDENTIFIER ::= { 1 3 6 1 4 1 48710 1 3 248 }
id-at-oxPushApplicationConf OBJECT IDENTIFIER ::= { 1 3 6 1 4 1 48710 1 3 249 }
id-at-oxPushDeviceConf OBJECT IDENTIFIER ::= { 1 3 6 1 4 1 48710 1 3 250 }
id-at-oxRegistrationConfiguration OBJECT IDENTIFIER ::= { 1 3 6 1 4 1 48710 1 3 251 }
id-at-oxResource OBJECT IDENTIFIER ::= { 1 3 6 1 4 1 48710 1 3 252 }
id-at-oxResourceSetId OBJECT IDENTIFIER ::= { 1 3 6 1 4 1 48710 1 3 253 }
id-at-oxRevision OBJECT IDENTIFIER ::= { 1 3 6 1 4 1 48710 1 3 254 }
id-at-oxLevel OBJECT IDENTIFIER ::= { 1 3 6 1 4 1 48710 1 3 255 }
id-at-oxSCIMCustomAttribute OBJECT IDENTIFIER ::= { 1 3 6 1 4 1 48710 1 3 256 }
id-at-oxScript OBJECT IDENTIFIER ::= { 1 3 6 1 4 1 48710 1 3 257 }
id-at-oxScriptDn OBJECT IDENTIFIER ::= { 1 3 6 1 4 1 48710 1 3 258 }
id-at-oxScriptType OBJECT IDENTIFIER ::= { 1 3 6 1 4 1 48710 1 3 259 }
id-at-oxScriptError OBJECT IDENTIFIER ::= { 1 3 6 1 4 1 48710 1 3 260 }
id-at-oxSmtpConfiguration OBJECT IDENTIFIER ::= { 1 3 6 1 4 1 48710 1 3 261 }
id-at-oxSourceAttribute OBJECT IDENTIFIER ::= { 1 3 6 1 4 1 48710 1 3 262 }
id-at-oxTicket OBJECT IDENTIFIER ::= { 1 3 6 1 4 1 48710 1 3 263 }
id-at-oxTrustActive OBJECT IDENTIFIER ::= { 1 3 6 1 4 1 48710 1 3 264 }
id-at-oxTrustCacheRefreshServerIpAddress OBJECT IDENTIFIER ::= { 1 3 6 1 4 1 48710 1 3 265 }
id-at-oxTrustAddresses OBJECT IDENTIFIER ::= { 1 3 6 1 4 1 48710 1 3 266 }
id-at-oxTrustConfApplication OBJECT IDENTIFIER ::= { 1 3 6 1 4 1 48710 1 3 267 }
id-at-oxTrustConfCacheRefresh OBJECT IDENTIFIER ::= { 1 3 6 1 4 1 48710 1 3 268 }
id-at-oxConfApplication OBJECT IDENTIFIER ::= { 1 3 6 1 4 1 48710 1 3 269 }
id-at-oxTrustCustAttrB OBJECT IDENTIFIER ::= { 1 3 6 1 4 1 48710 1 3 270 }
id-at-oxTrustEmail OBJECT IDENTIFIER ::= { 1 3 6 1 4 1 48710 1 3 271 }
id-at-oxTrustEntitlements OBJECT IDENTIFIER ::= { 1 3 6 1 4 1 48710 1 3 272 }
id-at-oxTrustExternalId OBJECT IDENTIFIER ::= { 1 3 6 1 4 1 48710 1 3 273 }
id-at-oxTrustImsValue OBJECT IDENTIFIER ::= { 1 3 6 1 4 1 48710 1 3 274 }
id-at-oxTrustMetaCreated OBJECT IDENTIFIER ::= { 1 3 6 1 4 1 48710 1 3 275 }
id-at-oxTrustMetaLastModified OBJECT IDENTIFIER ::= { 1 3 6 1 4 1 48710 1 3 276 }
id-at-oxTrustMetaLocation OBJECT IDENTIFIER ::= { 1 3 6 1 4 1 48710 1 3 277 }
id-at-oxTrustMetaVersion OBJECT IDENTIFIER ::= { 1 3 6 1 4 1 48710 1 3 278 }
id-at-oxTrustNameFormatted OBJECT IDENTIFIER ::= { 1 3 6 1 4 1 48710 1 3 279 }
id-at-oxTrustPhoneValue OBJECT IDENTIFIER ::= { 1 3 6 1 4 1 48710 1 3 280 }
id-at-oxTrustPhotos OBJECT IDENTIFIER ::= { 1 3 6 1 4 1 48710 1 3 281 }
id-at-oxTrustProfileURL OBJECT IDENTIFIER ::= { 1 3 6 1 4 1 48710 1 3 282 }
id-at-oxTrustRole OBJECT IDENTIFIER ::= { 1 3 6 1 4 1 48710 1 3 283 }
id-at-oxTrustStoreCert OBJECT IDENTIFIER ::= { 1 3 6 1 4 1 48710 1 3 284 }
id-at-oxTrustStoreConf OBJECT IDENTIFIER ::= { 1 3 6 1 4 1 48710 1 3 285 }
id-at-oxTrustTitle OBJECT IDENTIFIER ::= { 1 3 6 1 4 1 48710 1 3 286 }
id-at-oxTrustUserType OBJECT IDENTIFIER ::= { 1 3 6 1 4 1 48710 1 3 287 }
id-at-oxTrusthonorificPrefix OBJECT IDENTIFIER ::= { 1 3 6 1 4 1 48710 1 3 288 }
id-at-oxTrusthonorificSuffix OBJECT IDENTIFIER ::= { 1 3 6 1 4 1 48710 1 3 289 }
id-at-oxTrustx509Certificate OBJECT IDENTIFIER ::= { 1 3 6 1 4 1 48710 1 3 290 }
id-at-oxType OBJECT IDENTIFIER ::= { 1 3 6 1 4 1 48710 1 3 291 }
id-at-oxUmaPermission OBJECT IDENTIFIER ::= { 1 3 6 1 4 1 48710 1 3 292 }
id-at-oxUrl OBJECT IDENTIFIER ::= { 1 3 6 1 4 1 48710 1 3 293 }
id-at-oxX509PEM OBJECT IDENTIFIER ::= { 1 3 6 1 4 1 48710 1 3 294 }
id-at-oxX509URL OBJECT IDENTIFIER ::= { 1 3 6 1 4 1 48710 1 3 295 }
id-at-passwordResetAllowed OBJECT IDENTIFIER ::= { 1 3 6 1 4 1 48710 1 3 296 }
id-at-persistentId OBJECT IDENTIFIER ::= { 1 3 6 1 4 1 48710 1 3 297 }
id-at-personInum OBJECT IDENTIFIER ::= { 1 3 6 1 4 1 48710 1 3 298 }
id-at-primaryKeyAttrName OBJECT IDENTIFIER ::= { 1 3 6 1 4 1 48710 1 3 299 }
id-at-primaryKeyValue OBJECT IDENTIFIER ::= { 1 3 6 1 4 1 48710 1 3 300 }
id-at-proStoresToken OBJECT IDENTIFIER ::= { 1 3 6 1 4 1 48710 1 3 301 }
id-at-programmingLanguage OBJECT IDENTIFIER ::= { 1 3 6 1 4 1 48710 1 3 302 }
id-at-prostoresTimestamp OBJECT IDENTIFIER ::= { 1 3 6 1 4 1 48710 1 3 303 }
id-at-registrationDate OBJECT IDENTIFIER ::= { 1 3 6 1 4 1 48710 1 3 304 }
id-at-role OBJECT IDENTIFIER ::= { 1 3 6 1 4 1 48710 1 3 305 }
id-at-scimAuthMode OBJECT IDENTIFIER ::= { 1 3 6 1 4 1 48710 1 3 306 }
id-at-scimGroup OBJECT IDENTIFIER ::= { 1 3 6 1 4 1 48710 1 3 307 }
id-at-scimStatus OBJECT IDENTIFIER ::= { 1 3 6 1 4 1 48710 1 3 308 }
id-at-secondaryKeyAttrName OBJECT IDENTIFIER ::= { 1 3 6 1 4 1 48710 1 3 309 }
id-at-secondaryKeyValue OBJECT IDENTIFIER ::= { 1 3 6 1 4 1 48710 1 3 310 }
id-at-secretAnswer OBJECT IDENTIFIER ::= { 1 3 6 1 4 1 48710 1 3 311 }
id-at-secretQuestion OBJECT IDENTIFIER ::= { 1 3 6 1 4 1 48710 1 3 312 }
id-at-softwareVersion OBJECT IDENTIFIER ::= { 1 3 6 1 4 1 48710 1 3 313 }
id-at-sourceRelationalXdiStatement OBJECT IDENTIFIER ::= { 1 3 6 1 4 1 48710 1 3 314 }
id-at-targetRelationalXdiStatement OBJECT IDENTIFIER ::= { 1 3 6 1 4 1 48710 1 3 315 }
id-at-tertiaryKeyAttrName OBJECT IDENTIFIER ::= { 1 3 6 1 4 1 48710 1 3 316 }
id-at-tertiaryKeyValue OBJECT IDENTIFIER ::= { 1 3 6 1 4 1 48710 1 3 317 }
id-at-transientId OBJECT IDENTIFIER ::= { 1 3 6 1 4 1 48710 1 3 318 }
id-at-url OBJECT IDENTIFIER ::= { 1 3 6 1 4 1 48710 1 3 319 }
id-at-urn OBJECT IDENTIFIER ::= { 1 3 6 1 4 1 48710 1 3 320 }
id-at-x OBJECT IDENTIFIER ::= { 1 3 6 1 4 1 48710 1 3 321 }
id-at-xdiStatement OBJECT IDENTIFIER ::= { 1 3 6 1 4 1 48710 1 3 322 }
id-at-xri OBJECT IDENTIFIER ::= { 1 3 6 1 4 1 48710 1 3 323 }
id-at-middleName OBJECT IDENTIFIER ::= { 1 3 6 1 4 1 48710 1 3 324 }
id-at-nickname OBJECT IDENTIFIER ::= { 1 3 6 1 4 1 48710 1 3 325 }
id-at-preferredUsername OBJECT IDENTIFIER ::= { 1 3 6 1 4 1 48710 1 3 326 }
id-at-profile OBJECT IDENTIFIER ::= { 1 3 6 1 4 1 48710 1 3 327 }
id-at-picture OBJECT IDENTIFIER ::= { 1 3 6 1 4 1 48710 1 3 328 }
id-at-website OBJECT IDENTIFIER ::= { 1 3 6 1 4 1 48710 1 3 329 }
id-at-emailVerified OBJECT IDENTIFIER ::= { 1 3 6 1 4 1 48710 1 3 330 }
id-at-gender OBJECT IDENTIFIER ::= { 1 3 6 1 4 1 48710 1 3 331 }
id-at-birthdate OBJECT IDENTIFIER ::= { 1 3 6 1 4 1 48710 1 3 332 }
id-at-zoneinfo OBJECT IDENTIFIER ::= { 1 3 6 1 4 1 48710 1 3 333 }
id-at-locale OBJECT IDENTIFIER ::= { 1 3 6 1 4 1 48710 1 3 334 }
id-at-phoneNumberVerified OBJECT IDENTIFIER ::= { 1 3 6 1 4 1 48710 1 3 335 }
id-at-address OBJECT IDENTIFIER ::= { 1 3 6 1 4 1 48710 1 3 336 }
id-at-updatedAt OBJECT IDENTIFIER ::= { 1 3 6 1 4 1 48710 1 3 337 }
id-at-gluuRegExp OBJECT IDENTIFIER ::= { 1 3 6 1 4 1 48710 1 3 338 }
id-at-gluuTooltip OBJECT IDENTIFIER ::= { 1 3 6 1 4 1 48710 1 3 339 }
id-at-oxModuleProperty OBJECT IDENTIFIER ::= { 1 3 6 1 4 1 48710 1 3 340 }
id-at-oxConfigurationProperty OBJECT IDENTIFIER ::= { 1 3 6 1 4 1 48710 1 3 341 }
id-at-oxAuthSessionAttribute OBJECT IDENTIFIER ::= { 1 3 6 1 4 1 48710 1 3 342 }
id-at-researchAndScholarshipEnabled OBJECT IDENTIFIER ::= { 1 3 6 1 4 1 48710 1 3 343 }
id-at-oxStartDate OBJECT IDENTIFIER ::= { 1 3 6 1 4 1 48710 1 3 344 }
id-at-oxEndDate OBJECT IDENTIFIER ::= { 1 3 6 1 4 1 48710 1 3 345 }
id-at-oxApplicationType OBJECT IDENTIFIER ::= { 1 3 6 1 4 1 48710 1 3 346 }
id-at-oxMetricType OBJECT IDENTIFIER ::= { 1 3 6 1 4 1 48710 1 3 347 }
id-at-oxData OBJECT IDENTIFIER ::= { 1 3 6 1 4 1 48710 1 3 348 }
id-at-dat OBJECT IDENTIFIER ::= { 1 3 6 1 4 1 48710 1 3 349 }
id-at-oxCodeChallenge OBJECT IDENTIFIER ::= { 1 3 6 1 4 1 48710 1 3 350 }
id-at-chlng OBJECT IDENTIFIER ::= { 1 3 6 1 4 1 48710 1 3 351 }
id-at-chlngMth OBJECT IDENTIFIER ::= { 1 3 6 1 4 1 48710 1 3 352 }
id-at-oxSectorIdentifier OBJECT IDENTIFIER ::= { 1 3 6 1 4 1 48710 1 3 353 }
id-at-oxPersistClientAuthorizations OBJECT IDENTIFIER ::= { 1 3 6 1 4 1 48710 1 3 354 }
id-at-oxTrustConfImportPerson OBJECT IDENTIFIER ::= { 1 3 6 1 4 1 48710 1 3 355 }
id-at-oxSessionStateId OBJECT IDENTIFIER ::= { 1 3 6 1 4 1 48710 1 3 356 }
id-at-ssnId OBJECT IDENTIFIER ::= { 1 3 6 1 4 1 48710 1 3 357 }
id-at-oxPasswordExpirationDate OBJECT IDENTIFIER ::= { 1 3 6 1 4 1 48710 1 3 358 }
id-at-oxCountInvalidLogin OBJECT IDENTIFIER ::= { 1 3 6 1 4 1 48710 1 3 359 }
id-at-gluuIMAPData OBJECT IDENTIFIER ::= { 1 3 6 1 4 1 48710 1 3 360 }
id-at-gluuPassportConfiguration OBJECT IDENTIFIER ::= { 1 3 6 1 4 1 48710 1 3 361 }
id-at-gluuPassportEnabled OBJECT IDENTIFIER ::= { 1 3 6 1 4 1 48710 1 3 362 }
id-at-gluuRadiusEnabled OBJECT IDENTIFIER ::= { 1 3 6 1 4 1 48710 1 3 363 }
id-at-gluuSamlEnabled OBJECT IDENTIFIER ::= { 1 3 6 1 4 1 48710 1 3 364 }
id-at-oxValidation OBJECT IDENTIFIER ::= { 1 3 6 1 4 1 48710 1 3 365 }
id-at-gluuEntityType OBJECT IDENTIFIER ::= { 1 3 6 1 4 1 48710 1 3 366 }
id-at-oxPPID OBJECT IDENTIFIER ::= { 1 3 6 1 4 1 48710 1 3 367 }
id-at-oxAuthSessionId OBJECT IDENTIFIER ::= { 1 3 6 1 4 1 48710 1 3 368 }
id-at-oxCacheConfiguration OBJECT IDENTIFIER ::= { 1 3 6 1 4 1 48710 1 3 369 }
id-at-oxLogConfigLocation OBJECT IDENTIFIER ::= { 1 3 6 1 4 1 48710 1 3 370 }
id-at-oxIncludeClaimsInIdToken OBJECT IDENTIFIER ::= { 1 3 6 1 4 1 48710 1 3 371 }
id-at-oxClaimValues OBJECT IDENTIFIER ::= { 1 3 6 1 4 1 48710 1 3 372 }
id-at-oxClaimRedirectURI OBJECT IDENTIFIER ::= { 1 3 6 1 4 1 48710 1 3 373 }
id-at-oxAttributes OBJECT IDENTIFIER ::= { 1 3 6 1 4 1 48710 1 3 374 }
id-at-attr OBJECT IDENTIFIER ::= { 1 3 6 1 4 1 48710 1 3 375 }
id-at-userRandomKey OBJECT IDENTIFIER ::= { 1 3 6 1 4 1 48710 1 3 376 }
id-at-oxRefreshTokenLifetime OBJECT IDENTIFIER ::= { 1 3 6 1 4 1 48710 1 3 377 }
id-at-oxTrustConfAttributeResolver OBJECT IDENTIFIER ::= { 1 3 6 1 4 1 48710 1 3 378 }
id-at-oxAuthPermissionGranted OBJECT IDENTIFIER ::= { 1 3 6 1 4 1 48710 1 3 379 }
id-at-oxNickName OBJECT IDENTIFIER ::= { 1 3 6 1 4 1 48710 1 3 380 }
id-at-oxDeviceNotificationConf OBJECT IDENTIFIER ::= { 1 3 6 1 4 1 48710 1 3 381 }
id-at-clms OBJECT IDENTIFIER ::= { 1 3 6 1 4 1 48710 1 3 382 }
id-at-oxDisabled OBJECT IDENTIFIER ::= { 1 3 6 1 4 1 48710 1 3 383 }
id-at-oxWebKeysSettings OBJECT IDENTIFIER ::= { 1 3 6 1 4 1 48710 1 3 384 }
id-at-oxScopeExpression OBJECT IDENTIFIER ::= { 1 3 6 1 4 1 48710 1 3 385 }
id-at-oxPreferredMethod OBJECT IDENTIFIER ::= { 1 3 6 1 4 1 48710 1 3 386 }
id-at-oxOTPDevices OBJECT IDENTIFIER ::= { 1 3 6 1 4 1 48710 1 3 387 }
id-at-oxMobileDevices OBJECT IDENTIFIER ::= { 1 3 6 1 4 1 48710 1 3 388 }
id-at-oxdId OBJECT IDENTIFIER ::= { 1 3 6 1 4 1 48710 1 3 389 }
id-at-oxAuthAuthorizedOrigins OBJECT IDENTIFIER ::= { 1 3 6 1 4 1 48710 1 3 390 }
id-at-oxStrongAuthPolicy OBJECT IDENTIFIER ::= { 1 3 6 1 4 1 48710 1 3 391 }
id-at-oxTrustedDevicesInfo OBJECT IDENTIFIER ::= { 1 3 6 1 4 1 48710 1 3 392 }
id-at-tknBndCnf OBJECT IDENTIFIER ::= { 1 3 6 1 4 1 48710 1 3 393 }
id-at-oxUnlinkedExternalUids OBJECT IDENTIFIER ::= { 1 3 6 1 4 1 48710 1 3 394 }
id-at-oxAccessTokenAsJwt OBJECT IDENTIFIER ::= { 1 3 6 1 4 1 48710 1 3 395 }
id-at-oxAccessTokenSigningAlg OBJECT IDENTIFIER ::= { 1 3 6 1 4 1 48710 1 3 396 }
id-at-oxRegistrationData OBJECT IDENTIFIER ::= { 1 3 6 1 4 1 48710 1 3 397 }
id-at-oxAuthenticationData OBJECT IDENTIFIER ::= { 1 3 6 1 4 1 48710 1 3 398 }
id-at-oxPublicKeyId OBJECT IDENTIFIER ::= { 1 3 6 1 4 1 48710 1 3 399 }
id-at-oxAccessTokenLifetime OBJECT IDENTIFIER ::= { 1 3 6 1 4 1 48710 1 3 400 }
id-at-oxSoftwareId OBJECT IDENTIFIER ::= { 1 3 6 1 4 1 48710 1 3 401 }
id-at-oxSoftwareVersion OBJECT IDENTIFIER ::= { 1 3 6 1 4 1 48710 1 3 402 }
id-at-oxSoftwareStatement OBJECT IDENTIFIER ::= { 1 3 6 1 4 1 48710 1 3 403 }
id-at-oxRptAsJwt OBJECT IDENTIFIER ::= { 1 3 6 1 4 1 48710 1 3 404 }
id-at-oxCodeChallengeHash OBJECT IDENTIFIER ::= { 1 3 6 1 4 1 48710 1 3 405 }
id-at-del OBJECT IDENTIFIER ::= { 1 3 6 1 4 1 48710 1 3 406 }
id-at-oxEnabled OBJECT IDENTIFIER ::= { 1 3 6 1 4 1 48710 1 3 407 }
id-at-oxAlias OBJECT IDENTIFIER ::= { 1 3 6 1 4 1 48710 1 3 408 }
id-at-oxTrustLogoPath OBJECT IDENTIFIER ::= { 1 3 6 1 4 1 48710 1 3 409 }
id-at-oxTrustFaviconPath OBJECT IDENTIFIER ::= { 1 3 6 1 4 1 48710 1 3 410 }
id-at-oxAuthLogoPath OBJECT IDENTIFIER ::= { 1 3 6 1 4 1 48710 1 3 411 }
id-at-oxAuthFaviconPath OBJECT IDENTIFIER ::= { 1 3 6 1 4 1 48710 1 3 412 }
id-at-idpLogoPath OBJECT IDENTIFIER ::= { 1 3 6 1 4 1 48710 1 3 413 }
id-at-idpFaviconPath OBJECT IDENTIFIER ::= { 1 3 6 1 4 1 48710 1 3 414 }
id-at-parent OBJECT IDENTIFIER ::= { 1 3 6 1 4 1 48710 1 3 415 }
id-at-classRef OBJECT IDENTIFIER ::= { 1 3 6 1 4 1 48710 1 3 416 }
id-at-gluuSmtpServerTrust OBJECT IDENTIFIER ::= { 1 3 6 1 4 1 48710 1 3 417 }
id-at-pattern-type OBJECT IDENTIFIER ::= { 1 3 6 1 4 1 48710 1 3 418 }
id-at-oxAuthBackchannelTokenDeliveryMode OBJECT IDENTIFIER ::= { 1 3 6 1 4 1 48710 1 3 419 }
id-at-oxAuthBackchannelClientNotificationEndpoint OBJECT IDENTIFIER ::= { 1 3 6 1 4 1 48710 1 3 420 }
id-at-oxAuthBackchannelAuthenticationRequestSigningAlg OBJECT IDENTIFIER ::= { 1 3 6 1 4 1 48710 1 3 421 }
id-at-oxAuthBackchannelUserCodeParameter OBJECT IDENTIFIER ::= { 1 3 6 1 4 1 48710 1 3 422 }
id-at-oxAuthBackchannelDeviceRegistrationToken OBJECT IDENTIFIER ::= { 1 3 6 1 4 1 48710 1 3 423 }
id-at-oxAuthBackchannelUserCode OBJECT IDENTIFIER ::= { 1 3 6 1 4 1 48710 1 3 424 }
id-at-oxDocumentStoreConfiguration OBJECT IDENTIFIER ::= { 1 3 6 1 4 1 48710 1 3 425 }
id-at-gluuConfDynamic OBJECT IDENTIFIER ::= { 1 3 6 1 4 1 48710 1 3 426 }
id-at-gluuConfStatic OBJECT IDENTIFIER ::= { 1 3 6 1 4 1 48710 1 3 427 }
id-at-authReqId OBJECT IDENTIFIER ::= { 1 3 6 1 4 1 48710 1 3 428 }
id-at-sid OBJECT IDENTIFIER ::= { 1 3 6 1 4 1 48710 1 3 429 }
id-at-jansId OBJECT IDENTIFIER ::= { 1 3 6 1 4 1 48710 1 3 430 }
id-oc-pairwiseIdentifier OBJECT IDENTIFIER ::= { 1 3 6 1 4 1 48710 1 4 1 }
id-oc-gluuPerson OBJECT IDENTIFIER ::= { 1 3 6 1 4 1 48710 1 4 2 }
id-oc-gluuGroup OBJECT IDENTIFIER ::= { 1 3 6 1 4 1 48710 1 4 3 }
id-oc-gluuOrganization OBJECT IDENTIFIER ::= { 1 3 6 1 4 1 48710 1 4 4 }
id-oc-gluuConfiguration OBJECT IDENTIFIER ::= { 1 3 6 1 4 1 48710 1 4 5 }
id-oc-gluuAttribute OBJECT IDENTIFIER ::= { 1 3 6 1 4 1 48710 1 4 6 }
id-oc-gluuSAMLconfig OBJECT IDENTIFIER ::= { 1 3 6 1 4 1 48710 1 4 7 }
id-oc-gluuInumMap OBJECT IDENTIFIER ::= { 1 3 6 1 4 1 48710 1 4 8 }
id-oc-gluuInvoice OBJECT IDENTIFIER ::= { 1 3 6 1 4 1 48710 1 4 9 }
id-oc-gluuPasswordResetRequest OBJECT IDENTIFIER ::= { 1 3 6 1 4 1 48710 1 4 10 }
id-oc-oxLink OBJECT IDENTIFIER ::= { 1 3 6 1 4 1 48710 1 4 11 }
id-oc-vdapcontainer OBJECT IDENTIFIER ::= { 1 3 6 1 4 1 48710 1 4 12 }
id-oc-vdDirectoryView OBJECT IDENTIFIER ::= { 1 3 6 1 4 1 48710 1 4 13 }
id-oc-vdlabel OBJECT IDENTIFIER ::= { 1 3 6 1 4 1 48710 1 4 14 }
id-oc-oxEntry OBJECT IDENTIFIER ::= { 1 3 6 1 4 1 48710 1 4 15 }
id-oc-oxNode OBJECT IDENTIFIER ::= { 1 3 6 1 4 1 48710 1 4 16 }
id-oc-oxAuthClient OBJECT IDENTIFIER ::= { 1 3 6 1 4 1 48710 1 4 17 }
id-oc-oxAuthCustomScope OBJECT IDENTIFIER ::= { 1 3 6 1 4 1 48710 1 4 18 }
id-oc-oxAuthSessionId-2 OBJECT IDENTIFIER ::= { 1 3 6 1 4 1 48710 1 4 19 }
id-oc-oxAuthConfiguration OBJECT IDENTIFIER ::= { 1 3 6 1 4 1 48710 1 4 20 }
id-oc-oxTrustConfiguration OBJECT IDENTIFIER ::= { 1 3 6 1 4 1 48710 1 4 21 }
id-oc-oxApplicationConfiguration OBJECT IDENTIFIER ::= { 1 3 6 1 4 1 48710 1 4 22 }
id-oc-oxUmaResource OBJECT IDENTIFIER ::= { 1 3 6 1 4 1 48710 1 4 23 }
id-oc-oxUmaResourcePermission OBJECT IDENTIFIER ::= { 1 3 6 1 4 1 48710 1 4 24 }
id-oc-oxAuthGrant OBJECT IDENTIFIER ::= { 1 3 6 1 4 1 48710 1 4 25 }
id-oc-token OBJECT IDENTIFIER ::= { 1 3 6 1 4 1 48710 1 4 26 }
id-oc-oxAuthUmaRPT OBJECT IDENTIFIER ::= { 1 3 6 1 4 1 48710 1 4 27 }
id-oc-oxLiteralNode OBJECT IDENTIFIER ::= { 1 3 6 1 4 1 48710 1 4 28 }
id-oc-oxProxConfiguration OBJECT IDENTIFIER ::= { 1 3 6 1 4 1 48710 1 4 29 }
id-oc-oxProxOp OBJECT IDENTIFIER ::= { 1 3 6 1 4 1 48710 1 4 30 }
id-oc-oxProxClient OBJECT IDENTIFIER ::= { 1 3 6 1 4 1 48710 1 4 31 }
id-oc-oxProxAccessToken OBJECT IDENTIFIER ::= { 1 3 6 1 4 1 48710 1 4 32 }
id-oc-oxScript-2 OBJECT IDENTIFIER ::= { 1 3 6 1 4 1 48710 1 4 33 }
id-oc-oxPushApplication-2 OBJECT IDENTIFIER ::= { 1 3 6 1 4 1 48710 1 4 34 }
id-oc-oxPushDevice OBJECT IDENTIFIER ::= { 1 3 6 1 4 1 48710 1 4 35 }
id-oc-oxCustomScript OBJECT IDENTIFIER ::= { 1 3 6 1 4 1 48710 1 4 36 }
id-oc-oxDeviceRegistration OBJECT IDENTIFIER ::= { 1 3 6 1 4 1 48710 1 4 37 }
id-oc-oxU2fRequest OBJECT IDENTIFIER ::= { 1 3 6 1 4 1 48710 1 4 38 }
id-oc-oxMetric OBJECT IDENTIFIER ::= { 1 3 6 1 4 1 48710 1 4 39 }
id-oc-oxClientAuthorization OBJECT IDENTIFIER ::= { 1 3 6 1 4 1 48710 1 4 40 }
id-oc-oxSectorIdentifier-2 OBJECT IDENTIFIER ::= { 1 3 6 1 4 1 48710 1 4 41 }
id-oc-oxPassportConfiguration OBJECT IDENTIFIER ::= { 1 3 6 1 4 1 48710 1 4 42 }
id-oc-oxShibbolethCASProtocolConfiguration OBJECT IDENTIFIER ::= { 1 3 6 1 4 1 48710 1 4 43 }
id-oc-oxAuthUmaPCT OBJECT IDENTIFIER ::= { 1 3 6 1 4 1 48710 1 4 44 }
id-oc-cache OBJECT IDENTIFIER ::= { 1 3 6 1 4 1 48710 1 4 45 }
id-oc-oxFido2AuthenticationEntry OBJECT IDENTIFIER ::= { 1 3 6 1 4 1 48710 1 4 46 }
id-oc-oxFido2RegistrationEntry OBJECT IDENTIFIER ::= { 1 3 6 1 4 1 48710 1 4 47 }
id-oc-samlAcr OBJECT IDENTIFIER ::= { 1 3 6 1 4 1 48710 1 4 48 }
id-oc-gluuOxtrustStat OBJECT IDENTIFIER ::= { 1 3 6 1 4 1 48710 1 4 49 }
id-oc-gluuApplicationConfiguration OBJECT IDENTIFIER ::= { 1 3 6 1 4 1 48710 1 4 50 }
id-oc-oxExpiredObject OBJECT IDENTIFIER ::= { 1 3 6 1 4 1 48710 1 4 51 }
id-oc-oxRp OBJECT IDENTIFIER ::= { 1 3 6 1 4 1 48710 1 4 52 }
id-oc-cibaRequest OBJECT IDENTIFIER ::= { 1 3 6 1 4 1 48710 1 4 53 }
id-oc-jansStatEntry OBJECT IDENTIFIER ::= { 1 3 6 1 4 1 48710 1 4 54 }

-- Attribute types

-- X-ORIGIN: "Gluu created attribute"
oxAssociatedClient ATTRIBUTE ::= {
  WITH SYNTAX               DistinguishedName
  EQUALITY MATCHING RULE    distinguishedNameMatch
  LDAP-SYNTAX               dn.&id
  LDAP-NAME                 {"oxAssociatedClient", "associatedClient"}
  LDAP-DESC                 "Associate the dn of an OAuth2 client with a person or UMA Resource Set."
  ID                        id-at-oxAssociatedClient }

-- X-ORIGIN: "Gluu created attribute"
associatedPerson ATTRIBUTE ::= {
  WITH SYNTAX               DistinguishedName
  EQUALITY MATCHING RULE    distinguishedNameMatch
  LDAP-SYNTAX               dn.&id
  LDAP-NAME                 {"associatedPerson"}
  LDAP-DESC                 "Reference the dn of a person."
  ID                        id-at-associatedPerson }

-- X-ORIGIN: "Gluu created attribute"
blowfishPassword ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"blowfishPassword"}
  LDAP-DESC                 "Blowfish crypted text"
  ID                        id-at-blowfishPassword }

-- X-ORIGIN: "Gluu created attribute"
county ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"county"}
  LDAP-DESC                 "ISO 3166-1 Alpha-2 Country Code"
  ID                        id-at-county }

-- X-ORIGIN: "Gluu created attribute"
creationDate ATTRIBUTE ::= {
  WITH SYNTAX               GeneralizedTime
  EQUALITY MATCHING RULE    generalizedTimeMatch
  ORDERING MATCHING RULE    generalizedTimeOrderingMatch
  LDAP-SYNTAX               generalizedTime.&id
  LDAP-NAME                 {"creationDate"}
  LDAP-DESC                 "Creation Date used for password reset requests"
  ID                        id-at-creationDate }

-- X-ORIGIN: "Gluu created attribute"
defaultScope ATTRIBUTE ::= {
  WITH SYNTAX               BOOLEAN
  EQUALITY MATCHING RULE    booleanMatch
  LDAP-SYNTAX               boolean.&id
  LDAP-NAME                 {"defaultScope"}
  LDAP-DESC                 "Track the default scope for an custom OAuth2 Scope."
  ID                        id-at-defaultScope }

-- X-ORIGIN: "Gluu created attribute"
deployedAppliances ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"deployedAppliances"}
  LDAP-DESC                 "Track which appliances are deployed at an organization."
  ID                        id-at-deployedAppliances }

-- X-ORIGIN: "Gluu created attribute"
federationRules ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"federationRules"}
  LDAP-DESC                 "Track rules for the federation in Gluu SAML config. Deprecated as multi-party federation management should move to Jagger."
  ID                        id-at-federationRules }

-- X-ORIGIN: "Gluu created attribute"
gluuAddPersonCapability ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuAddPersonCapability"}
  LDAP-DESC                 "Organizational attribute to control whether new users can be added via the oxTrust GUI."
  ID                        id-at-gluuAddPersonCapability }

-- X-ORIGIN: "Gluu created attribute"
gluuAdditionalBandwidth ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuAdditionalBandwidth"}
  LDAP-DESC                 "Track bandwidth requirements for the Gluu Server instance"
  ID                        id-at-gluuAdditionalBandwidth }

-- X-ORIGIN: "Gluu created attribute"
gluuAdditionalMemory ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuAdditionalMemory"}
  LDAP-DESC                 "Track additional memory requirements for the Gluu Server instance."
  ID                        id-at-gluuAdditionalMemory }

-- X-ORIGIN: "Gluu created attribute"
gluuAdditionalUsers ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuAdditionalUsers"}
  LDAP-DESC                 "TODO : use unclear"
  ID                        id-at-gluuAdditionalUsers }

-- X-ORIGIN: "Gluu created attribute"
gluuApplianceDnsServer ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuApplianceDnsServer"}
  LDAP-DESC                 "Persist the DNS server that should be used for the Gluu Server instance."
  ID                        id-at-gluuApplianceDnsServer }

-- X-ORIGIN: "Gluu created attribute"
gluuAppliancePollingInterval ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuAppliancePollingInterval"}
  LDAP-DESC                 "Set the frequency of the health status update of the Gluu Server"
  ID                        id-at-gluuAppliancePollingInterval }

-- X-ORIGIN: "Gluu created attribute"
gluuApplianceUpdateRequestList ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuApplianceUpdateRequestList", "gluuApplianceUpdateReuestList"}
  LDAP-DESC                 "Used by the Gluu Server to request an update"
  ID                        id-at-gluuApplianceUpdateRequestList }

-- X-ORIGIN: "Gluu created attribute"
gluuAttributeViewType ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuAttributeViewType"}
  LDAP-DESC                 "Specify in oxTrust who can view an attribute, admin or user"
  ID                        id-at-gluuAttributeViewType }

-- X-ORIGIN: "Gluu created attribute"
gluuAttributeEditType ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuAttributeEditType"}
  LDAP-DESC                 "Specify in oxTrust who can update an attribute, admin or user"
  ID                        id-at-gluuAttributeEditType }

-- X-ORIGIN: "Gluu created attribute"
gluuAttributeName ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuAttributeName"}
  LDAP-DESC                 "Specify an identifier for an attribute. May be multi-value where an attribute has two names, like givenName and first-name."
  ID                        id-at-gluuAttributeName }

-- X-ORIGIN: "Gluu created attribute"
gluuAttributeOrigin ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuAttributeOrigin"}
  LDAP-DESC                 "Specify the person objectclass associated with the attribute, used for display purposes in oxTrust."
  ID                        id-at-gluuAttributeOrigin }

-- X-ORIGIN: "Gluu created attribute"
gluuAttributeSystemEditType ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuAttributeSystemEditType"}
  LDAP-DESC                 "TODO - still required?"
  ID                        id-at-gluuAttributeSystemEditType }

-- X-ORIGIN: "Gluu created attribute"
gluuAttributeType ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuAttributeType"}
  LDAP-DESC                 "Data type of attribute. Values can be string, photo, numeric, date"
  ID                        id-at-gluuAttributeType }

-- X-ORIGIN: "Gluu created attribute"
gluuAttributeUsageType ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuAttributeUsageType"}
  LDAP-DESC                 "TODO - Usage? Value can be OpenID"
  ID                        id-at-gluuAttributeUsageType }

-- X-ORIGIN: "Gluu created attribute"
gluuBandwidthRX ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuBandwidthRX"}
  LDAP-DESC                 "Track data received by the Gluu Server"
  ID                        id-at-gluuBandwidthRX }

-- X-ORIGIN: "Gluu created attribute"
gluuBandwidthTX ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuBandwidthTX"}
  LDAP-DESC                 "Track data sent by the Gluu Server"
  ID                        id-at-gluuBandwidthTX }

-- X-ORIGIN: "Gluu created attribute"
gluuCategory ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuCategory"}
  LDAP-DESC                 "TODO - in use? Used to group attributes together."
  ID                        id-at-gluuCategory }

-- X-ORIGIN: "Gluu created attribute"
gluuContainerFederation ATTRIBUTE ::= {
  WITH SYNTAX               DistinguishedName
  EQUALITY MATCHING RULE    distinguishedNameMatch
  LDAP-SYNTAX               dn.&id
  LDAP-NAME                 {"gluuContainerFederation"}
  LDAP-DESC                 "SAML Trust Relationship federation info"
  ID                        id-at-gluuContainerFederation }

-- X-ORIGIN: "Gluu created attribute"
gluuCustomMessage ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuCustomMessage"}
  LDAP-DESC                 "oxTrust custom welcome message"
  ID                        id-at-gluuCustomMessage }

-- X-ORIGIN: "Gluu created attribute"
gluuDSstatus ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuDSstatus"}
  LDAP-DESC                 "Monitor health of the instance LDAP server."
  ID                        id-at-gluuDSstatus }

-- X-ORIGIN: "Gluu created attribute"
gluuEntityId ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuEntityId"}
  LDAP-DESC                 "Specifies SAML trust relationship entity ID"
  ID                        id-at-gluuEntityId }

-- X-ORIGIN: "Gluu created attribute"
gluuFaviconImage ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuFaviconImage"}
  LDAP-DESC                 "TODO - Stores URL of favicon"
  ID                        id-at-gluuFaviconImage }

-- X-ORIGIN: "Gluu created attribute"
gluuFederationHostingEnabled ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuFederationHostingEnabled"}
  LDAP-DESC                 "oxTrust flag for the federation feature. Values enabled or disabled."
  ID                        id-at-gluuFederationHostingEnabled }

-- X-ORIGIN: "Gluu created attribute"
gluuFreeDiskSpace ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuFreeDiskSpace"}
  LDAP-DESC                 "Monitor free disk space on the Gluu Server instance"
  ID                        id-at-gluuFreeDiskSpace }

-- X-ORIGIN: "Gluu created attribute"
gluuFreeMemory ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuFreeMemory"}
  LDAP-DESC                 "Monitor free memory on the Gluu Server instance"
  ID                        id-at-gluuFreeMemory }

-- X-ORIGIN: "Gluu created attribute"
gluuFreeSwap ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuFreeSwap"}
  LDAP-DESC                 "Monitor swap space on the Gluu Server instance"
  ID                        id-at-gluuFreeSwap }

-- X-ORIGIN: "Gluu created attribute"
gluuHTTPstatus ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuHTTPstatus"}
  LDAP-DESC                 "Monitor HTTP availability of the Gluu Server instance"
  ID                        id-at-gluuHTTPstatus }

-- X-ORIGIN: "Gluu created attribute"
gluuGroupCount ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuGroupCount"}
  LDAP-DESC                 "Monitor the number of groups. TODO - Remove?"
  ID                        id-at-gluuGroupCount }

-- X-ORIGIN: "Gluu created attribute"
gluuGroupType ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuGroupType"}
  LDAP-DESC                 "Type of Group. Not used."
  ID                        id-at-gluuGroupType }

-- X-ORIGIN: "Gluu created attribute"
gluuGroupVisibility ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuGroupVisibility"}
  LDAP-DESC                 "Group visibility. Not used."
  ID                        id-at-gluuGroupVisibility }

-- X-ORIGIN: "Gluu created attribute"
gluuHostname ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuHostname"}
  LDAP-DESC                 "The hostname of the Gluu Server instance"
  ID                        id-at-gluuHostname }

-- X-ORIGIN: "Gluu created attribute"
gluuInvoiceAmount ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuInvoiceAmount"}
  LDAP-DESC                 "TODO - in use?"
  ID                        id-at-gluuInvoiceAmount }

-- X-ORIGIN: "Gluu created attribute"
gluuInvoiceDate ATTRIBUTE ::= {
  WITH SYNTAX               GeneralizedTime
  EQUALITY MATCHING RULE    generalizedTimeMatch
  ORDERING MATCHING RULE    generalizedTimeOrderingMatch
  LDAP-SYNTAX               generalizedTime.&id
  LDAP-NAME                 {"gluuInvoiceDate"}
  LDAP-DESC                 "TODO - in use?"
  ID                        id-at-gluuInvoiceDate }

-- X-ORIGIN: "Gluu created attribute"
gluuInvoiceLineItemName ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuInvoiceLineItemName"}
  LDAP-DESC                 "TODO - in use?"
  ID                        id-at-gluuInvoiceLineItemName }

-- X-ORIGIN: "Gluu created attribute"
gluuInvoiceNo ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuInvoiceNo"}
  LDAP-DESC                 "TODO - in use?"
  ID                        id-at-gluuInvoiceNo }

-- X-ORIGIN: "Gluu created attribute"
gluuInvoiceNumber ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuInvoiceNumber"}
  LDAP-DESC                 "TODO - in use?"
  ID                        id-at-gluuInvoiceNumber }

-- X-ORIGIN: "Gluu created attribute"
gluuInvoiceProductNumber ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuInvoiceProductNumber"}
  LDAP-DESC                 "TODO - in use?"
  ID                        id-at-gluuInvoiceProductNumber }

-- X-ORIGIN: "Gluu created attribute"
gluuInvoiceQuantity ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuInvoiceQuantity"}
  LDAP-DESC                 "TODO - in use?"
  ID                        id-at-gluuInvoiceQuantity }

-- X-ORIGIN: "Gluu created attribute"
gluuInvoiceStatus ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuInvoiceStatus"}
  LDAP-DESC                 "TODO - in use?"
  ID                        id-at-gluuInvoiceStatus }

-- X-ORIGIN: "Gluu created attribute"
gluuIpAddress ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuIpAddress"}
  LDAP-DESC                 "IP address of the Gluu Server instance"
  ID                        id-at-gluuIpAddress }

-- X-ORIGIN: "Gluu created attribute"
gluuIsFederation ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuIsFederation"}
  LDAP-DESC                 "Used in oxTrust to specify if a SAML Trust Relationship is a federation. It could also be a website"
  ID                        id-at-gluuIsFederation }

-- X-ORIGIN: "Gluu created attribute"
gluuLastUpdate ATTRIBUTE ::= {
  WITH SYNTAX               GeneralizedTime
  EQUALITY MATCHING RULE    generalizedTimeMatch
  ORDERING MATCHING RULE    generalizedTimeOrderingMatch
  LDAP-SYNTAX               generalizedTime.&id
  LDAP-NAME                 {"gluuLastUpdate"}
  LDAP-DESC                 "Monitors last time the server was able to connect to the monitoring system."
  ID                        id-at-gluuLastUpdate }

-- X-ORIGIN: "Gluu created attribute"
gluuLifeRay ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuLifeRay", "TODO-remove"}
  ID                        id-at-gluuLifeRay }

-- X-ORIGIN: "Gluu created attribute"
gluuLoadAvg ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuLoadAvg"}
  LDAP-DESC                 "Montior the average CPU load for a Gluu Server instance."
  ID                        id-at-gluuLoadAvg }

-- X-ORIGIN: "Gluu created attribute"
gluuLogoImage ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuLogoImage"}
  LDAP-DESC                 "Logo used by oxTrust for default look and feel."
  ID                        id-at-gluuLogoImage }

-- X-ORIGIN: "Gluu created attribute"
gluuManageIdentityPermission ATTRIBUTE ::= {
  WITH SYNTAX               BOOLEAN
  EQUALITY MATCHING RULE    booleanMatch
  LDAP-SYNTAX               boolean.&id
  LDAP-NAME                 {"gluuManageIdentityPermission"}
  LDAP-DESC                 "TODO - in use?"
  ID                        id-at-gluuManageIdentityPermission }

-- X-ORIGIN: "Gluu created attribute"
gluuManagedOrganizations ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuManagedOrganizations"}
  LDAP-DESC                 "Used to track with which organizations a person is associated"
  ID                        id-at-gluuManagedOrganizations }

-- X-ORIGIN: "Gluu created attribute"
gluuManager ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuManager"}
  LDAP-DESC                 "Used to specify if a person has the manager role"
  ID                        id-at-gluuManager }

-- X-ORIGIN: "Gluu created attribute"
gluuManagerGroup ATTRIBUTE ::= {
  WITH SYNTAX               DistinguishedName
  EQUALITY MATCHING RULE    distinguishedNameMatch
  LDAP-SYNTAX               dn.&id
  LDAP-NAME                 {"gluuManagerGroup"}
  LDAP-DESC                 "Used in organizatoin entry to specifies the dn of the group that has admin priviledges in oxTrust."
  ID                        id-at-gluuManagerGroup }

-- X-ORIGIN: "Gluu created attribute"
gluuMaxLogSize ATTRIBUTE ::= {
  WITH SYNTAX               INTEGER
  EQUALITY MATCHING RULE    integerMatch
  LDAP-SYNTAX               integer.&id
  LDAP-NAME                 {"gluuMaxLogSize"}
  LDAP-DESC                 "Maximum Log File Size"
  ID                        id-at-gluuMaxLogSize }

-- X-ORIGIN: "Gluu created attribute"
gluuOptOuts ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuOptOuts"}
  LDAP-DESC                 "White pages attributes restricted by person in oxTrust profile management"
  ID                        id-at-gluuOptOuts }

-- X-ORIGIN: "Gluu created attribute"
gluuOrgProfileMgt ATTRIBUTE ::= {
  WITH SYNTAX               BOOLEAN
  EQUALITY MATCHING RULE    booleanMatch
  LDAP-SYNTAX               boolean.&id
  LDAP-NAME                 {"gluuOrgProfileMgt"}
  LDAP-DESC                 "enable or disable profile management feature in oxTrust"
  ID                        id-at-gluuOrgProfileMgt }

-- X-ORIGIN: "Gluu created attribute"
gluuOrgShortName ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuOrgShortName"}
  LDAP-DESC                 "Short description, as few letters as possible, no spaces."
  ID                        id-at-gluuOrgShortName }

-- X-ORIGIN: "Gluu created attribute"
gluuPaidUntil ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuPaidUntil"}
  LDAP-DESC                 "TODO - in use?"
  ID                        id-at-gluuPaidUntil }

-- X-ORIGIN: "Gluu created attribute"
gluuPaymentProcessorTimestamp ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuPaymentProcessorTimestamp"}
  LDAP-DESC                 "TODO - in use?"
  ID                        id-at-gluuPaymentProcessorTimestamp }

-- X-ORIGIN: "Gluu created attribute"
gluuPersonCount ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuPersonCount"}
  LDAP-DESC                 "Monitor the number of people in the LDAP severs for a Gluu Server instance"
  ID                        id-at-gluuPersonCount }

-- X-ORIGIN: "Gluu created attribute"
gluuPrivate ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuPrivate"}
  LDAP-DESC                 "TODO - in use?"
  ID                        id-at-gluuPrivate }

-- X-ORIGIN: "Gluu created attribute"
gluuProStoresUser ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuProStoresUser"}
  LDAP-DESC                 "TODO - remove"
  ID                        id-at-gluuProStoresUser }

-- X-ORIGIN: "Gluu created attribute"
gluuProfileConfiguration ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuProfileConfiguration"}
  LDAP-DESC                 "SAML Trust Relationship attribute"
  ID                        id-at-gluuProfileConfiguration }

-- X-ORIGIN: "Gluu created attribute"
gluuPublishIdpMetadata ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuPublishIdpMetadata"}
  LDAP-DESC                 "Gluu Server flag to publish the IDP metadata via the web server"
  ID                        id-at-gluuPublishIdpMetadata }

-- X-ORIGIN: "Gluu created attribute"
gluuReleasedAttribute ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuReleasedAttribute"}
  LDAP-DESC                 "oxTrust reference for the dn of the released attribute"
  ID                        id-at-gluuReleasedAttribute }

-- X-ORIGIN: "Gluu created attribute"
gluuResizeInitiated ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuResizeInitiated"}
  LDAP-DESC                 "TODO - in use?"
  ID                        id-at-gluuResizeInitiated }

-- X-ORIGIN: "Gluu created attribute"
gluuRulesAccepted ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuRulesAccepted"}
  LDAP-DESC                 "TODO - use unknown for Gluu SAML config"
  ID                        id-at-gluuRulesAccepted }

-- X-ORIGIN: "Gluu created attribute"
gluuSAML1URI ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuSAML1URI"}
  LDAP-DESC                 "SAML 1 uri of attribute"
  ID                        id-at-gluuSAML1URI }

-- X-ORIGIN: "Gluu created attribute"
gluuSAML2URI ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuSAML2URI"}
  LDAP-DESC                 "SAML 2 uri of attribute"
  ID                        id-at-gluuSAML2URI }

-- X-ORIGIN: "Gluu created attribute"
gluuSAMLMetaDataFilter ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuSAMLMetaDataFilter"}
  LDAP-DESC                 "Metadata filter in SAML trust relationship"
  ID                        id-at-gluuSAMLMetaDataFilter }

-- X-ORIGIN: "Gluu created attribute"
gluuSAMLTrustEngine ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuSAMLTrustEngine"}
  LDAP-DESC                 "SAML trust relationship configuration"
  ID                        id-at-gluuSAMLTrustEngine }

-- X-ORIGIN: "Gluu created attribute"
gluuSAMLmaxRefreshDelay ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuSAMLmaxRefreshDelay"}
  LDAP-DESC                 "SAML trust relationship refresh time"
  ID                        id-at-gluuSAMLmaxRefreshDelay }

-- X-ORIGIN: "Gluu created attribute"
gluuSAMLspMetaDataFN ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuSAMLspMetaDataFN"}
  LDAP-DESC                 "SAML Trust Relationship file location of metadata"
  ID                        id-at-gluuSAMLspMetaDataFN }

-- X-ORIGIN: "Gluu created attribute"
gluuSAMLspMetaDataSourceType ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuSAMLspMetaDataSourceType"}
  LDAP-DESC                 "SAML Trust Relationship SP metadata type - file, URI, federation"
  ID                        id-at-gluuSAMLspMetaDataSourceType }

-- X-ORIGIN: "Gluu created attribute"
gluuSAMLspMetaDataURL ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuSAMLspMetaDataURL"}
  LDAP-DESC                 "SAML Trust Relationship URI location of metadata"
  ID                        id-at-gluuSAMLspMetaDataURL }

-- X-ORIGIN: "Gluu created attribute"
gluuSLAManager ATTRIBUTE ::= {
  WITH SYNTAX               BOOLEAN
  EQUALITY MATCHING RULE    booleanMatch
  LDAP-SYNTAX               boolean.&id
  LDAP-NAME                 {"gluuSLAManager"}
  LDAP-DESC                 "Specifies if the person has the SLA manager role"
  ID                        id-at-gluuSLAManager }

-- X-ORIGIN: "Gluu created attribute"
gluuSPTR ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuSPTR"}
  LDAP-DESC                 "TODO - in use?"
  ID                        id-at-gluuSPTR }

-- X-ORIGIN: "Gluu created attribute"
gluuScimEnabled ATTRIBUTE ::= {
  WITH SYNTAX               BOOLEAN
  EQUALITY MATCHING RULE    caseIgnoreMatch
  SUBSTRINGS MATCHING RULE  caseIgnoreSubstringsMatch
  LDAP-SYNTAX               boolean.&id
  LDAP-NAME                 {"gluuScimEnabled"}
  LDAP-DESC                 "oxTrust SCIM feature - enabled or disabled"
  ID                        id-at-gluuScimEnabled }

-- X-ORIGIN: "Gluu created attribute"
gluuShibAssertionsIssued ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuShibAssertionsIssued"}
  LDAP-DESC                 "Monitors activity of Gluu Server Shibboleth IDP"
  ID                        id-at-gluuShibAssertionsIssued }

-- X-ORIGIN: "Gluu created attribute"
gluuShibFailedAuth ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuShibFailedAuth"}
  LDAP-DESC                 "Monitors failed login attempts on Gluu Server Shibboleth IDP"
  ID                        id-at-gluuShibFailedAuth }

-- X-ORIGIN: "Gluu created attribute"
gluuShibSecurityEvents ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuShibSecurityEvents"}
  LDAP-DESC                 "Monitors security events on Gluu Server Shibboleth IDP"
  ID                        id-at-gluuShibSecurityEvents }

-- X-ORIGIN: "Gluu created attribute"
gluuShibSuccessfulAuths ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuShibSuccessfulAuths"}
  LDAP-DESC                 "Monitors login attempts on Gluu Server Shibboleth IDP"
  ID                        id-at-gluuShibSuccessfulAuths }

-- X-ORIGIN: "Gluu created attribute"
gluuSmtpFromEmailAddress ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuSmtpFromEmailAddress"}
  LDAP-DESC                 "Gluu Server SMTP configuration"
  ID                        id-at-gluuSmtpFromEmailAddress }

-- X-ORIGIN: "Gluu created attribute"
gluuSmtpFromName ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuSmtpFromName"}
  LDAP-DESC                 "SMTP From Name"
  ID                        id-at-gluuSmtpFromName }

-- X-ORIGIN: "Gluu created attribute"
gluuSmtpHost ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuSmtpHost"}
  LDAP-DESC                 "SMTP Host"
  ID                        id-at-gluuSmtpHost }

-- X-ORIGIN: "Gluu created attribute"
gluuSmtpPassword ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuSmtpPassword"}
  LDAP-DESC                 "SMTP User Password"
  ID                        id-at-gluuSmtpPassword }

-- X-ORIGIN: "Gluu created attribute"
gluuSmtpPort ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuSmtpPort"}
  LDAP-DESC                 "SMTP Port"
  ID                        id-at-gluuSmtpPort }

-- X-ORIGIN: "Gluu created attribute"
gluuSmtpRequiresAuthentication ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuSmtpRequiresAuthentication"}
  LDAP-DESC                 "SMTP Requires Authentication"
  ID                        id-at-gluuSmtpRequiresAuthentication }

-- X-ORIGIN: "Gluu created attribute"
gluuSmtpRequiresSsl ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuSmtpRequiresSsl"}
  LDAP-DESC                 "SMTP Requires SSL"
  ID                        id-at-gluuSmtpRequiresSsl }

-- X-ORIGIN: "Gluu created attribute"
gluuSmtpUserName ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuSmtpUserName"}
  LDAP-DESC                 "SMTP User Name"
  ID                        id-at-gluuSmtpUserName }

-- X-ORIGIN: "Gluu created attribute"
gluuSpecificRelyingPartyConfig ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuSpecificRelyingPartyConfig"}
  LDAP-DESC                 "SAML Trust Relationship configuration"
  ID                        id-at-gluuSpecificRelyingPartyConfig }

-- X-ORIGIN: "Gluu created attribute"
gluuSslExpiry ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuSslExpiry"}
  LDAP-DESC                 "SAML Trust Relationship configuration"
  ID                        id-at-gluuSslExpiry }

-- X-ORIGIN: "Gluu created attribute"
gluuStatus ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuStatus"}
  LDAP-DESC                 "Status of the entry, used by many objectclasses"
  ID                        id-at-gluuStatus }

-- X-ORIGIN: "Gluu created attribute"
gluuSystemUptime ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuSystemUptime"}
  LDAP-DESC                 "Monitors how long the Gluu Server instance has been running."
  ID                        id-at-gluuSystemUptime }

-- X-ORIGIN: "Gluu created attribute"
gluuTargetRAM ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuTargetRAM"}
  LDAP-DESC                 "Monitors total available RAM on Gluu Server instance"
  ID                        id-at-gluuTargetRAM }

-- X-ORIGIN: "Gluu created attribute"
gluuTempFaviconImage ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuTempFaviconImage"}
  LDAP-DESC                 "Store location for upload of Favicon"
  ID                        id-at-gluuTempFaviconImage }

-- X-ORIGIN: "Gluu created attribute"
gluuThemeColor ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuThemeColor"}
  LDAP-DESC                 "oxTrust login page configuration"
  ID                        id-at-gluuThemeColor }

-- X-ORIGIN: "Gluu created attribute"
gluuTrustContact ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuTrustContact"}
  LDAP-DESC                 "oxTrust login page configuration"
  ID                        id-at-gluuTrustContact }

-- X-ORIGIN: "Gluu created attribute"
gluuTrustDeconstruction ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuTrustDeconstruction"}
  LDAP-DESC                 "TODO - in use?"
  ID                        id-at-gluuTrustDeconstruction }

-- X-ORIGIN: "Gluu created attribute"
gluuUrl ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuUrl"}
  LDAP-DESC                 "Gluu instance URL"
  ID                        id-at-gluuUrl }

-- X-ORIGIN: "Gluu created attribute"
gluuVDSenabled ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuVDSenabled"}
  LDAP-DESC                 "oxTrust VDS enabled or disabled"
  ID                        id-at-gluuVDSenabled }

-- X-ORIGIN: "Gluu created attribute"
gluuVDSstatus ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuVDSstatus"}
  LDAP-DESC                 "Gluu VDS configuration"
  ID                        id-at-gluuVDSstatus }

-- X-ORIGIN: "Gluu created attribute"
gluuValidationLog ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuValidationLog"}
  ID                        id-at-gluuValidationLog }

-- X-ORIGIN: "Gluu created attribute"
gluuValidationStatus ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuValidationStatus"}
  ID                        id-at-gluuValidationStatus }

-- X-ORIGIN: "Gluu created attribute"
gluuVdsCacheRefreshEnabled ATTRIBUTE ::= {
  WITH SYNTAX               BOOLEAN
  EQUALITY MATCHING RULE    booleanMatch
  LDAP-SYNTAX               boolean.&id
  LDAP-NAME                 {"gluuVdsCacheRefreshEnabled"}
  ID                        id-at-gluuVdsCacheRefreshEnabled }

-- X-ORIGIN: "Gluu created attribute"
gluuVdsCacheRefreshLastUpdate ATTRIBUTE ::= {
  WITH SYNTAX               GeneralizedTime
  EQUALITY MATCHING RULE    generalizedTimeMatch
  ORDERING MATCHING RULE    generalizedTimeOrderingMatch
  LDAP-SYNTAX               generalizedTime.&id
  LDAP-NAME                 {"gluuVdsCacheRefreshLastUpdate"}
  ID                        id-at-gluuVdsCacheRefreshLastUpdate }

-- X-ORIGIN: "Gluu created attribute"
gluuVdsCacheRefreshLastUpdateCount ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuVdsCacheRefreshLastUpdateCount"}
  ID                        id-at-gluuVdsCacheRefreshLastUpdateCount }

-- X-ORIGIN: "Gluu created attribute"
gluuVdsCacheRefreshPollingInterval ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuVdsCacheRefreshPollingInterval"}
  ID                        id-at-gluuVdsCacheRefreshPollingInterval }

-- X-ORIGIN: "Gluu created attribute"
gluuVdsCacheRefreshProblemCount ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuVdsCacheRefreshProblemCount"}
  ID                        id-at-gluuVdsCacheRefreshProblemCount }

-- X-ORIGIN: "Gluu created attribute"
gluuWhitePagesEnabled ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuWhitePagesEnabled"}
  ID                        id-at-gluuWhitePagesEnabled }

-- X-ORIGIN: "Gluu created attribute"
gluuWhitePagesListed ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuWhitePagesListed"}
  LDAP-DESC                 "Allow Publication"
  ID                        id-at-gluuWhitePagesListed }

-- X-ORIGIN: "Gluu created attribute"
iname ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"iname"}
  ID                        id-at-iname }

-- X-ORIGIN: "Gluu created attribute"
inum ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"inum"}
  LDAP-DESC                 "XRI i-number"
  ID                        id-at-inum }

-- X-ORIGIN: "Gluu created attribute"
inumFN ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"inumFN"}
  LDAP-DESC                 "XRI i-number sans punctuation"
  ID                        id-at-inumFN }

-- X-ORIGIN: "Gluu created attribute"
literalBinaryValue ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"literalBinaryValue"}
  LDAP-DESC                 "OX literalValue"
  ID                        id-at-literalBinaryValue }

-- X-ORIGIN: "Gluu created attribute"
literalValue ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"literalValue"}
  LDAP-DESC                 "OX literalValue"
  ID                        id-at-literalValue }

-- X-ORIGIN: "Gluu created attribute"
memberOf ATTRIBUTE ::= {
  WITH SYNTAX               DistinguishedName
  EQUALITY MATCHING RULE    distinguishedNameMatch
  LDAP-SYNTAX               dn.&id
  LDAP-NAME                 {"memberOf"}
  ID                        id-at-memberOf }

-- X-ORIGIN: "Gluu created attribute"
nonProfit ATTRIBUTE ::= {
  WITH SYNTAX               BOOLEAN
  EQUALITY MATCHING RULE    booleanMatch
  LDAP-SYNTAX               boolean.&id
  LDAP-NAME                 {"nonProfit"}
  LDAP-DESC                 "TODO - in use?"
  ID                        id-at-nonProfit }

-- X-ORIGIN: "Gluu created attribute"
organizationalOwner ATTRIBUTE ::= {
  WITH SYNTAX               DistinguishedName
  EQUALITY MATCHING RULE    distinguishedNameMatch
  LDAP-SYNTAX               dn.&id
  LDAP-NAME                 {"organizationalOwner"}
  LDAP-DESC                 "OX organizationalOwner"
  ID                        id-at-organizationalOwner }

-- X-ORIGIN: "Gluu created attribute"
oxAmHost ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAmHost"}
  LDAP-DESC                 "am host"
  ID                        id-at-oxAmHost }

-- X-ORIGIN: "Gluu created attribute"
oxAuthClaimName ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthClaimName"}
  LDAP-DESC                 "Used by oxAuth in conjunction with gluuttributeName to map claims to attributes in LDAP."
  ID                        id-at-oxAuthClaimName }

-- X-ORIGIN: "Gluu created attribute"
oxAuthAppType ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthAppType"}
  LDAP-DESC                 "oxAuth App Type"
  ID                        id-at-oxAuthAppType }

-- X-ORIGIN: "Gluu created attribute"
authnTime ATTRIBUTE ::= {
  WITH SYNTAX               GeneralizedTime
  EQUALITY MATCHING RULE    generalizedTimeMatch
  ORDERING MATCHING RULE    generalizedTimeOrderingMatch
  LDAP-SYNTAX               generalizedTime.&id
  LDAP-NAME                 {"authnTime"}
  LDAP-DESC                 "oxAuth Authentication Time"
  ID                        id-at-authnTime }

-- X-ORIGIN: "Gluu created attribute"
authzCode ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"authzCode"}
  LDAP-DESC                 "oxAuth authorization code"
  ID                        id-at-authzCode }

-- X-ORIGIN: "Gluu created attribute"
oxAuthClaim ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthClaim"}
  LDAP-DESC                 "oxAuth Attribute Claim"
  ID                        id-at-oxAuthClaim }

-- X-ORIGIN: "Gluu created attribute"
oxAuthGroupClaims ATTRIBUTE ::= {
  WITH SYNTAX               BOOLEAN
  EQUALITY MATCHING RULE    booleanMatch
  LDAP-SYNTAX               boolean.&id
  LDAP-NAME                 {"oxAuthGroupClaims"}
  LDAP-DESC                 "oxAuth Group Attribute Claims (true or false)"
  ID                        id-at-oxAuthGroupClaims }

-- X-ORIGIN: "Gluu created attribute"
oxAuthClientId ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthClientId"}
  LDAP-DESC                 "oxAuth Client id"
  ID                        id-at-oxAuthClientId }

-- X-ORIGIN: "Gluu created attribute"
clnId ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"clnId"}
  LDAP-DESC                 "oxAuth Client id"
  ID                        id-at-clnId }

-- X-ORIGIN: "Gluu created attribute"
oxAuthClientIdIssuedAt ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthClientIdIssuedAt"}
  LDAP-DESC                 "oxAuth Client Issued At"
  ID                        id-at-oxAuthClientIdIssuedAt }

-- X-ORIGIN: "Gluu created attribute"
oxAuthClientSecret ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthClientSecret"}
  LDAP-DESC                 "oxAuth Client Secret"
  ID                        id-at-oxAuthClientSecret }

-- X-ORIGIN: "Gluu created attribute"
oxAuthClientSecretExpiresAt ATTRIBUTE ::= {
  WITH SYNTAX               GeneralizedTime
  EQUALITY MATCHING RULE    generalizedTimeMatch
  ORDERING MATCHING RULE    generalizedTimeOrderingMatch
  LDAP-SYNTAX               generalizedTime.&id
  LDAP-NAME                 {"oxAuthClientSecretExpiresAt"}
  LDAP-DESC                 "Date client expires"
  ID                        id-at-oxAuthClientSecretExpiresAt }

-- X-ORIGIN: "Gluu created attribute"
oxAuthClientURI ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthClientURI"}
  LDAP-DESC                 "oxAuth Client URI"
  ID                        id-at-oxAuthClientURI }

-- X-ORIGIN: "Gluu created attribute"
oxAuthConfDynamic ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthConfDynamic"}
  LDAP-DESC                 "oxAuth Dynamic Configuration"
  ID                        id-at-oxAuthConfDynamic }

-- X-ORIGIN: "Gluu created attribute"
oxAuthConfErrors ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthConfErrors"}
  LDAP-DESC                 "oxAuth Errors Configuration"
  ID                        id-at-oxAuthConfErrors }

-- X-ORIGIN: "Gluu created attribute"
oxAuthConfStatic ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthConfStatic"}
  LDAP-DESC                 "oxAuth Static Configuration"
  ID                        id-at-oxAuthConfStatic }

-- X-ORIGIN: "Gluu created attribute"
oxAuthConfWebKeys ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthConfWebKeys"}
  LDAP-DESC                 "oxAuth Web Keys Configuration"
  ID                        id-at-oxAuthConfWebKeys }

-- X-ORIGIN: "Gluu created attribute"
oxAuthContact ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthContact"}
  LDAP-DESC                 "oxAuth Contact"
  ID                        id-at-oxAuthContact }

-- X-ORIGIN: "Gluu created attribute"
iat ATTRIBUTE ::= {
  WITH SYNTAX               GeneralizedTime
  EQUALITY MATCHING RULE    generalizedTimeMatch
  ORDERING MATCHING RULE    generalizedTimeOrderingMatch
  LDAP-SYNTAX               generalizedTime.&id
  LDAP-NAME                 {"iat"}
  LDAP-DESC                 "oxAuth Creation"
  ID                        id-at-iat }

-- X-ORIGIN: "Gluu created attribute"
oxAuthDefaultAcrValues ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthDefaultAcrValues"}
  LDAP-DESC                 "oxAuth Default Acr Values"
  ID                        id-at-oxAuthDefaultAcrValues }

-- X-ORIGIN: "Gluu created attribute"
oxAuthDefaultMaxAge ATTRIBUTE ::= {
  WITH SYNTAX               INTEGER
  EQUALITY MATCHING RULE    integerMatch
  LDAP-SYNTAX               integer.&id
  LDAP-NAME                 {"oxAuthDefaultMaxAge"}
  LDAP-DESC                 "oxAuth Default Max Age"
  ID                        id-at-oxAuthDefaultMaxAge }

-- X-ORIGIN: "Gluu created attribute"
exp ATTRIBUTE ::= {
  WITH SYNTAX               GeneralizedTime
  EQUALITY MATCHING RULE    generalizedTimeMatch
  ORDERING MATCHING RULE    generalizedTimeOrderingMatch
  LDAP-SYNTAX               generalizedTime.&id
  LDAP-NAME                 {"exp"}
  LDAP-DESC                 "oxAuth Expiration"
  ID                        id-at-exp }

-- X-ORIGIN: "Gluu created attribute"
grtId ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"grtId"}
  LDAP-DESC                 "oxAuth grant id"
  ID                        id-at-grtId }

-- X-ORIGIN: "Gluu created attribute"
oxAuthGrantType ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthGrantType"}
  LDAP-DESC                 "oxAuth Grant Type"
  ID                        id-at-oxAuthGrantType }

-- X-ORIGIN: "Gluu created attribute"
grtTyp ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"grtTyp"}
  LDAP-DESC                 "oxAuth Grant Type"
  ID                        id-at-grtTyp }

-- X-ORIGIN: "Gluu created attribute"
oxAuthIdTokenEncryptedResponseAlg ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthIdTokenEncryptedResponseAlg"}
  LDAP-DESC                 "oxAuth ID Token Encrypted Response Alg"
  ID                        id-at-oxAuthIdTokenEncryptedResponseAlg }

-- X-ORIGIN: "Gluu created attribute"
oxAuthIdTokenEncryptedResponseEnc ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthIdTokenEncryptedResponseEnc"}
  LDAP-DESC                 "oxAuth ID Token Encrypted Response Enc"
  ID                        id-at-oxAuthIdTokenEncryptedResponseEnc }

-- X-ORIGIN: "Gluu created attribute"
oxAuthIdTokenSignedResponseAlg ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthIdTokenSignedResponseAlg"}
  LDAP-DESC                 "oxAuth ID Token Signed Response Alg"
  ID                        id-at-oxAuthIdTokenSignedResponseAlg }

-- X-ORIGIN: "Gluu created attribute"
oxAuthInitiateLoginURI ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthInitiateLoginURI"}
  LDAP-DESC                 "oxAuth Initiate Login URI"
  ID                        id-at-oxAuthInitiateLoginURI }

-- X-ORIGIN: "Gluu created attribute"
oxAuthJwksURI ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthJwksURI"}
  LDAP-DESC                 "oxAuth JWKs URI"
  ID                        id-at-oxAuthJwksURI }

-- X-ORIGIN: "Gluu created attribute"
oxAuthJwks ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthJwks"}
  LDAP-DESC                 "oxAuth JWKs"
  ID                        id-at-oxAuthJwks }

-- X-ORIGIN: "Gluu created attribute"
jwtReq ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"jwtReq"}
  LDAP-DESC                 "oxAuth JWT Request"
  ID                        id-at-jwtReq }

-- X-ORIGIN: "Gluu created attribute"
oxAuthLogoURI ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthLogoURI"}
  LDAP-DESC                 "oxAuth Logo URI"
  ID                        id-at-oxAuthLogoURI }

-- X-ORIGIN: "Gluu created attribute"
nnc ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"nnc"}
  LDAP-DESC                 "oxAuth nonce"
  ID                        id-at-nnc }

-- X-ORIGIN: "Gluu created attribute"
oxSessionState ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxSessionState"}
  LDAP-DESC                 "oxAuth Session State"
  ID                        id-at-oxSessionState }

-- X-ORIGIN: "Gluu created attribute"
oxAuthPermissionGrantedMap ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthPermissionGrantedMap"}
  LDAP-DESC                 "oxAuth Permission Granted Map"
  ID                        id-at-oxAuthPermissionGrantedMap }

-- X-ORIGIN: "Gluu created attribute"
oxAuthPersistentJWT ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthPersistentJWT"}
  LDAP-DESC                 "oxAuth Persistent JWT"
  ID                        id-at-oxAuthPersistentJWT }

-- X-ORIGIN: "Gluu created attribute"
oxAuthPolicyURI ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthPolicyURI"}
  LDAP-DESC                 "oxAuth Policy URI"
  ID                        id-at-oxAuthPolicyURI }

-- X-ORIGIN: "Gluu created attribute"
oxAuthLogoutURI ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthLogoutURI"}
  LDAP-DESC                 "oxAuth Policy URI"
  ID                        id-at-oxAuthLogoutURI }

-- X-ORIGIN: "Gluu created attribute"
oxAuthLogoutSessionRequired ATTRIBUTE ::= {
  WITH SYNTAX               BOOLEAN
  EQUALITY MATCHING RULE    booleanMatch
  LDAP-SYNTAX               boolean.&id
  LDAP-NAME                 {"oxAuthLogoutSessionRequired"}
  LDAP-DESC                 "oxAuth Policy URI"
  ID                        id-at-oxAuthLogoutSessionRequired }

-- X-ORIGIN: "Gluu created attribute"
oxAuthPostLogoutRedirectURI ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthPostLogoutRedirectURI"}
  LDAP-DESC                 "oxAuth Post Logout Redirect URI"
  ID                        id-at-oxAuthPostLogoutRedirectURI }

-- X-ORIGIN: "Gluu created attribute"
oxAuthRedirectURI ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthRedirectURI"}
  LDAP-DESC                 "oxAuth Redirect URI"
  ID                        id-at-oxAuthRedirectURI }

-- X-ORIGIN: "Gluu created attribute"
oxAuthRegistrationAccessToken ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthRegistrationAccessToken"}
  LDAP-DESC                 "oxAuth Registration Access Token"
  ID                        id-at-oxAuthRegistrationAccessToken }

-- X-ORIGIN: "Gluu created attribute"
oxAuthReleasedScope ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthReleasedScope"}
  LDAP-DESC                 "oxAuth released scope attribute"
  ID                        id-at-oxAuthReleasedScope }

-- X-ORIGIN: "Gluu created attribute"
oxAuthRequestObjectSigningAlg ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthRequestObjectSigningAlg"}
  LDAP-DESC                 "oxAuth Request Object Signing Alg"
  ID                        id-at-oxAuthRequestObjectSigningAlg }

-- X-ORIGIN: "Gluu created attribute"
oxAuthRequestObjectEncryptionAlg ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthRequestObjectEncryptionAlg"}
  LDAP-DESC                 "oxAuth Request Object Encryption Alg"
  ID                        id-at-oxAuthRequestObjectEncryptionAlg }

-- X-ORIGIN: "Gluu created attribute"
oxAuthRequestObjectEncryptionEnc ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthRequestObjectEncryptionEnc"}
  LDAP-DESC                 "oxAuth Request Object Encryption Enc"
  ID                        id-at-oxAuthRequestObjectEncryptionEnc }

-- X-ORIGIN: "Gluu created attribute"
oxAuthRequestURI ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthRequestURI"}
  LDAP-DESC                 "oxAuth Request URI"
  ID                        id-at-oxAuthRequestURI }

-- X-ORIGIN: "Gluu created attribute"
oxAuthRequireAuthTime ATTRIBUTE ::= {
  WITH SYNTAX               BOOLEAN
  EQUALITY MATCHING RULE    booleanMatch
  LDAP-SYNTAX               boolean.&id
  LDAP-NAME                 {"oxAuthRequireAuthTime"}
  LDAP-DESC                 "oxAuth Require Authentication Time"
  ID                        id-at-oxAuthRequireAuthTime }

-- X-ORIGIN: "Gluu created attribute"
oxAuthResponseType ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthResponseType"}
  LDAP-DESC                 "oxAuth Response Type"
  ID                        id-at-oxAuthResponseType }

-- X-ORIGIN: "Gluu created attribute"
oxAuthScope ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthScope"}
  LDAP-DESC                 "oxAuth Attribute Scope"
  ID                        id-at-oxAuthScope }

-- X-ORIGIN: "Gluu created attribute"
scp ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"scp"}
  LDAP-DESC                 "oxAuth Attribute Scope"
  ID                        id-at-scp }

-- X-ORIGIN: "Gluu created attribute"
oxScopeType ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxScopeType"}
  LDAP-DESC                 "OX Attribute Scope type"
  ID                        id-at-oxScopeType }

-- X-ORIGIN: "Gluu created attribute"
oxAuthSectorIdentifierURI ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthSectorIdentifierURI"}
  LDAP-DESC                 "oxAuth Sector Identifier URI"
  ID                        id-at-oxAuthSectorIdentifierURI }

-- X-ORIGIN: "Gluu created attribute"
oxAuthSignedResponseAlg ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthSignedResponseAlg"}
  LDAP-DESC                 "oxAuth Signed Response Alg"
  ID                        id-at-oxAuthSignedResponseAlg }

-- X-ORIGIN: "Gluu created attribute"
oxAuthSkipAuthorization ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthSkipAuthorization"}
  LDAP-DESC                 "oxAuth skip authorization attribute"
  ID                        id-at-oxAuthSkipAuthorization }

-- X-ORIGIN: "Gluu created attribute"
oxAuthSubjectType ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthSubjectType"}
  LDAP-DESC                 "oxAuth Subject Type"
  ID                        id-at-oxAuthSubjectType }

-- X-ORIGIN: "Gluu created attribute"
tknCde ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"tknCde"}
  LDAP-DESC                 "oxAuth Token Code"
  ID                        id-at-tknCde }

-- X-ORIGIN: "Gluu created attribute"
oxAuthTokenEndpointAuthMethod ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthTokenEndpointAuthMethod"}
  LDAP-DESC                 "oxAuth Token Endpoint Auth Method"
  ID                        id-at-oxAuthTokenEndpointAuthMethod }

-- X-ORIGIN: "Gluu created attribute"
oxAuthTokenEndpointAuthSigningAlg ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthTokenEndpointAuthSigningAlg"}
  LDAP-DESC                 "oxAuth Token Endpoint Auth Signing Alg"
  ID                        id-at-oxAuthTokenEndpointAuthSigningAlg }

-- X-ORIGIN: "Gluu created attribute"
tknTyp ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"tknTyp"}
  LDAP-DESC                 "oxAuth Token Type"
  ID                        id-at-tknTyp }

-- X-ORIGIN: "Gluu created attribute"
oxAuthTosURI ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthTosURI"}
  LDAP-DESC                 "oxAuth TOS URI"
  ID                        id-at-oxAuthTosURI }

-- X-ORIGIN: "Gluu created attribute"
oxAuthTrustedClient ATTRIBUTE ::= {
  WITH SYNTAX               BOOLEAN
  EQUALITY MATCHING RULE    booleanMatch
  LDAP-SYNTAX               boolean.&id
  LDAP-NAME                 {"oxAuthTrustedClient"}
  LDAP-DESC                 "oxAuth Trusted Client"
  ID                        id-at-oxAuthTrustedClient }

-- X-ORIGIN: "Gluu created attribute"
oxAuthUmaScope ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthUmaScope"}
  LDAP-DESC                 "URI reference of scope descriptor"
  ID                        id-at-oxAuthUmaScope }

-- X-ORIGIN: "Gluu created attribute"
oxAuthUserDN ATTRIBUTE ::= {
  WITH SYNTAX               DistinguishedName
  EQUALITY MATCHING RULE    distinguishedNameMatch
  LDAP-SYNTAX               dn.&id
  LDAP-NAME                 {"oxAuthUserDN"}
  LDAP-DESC                 "oxAuth User DN"
  ID                        id-at-oxAuthUserDN }

-- X-ORIGIN: "Gluu created attribute"
oxAuthUserId ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthUserId", "usrId"}
  LDAP-DESC                 "oxAuth user id"
  ID                        id-at-oxAuthUserId }

-- X-ORIGIN: "Gluu created attribute"
oxAuthUserInfoEncryptedResponseAlg ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthUserInfoEncryptedResponseAlg"}
  LDAP-DESC                 "oxAuth User Info Encrypted Response Alg"
  ID                        id-at-oxAuthUserInfoEncryptedResponseAlg }

-- X-ORIGIN: "Gluu created attribute"
oxAuthUserInfoEncryptedResponseEnc ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthUserInfoEncryptedResponseEnc"}
  LDAP-DESC                 "oxAuth User Info Encrypted Response Enc"
  ID                        id-at-oxAuthUserInfoEncryptedResponseEnc }

-- X-ORIGIN: "Gluu created attribute"
oxAuthExtraConf ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthExtraConf"}
  LDAP-DESC                 "oxAuth additional configuration"
  ID                        id-at-oxAuthExtraConf }

-- X-ORIGIN: "Gluu created attribute"
oxAuthX509PEM ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthX509PEM"}
  LDAP-DESC                 "oxAuth x509 in PEM format"
  ID                        id-at-oxAuthX509PEM }

-- X-ORIGIN: "Gluu created attribute"
oxAuthX509URL ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthX509URL"}
  LDAP-DESC                 "oxAuth x509 URL"
  ID                        id-at-oxAuthX509URL }

-- X-ORIGIN: "Gluu created attribute"
oxAuthenticationMode ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthenticationMode"}
  ID                        id-at-oxAuthenticationMode }

-- X-ORIGIN: "Gluu created attribute"
acr ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"acr"}
  ID                        id-at-acr }

-- X-ORIGIN: "Gluu created attribute"
oxTrustAuthenticationMode ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxTrustAuthenticationMode"}
  ID                        id-at-oxTrustAuthenticationMode }

-- X-ORIGIN: "Gluu created attribute"
oxConfigurationCode ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxConfigurationCode"}
  LDAP-DESC                 "ox configuration code"
  ID                        id-at-oxConfigurationCode }

-- X-ORIGIN: "Gluu created attribute"
oxCreationTimestamp ATTRIBUTE ::= {
  WITH SYNTAX               GeneralizedTime
  EQUALITY MATCHING RULE    generalizedTimeMatch
  ORDERING MATCHING RULE    generalizedTimeOrderingMatch
  LDAP-SYNTAX               generalizedTime.&id
  LDAP-NAME                 {"oxCreationTimestamp"}
  LDAP-DESC                 "Registration time"
  ID                        id-at-oxCreationTimestamp }

-- X-ORIGIN: "Gluu created attribute"
oxDomain ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxDomain"}
  LDAP-DESC                 "domain"
  ID                        id-at-oxDomain }

-- X-ORIGIN: "Gluu created attribute"
oxExternalUid ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxExternalUid"}
  ID                        id-at-oxExternalUid }

-- X-ORIGIN: "Gluu created attribute"
oxOTPCache ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxOTPCache"}
  LDAP-DESC                 "Stores a used OTP to prevent a hacker from using it again. Complementary to oxExternalUid attribute"
  ID                        id-at-oxOTPCache }

-- X-ORIGIN: "Gluu created attribute"
oxFaviconImage ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxFaviconImage"}
  LDAP-DESC                 "URI for a graphic icon"
  ID                        id-at-oxFaviconImage }

-- X-ORIGIN: "Gluu created attribute"
oxGroup ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxGroup"}
  LDAP-DESC                 "User group"
  ID                        id-at-oxGroup }

-- X-ORIGIN: "Gluu created attribute"
oxGuid ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxGuid"}
  LDAP-DESC                 "A random string to mark temporary tokens"
  ID                        id-at-oxGuid }

-- X-ORIGIN: "Gluu created attribute"
uuid ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"uuid"}
  LDAP-DESC                 "Unique identifier"
  ID                        id-at-uuid }

-- X-ORIGIN: "Gluu created attribute"
oxHost ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxHost"}
  LDAP-DESC                 "ox host"
  ID                        id-at-oxHost }

-- X-ORIGIN: "Gluu created attribute"
oxIDPAuthentication ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxIDPAuthentication"}
  LDAP-DESC                 "Custom IDP authentication configuration"
  ID                        id-at-oxIDPAuthentication }

-- X-ORIGIN: "Gluu created attribute"
oxIconUrl ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxIconUrl"}
  LDAP-DESC                 "ox icon url"
  ID                        id-at-oxIconUrl }

-- X-ORIGIN: "Gluu created attribute"
oxId ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxId"}
  LDAP-DESC                 "Identifier"
  ID                        id-at-oxId }

-- X-ORIGIN: "Gluu created attribute"
oxAsJwt ATTRIBUTE ::= {
  WITH SYNTAX               BOOLEAN
  EQUALITY MATCHING RULE    booleanMatch
  LDAP-SYNTAX               boolean.&id
  LDAP-NAME                 {"oxAsJwt"}
  LDAP-DESC                 "Boolean field to indicate whether object is used as JWT"
  ID                        id-at-oxAsJwt }

-- X-ORIGIN: "Gluu created attribute"
oxJwt ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxJwt"}
  LDAP-DESC                 "JWT representation of the object or otherwise jwt associated with the object"
  ID                        id-at-oxJwt }

-- X-ORIGIN: "Gluu created attribute"
oxInvolvedClients ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxInvolvedClients"}
  LDAP-DESC                 "Involved clients"
  ID                        id-at-oxInvolvedClients }

-- X-ORIGIN: "Gluu created attribute"
oxLastAccessTime ATTRIBUTE ::= {
  WITH SYNTAX               GeneralizedTime
  EQUALITY MATCHING RULE    generalizedTimeMatch
  ORDERING MATCHING RULE    generalizedTimeOrderingMatch
  LDAP-SYNTAX               generalizedTime.&id
  LDAP-NAME                 {"oxLastAccessTime"}
  LDAP-DESC                 "Last access time"
  ID                        id-at-oxLastAccessTime }

-- X-ORIGIN: "Gluu created attribute"
oxLastLogonTime ATTRIBUTE ::= {
  WITH SYNTAX               GeneralizedTime
  EQUALITY MATCHING RULE    generalizedTimeMatch
  ORDERING MATCHING RULE    generalizedTimeOrderingMatch
  LDAP-SYNTAX               generalizedTime.&id
  LDAP-NAME                 {"oxLastLogonTime"}
  LDAP-DESC                 "Last logon time"
  ID                        id-at-oxLastLogonTime }

-- X-ORIGIN: "Gluu created attribute"
oxLinkCreator ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxLinkCreator"}
  LDAP-DESC                 "Link Creator"
  ID                        id-at-oxLinkCreator }

-- X-ORIGIN: "Gluu created attribute"
oxLinkExpirationDate ATTRIBUTE ::= {
  WITH SYNTAX               GeneralizedTime
  EQUALITY MATCHING RULE    generalizedTimeMatch
  ORDERING MATCHING RULE    generalizedTimeOrderingMatch
  LDAP-SYNTAX               generalizedTime.&id
  LDAP-NAME                 {"oxLinkExpirationDate"}
  LDAP-DESC                 "Link Expiration Date"
  ID                        id-at-oxLinkExpirationDate }

-- X-ORIGIN: "Gluu created attribute"
oxLinkLinktrack ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxLinkLinktrack"}
  LDAP-DESC                 "Linktrack link"
  ID                        id-at-oxLinkLinktrack }

-- X-ORIGIN: "Gluu created attribute"
oxLinkModerated ATTRIBUTE ::= {
  WITH SYNTAX               BOOLEAN
  EQUALITY MATCHING RULE    booleanMatch
  LDAP-SYNTAX               boolean.&id
  LDAP-NAME                 {"oxLinkModerated"}
  LDAP-DESC                 "Is Link Moderated?"
  ID                        id-at-oxLinkModerated }

-- X-ORIGIN: "Gluu created attribute"
oxLinkModerators ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxLinkModerators"}
  LDAP-DESC                 "Link Moderators"
  ID                        id-at-oxLinkModerators }

-- X-ORIGIN: "Gluu created attribute"
oxLinkPending ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxLinkPending"}
  LDAP-DESC                 "Pending Registrations"
  ID                        id-at-oxLinkPending }

-- X-ORIGIN: "Gluu created attribute"
oxLinktrackEnabled ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxLinktrackEnabled"}
  LDAP-DESC                 "Is Linktrack API configured"
  ID                        id-at-oxLinktrackEnabled }

-- X-ORIGIN: "Gluu created attribute"
oxLinktrackLogin ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxLinktrackLogin"}
  LDAP-DESC                 "Linktrack API login"
  ID                        id-at-oxLinktrackLogin }

-- X-ORIGIN: "Gluu created attribute"
oxLinktrackPassword ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxLinktrackPassword"}
  LDAP-DESC                 "Linktrack API password"
  ID                        id-at-oxLinktrackPassword }

-- X-ORIGIN: "Gluu created attribute"
oxLogViewerConfig ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxLogViewerConfig"}
  LDAP-DESC                 "Log viewer configuration"
  ID                        id-at-oxLogViewerConfig }

-- X-ORIGIN: "Gluu created attribute"
oxMultivaluedAttribute ATTRIBUTE ::= {
  WITH SYNTAX               BOOLEAN
  EQUALITY MATCHING RULE    booleanMatch
  LDAP-SYNTAX               boolean.&id
  LDAP-NAME                 {"oxMultivaluedAttribute"}
  ID                        id-at-oxMultivaluedAttribute }

-- X-ORIGIN: "Gluu created attribute"
oxName ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxName"}
  LDAP-DESC                 "Name"
  ID                        id-at-oxName }

-- X-ORIGIN: "Gluu created attribute"
oxNameIdType ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxNameIdType"}
  LDAP-DESC                 "NameId Type"
  ID                        id-at-oxNameIdType }

-- X-ORIGIN: "Gluu created attribute"
oxPolicyRule ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxPolicyRule"}
  LDAP-DESC                 "Policy Rule"
  ID                        id-at-oxPolicyRule }

-- X-ORIGIN: "Gluu created attribute"
oxUmaPolicyScriptDn ATTRIBUTE ::= {
  WITH SYNTAX               DistinguishedName
  EQUALITY MATCHING RULE    distinguishedNameMatch
  LDAP-SYNTAX               dn.&id
  LDAP-NAME                 {"oxUmaPolicyScriptDn"}
  LDAP-DESC                 "OX policy script Dn"
  ID                        id-at-oxUmaPolicyScriptDn }

-- X-ORIGIN: "Gluu created attribute"
oxProxConf ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxProxConf"}
  LDAP-DESC                 "oxProx Configuration"
  ID                        id-at-oxProxConf }

-- X-ORIGIN: "Gluu created attribute"
oxProxyAccessToken ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxProxyAccessToken"}
  LDAP-DESC                 "oxProx access token"
  ID                        id-at-oxProxyAccessToken }

-- X-ORIGIN: "Gluu created attribute"
oxProxyClaimMapping ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxProxyClaimMapping"}
  LDAP-DESC                 "oxProx claim mapping"
  ID                        id-at-oxProxyClaimMapping }

-- X-ORIGIN: "Gluu created attribute"
oxState ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxState"}
  LDAP-DESC                 "oxState"
  ID                        id-at-oxState }

-- X-ORIGIN: "Gluu created attribute"
oxCounter ATTRIBUTE ::= {
  WITH SYNTAX               INTEGER
  EQUALITY MATCHING RULE    integerMatch
  LDAP-SYNTAX               integer.&id
  LDAP-NAME                 {"oxCounter"}
  LDAP-DESC                 "oxCounter"
  ID                        id-at-oxCounter }

-- X-ORIGIN: "Gluu created attribute"
oxStatus ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxStatus"}
  LDAP-DESC                 "oxStatus"
  ID                        id-at-oxStatus }

-- X-ORIGIN: "Gluu created attribute"
oxApplication ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxApplication"}
  LDAP-DESC                 "oxApplication"
  ID                        id-at-oxApplication }

-- X-ORIGIN: "Gluu created attribute"
oxDeviceRegistrationConf ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxDeviceRegistrationConf"}
  LDAP-DESC                 "oxDeviceRegistrationConf"
  ID                        id-at-oxDeviceRegistrationConf }

-- X-ORIGIN: "Gluu created attribute"
oxDeviceKeyHandle ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxDeviceKeyHandle"}
  LDAP-DESC                 "oxDeviceKeyHandle"
  ID                        id-at-oxDeviceKeyHandle }

-- X-ORIGIN: "Gluu created attribute"
oxDeviceHashCode ATTRIBUTE ::= {
  WITH SYNTAX               INTEGER
  EQUALITY MATCHING RULE    integerMatch
  LDAP-SYNTAX               integer.&id
  LDAP-NAME                 {"oxDeviceHashCode"}
  LDAP-DESC                 "oxDeviceHashCode"
  ID                        id-at-oxDeviceHashCode }

-- X-ORIGIN: "Gluu created attribute"
oxRequest ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxRequest"}
  LDAP-DESC                 "oxRequest"
  ID                        id-at-oxRequest }

-- X-ORIGIN: "Gluu created attribute"
oxRequestId ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxRequestId"}
  LDAP-DESC                 "oxRequestId"
  ID                        id-at-oxRequestId }

-- X-ORIGIN: "Gluu created attribute"
oxDeviceData ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxDeviceData"}
  LDAP-DESC                 "oxDeviceData"
  ID                        id-at-oxDeviceData }

-- X-ORIGIN: "Gluu created attribute"
oxEnrollmentCode ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxEnrollmentCode"}
  LDAP-DESC                 "oxEnrollmentCode"
  ID                        id-at-oxEnrollmentCode }

-- X-ORIGIN: "Gluu created attribute"
oxProxyClientId ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxProxyClientId"}
  LDAP-DESC                 "oxProx client id"
  ID                        id-at-oxProxyClientId }

-- X-ORIGIN: "Gluu created attribute"
oxProxyScope ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxProxyScope"}
  LDAP-DESC                 "oxProx scope"
  ID                        id-at-oxProxyScope }

-- X-ORIGIN: "Gluu created attribute"
oxProxyToOpClientMapping ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxProxyToOpClientMapping"}
  LDAP-DESC                 "oxProx client mapping to op client"
  ID                        id-at-oxProxyToOpClientMapping }

-- X-ORIGIN: "Gluu created attribute"
oxPushApplication ATTRIBUTE ::= {
  WITH SYNTAX               DistinguishedName
  EQUALITY MATCHING RULE    distinguishedNameMatch
  LDAP-SYNTAX               dn.&id
  LDAP-NAME                 {"oxPushApplication"}
  LDAP-DESC                 "oxPush application DN"
  ID                        id-at-oxPushApplication }

-- X-ORIGIN: "Gluu created attribute"
oxPushApplicationConf ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxPushApplicationConf"}
  LDAP-DESC                 "oxPush application configuration"
  ID                        id-at-oxPushApplicationConf }

-- X-ORIGIN: "Gluu created attribute"
oxPushDeviceConf ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxPushDeviceConf"}
  LDAP-DESC                 "oxPush device configuration"
  ID                        id-at-oxPushDeviceConf }

-- X-ORIGIN: "Gluu created attribute"
oxRegistrationConfiguration ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxRegistrationConfiguration"}
  LDAP-DESC                 "Registration Configuration"
  ID                        id-at-oxRegistrationConfiguration }

-- X-ORIGIN: "Gluu created attribute"
oxResource ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxResource"}
  LDAP-DESC                 "Host path"
  ID                        id-at-oxResource }

-- X-ORIGIN: "Gluu created attribute"
oxResourceSetId ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxResourceSetId"}
  LDAP-DESC                 "ox resource set id"
  ID                        id-at-oxResourceSetId }

-- X-ORIGIN: "Gluu created attribute"
oxRevision ATTRIBUTE ::= {
  WITH SYNTAX               INTEGER
  EQUALITY MATCHING RULE    integerMatch
  LDAP-SYNTAX               integer.&id
  LDAP-NAME                 {"oxRevision"}
  LDAP-DESC                 "Revision"
  ID                        id-at-oxRevision }

-- X-ORIGIN: "Gluu created attribute"
oxLevel ATTRIBUTE ::= {
  WITH SYNTAX               INTEGER
  EQUALITY MATCHING RULE    integerMatch
  LDAP-SYNTAX               integer.&id
  LDAP-NAME                 {"oxLevel"}
  LDAP-DESC                 "Level"
  ID                        id-at-oxLevel }

-- X-ORIGIN: "Gluu created attribute"
oxSCIMCustomAttribute ATTRIBUTE ::= {
  WITH SYNTAX               BOOLEAN
  EQUALITY MATCHING RULE    booleanMatch
  LDAP-SYNTAX               boolean.&id
  LDAP-NAME                 {"oxSCIMCustomAttribute"}
  ID                        id-at-oxSCIMCustomAttribute }

-- X-ORIGIN: "Gluu created attribute"
oxScript ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxScript"}
  LDAP-DESC                 "Attribute that contains script (python, java script)"
  ID                        id-at-oxScript }

-- X-ORIGIN: "Gluu created attribute"
oxScriptDn ATTRIBUTE ::= {
  WITH SYNTAX               DistinguishedName
  EQUALITY MATCHING RULE    distinguishedNameMatch
  LDAP-SYNTAX               dn.&id
  LDAP-NAME                 {"oxScriptDn"}
  LDAP-DESC                 "Script object DN"
  ID                        id-at-oxScriptDn }

-- X-ORIGIN: "Gluu created attribute"
oxScriptType ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxScriptType"}
  LDAP-DESC                 "Attribute that contains script type (e.g. python, java script)"
  ID                        id-at-oxScriptType }

-- X-ORIGIN: "Gluu created attribute"
oxScriptError ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxScriptError"}
  LDAP-DESC                 "Attribute that contains first error which application get during it execution"
  ID                        id-at-oxScriptError }

-- X-ORIGIN: "Gluu created attribute"
oxSmtpConfiguration ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxSmtpConfiguration"}
  LDAP-DESC                 "SMTP configuration"
  ID                        id-at-oxSmtpConfiguration }

-- X-ORIGIN: "Gluu created attribute"
oxSourceAttribute ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxSourceAttribute"}
  LDAP-DESC                 "Source Attribute for this Attribute"
  ID                        id-at-oxSourceAttribute }

-- X-ORIGIN: "Gluu created attribute"
oxTicket ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxTicket"}
  LDAP-DESC                 "ox ticket"
  ID                        id-at-oxTicket }

-- X-ORIGIN: "Gluu created attribute"
oxTrustActive ATTRIBUTE ::= {
  WITH SYNTAX               BOOLEAN
  EQUALITY MATCHING RULE    booleanMatch
  LDAP-SYNTAX               boolean.&id
  LDAP-NAME                 {"oxTrustActive"}
  ID                        id-at-oxTrustActive }

-- X-ORIGIN: "Specifies the oxTrust server which should run Cache refresh"
oxTrustCacheRefreshServerIpAddress ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxTrustCacheRefreshServerIpAddress"}
  ID                        id-at-oxTrustCacheRefreshServerIpAddress }

-- X-ORIGIN: "Gluu created attribute"
oxTrustAddresses ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxTrustAddresses"}
  ID                        id-at-oxTrustAddresses }

-- X-ORIGIN: "Gluu created attribute"
oxTrustConfApplication ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxTrustConfApplication"}
  LDAP-DESC                 "oxTrust Application Configuration"
  ID                        id-at-oxTrustConfApplication }

-- X-ORIGIN: "Gluu created attribute"
oxTrustConfCacheRefresh ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxTrustConfCacheRefresh"}
  LDAP-DESC                 "oxTrust Cache Refresh Configuration"
  ID                        id-at-oxTrustConfCacheRefresh }

-- X-ORIGIN: "Gluu created attribute"
oxConfApplication ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxConfApplication"}
  LDAP-DESC                 "ox Application Configuration"
  ID                        id-at-oxConfApplication }

-- X-ORIGIN: "Gluu created attribute"
oxTrustCustAttrB ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxTrustCustAttrB"}
  LDAP-DESC                 "scim status"
  ID                        id-at-oxTrustCustAttrB }

-- X-ORIGIN: "Gluu created attribute"
oxTrustEmail ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxTrustEmail"}
  ID                        id-at-oxTrustEmail }

-- X-ORIGIN: "Gluu created attribute"
oxTrustEntitlements ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxTrustEntitlements"}
  ID                        id-at-oxTrustEntitlements }

-- X-ORIGIN: "Gluu created attribute"
oxTrustExternalId ATTRIBUTE ::= {
  WITH SYNTAX               UnboundedDirectoryString
  EQUALITY MATCHING RULE    caseExactMatch
  SUBSTRINGS MATCHING RULE  caseExactSubstringsMatch
  LDAP-SYNTAX               directoryString.&id
  LDAP-NAME                 {"oxTrustExternalId"}
  ID                        id-at-oxTrustExternalId }

-- X-ORIGIN: "Gluu created attribute"
oxTrustImsValue ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxTrustImsValue"}
  ID                        id-at-oxTrustImsValue }

-- X-ORIGIN: "Gluu created attribute"
oxTrustMetaCreated ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxTrustMetaCreated"}
  ID                        id-at-oxTrustMetaCreated }

-- X-ORIGIN: "Gluu created attribute"
oxTrustMetaLastModified ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxTrustMetaLastModified"}
  ID                        id-at-oxTrustMetaLastModified }

-- X-ORIGIN: "Gluu created attribute"
oxTrustMetaLocation ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxTrustMetaLocation"}
  ID                        id-at-oxTrustMetaLocation }

-- X-ORIGIN: "Gluu created attribute"
oxTrustMetaVersion ATTRIBUTE ::= {
  WITH SYNTAX               UnboundedDirectoryString
  EQUALITY MATCHING RULE    caseExactMatch
  SUBSTRINGS MATCHING RULE  caseExactSubstringsMatch
  LDAP-SYNTAX               directoryString.&id
  LDAP-NAME                 {"oxTrustMetaVersion"}
  ID                        id-at-oxTrustMetaVersion }

-- X-ORIGIN: "Gluu created attribute"
oxTrustNameFormatted ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxTrustNameFormatted"}
  ID                        id-at-oxTrustNameFormatted }

-- X-ORIGIN: "Gluu created attribute"
oxTrustPhoneValue ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxTrustPhoneValue"}
  ID                        id-at-oxTrustPhoneValue }

-- X-ORIGIN: "Gluu created attribute"
oxTrustPhotos ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxTrustPhotos"}
  ID                        id-at-oxTrustPhotos }

-- X-ORIGIN: "Gluu created attribute"
oxTrustProfileURL ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxTrustProfileURL"}
  ID                        id-at-oxTrustProfileURL }

-- X-ORIGIN: "Gluu created attribute"
oxTrustRole ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxTrustRole"}
  ID                        id-at-oxTrustRole }

-- X-ORIGIN: "Gluu created attribute"
oxTrustStoreCert ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxTrustStoreCert"}
  LDAP-DESC                 "oxPush device configuration"
  ID                        id-at-oxTrustStoreCert }

-- X-ORIGIN: "Gluu created attribute"
oxTrustStoreConf ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxTrustStoreConf"}
  LDAP-DESC                 "oxPush application configuration"
  ID                        id-at-oxTrustStoreConf }

-- X-ORIGIN: "Gluu created attribute"
oxTrustTitle ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxTrustTitle"}
  ID                        id-at-oxTrustTitle }

-- X-ORIGIN: "Gluu created attribute"
oxTrustUserType ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxTrustUserType"}
  ID                        id-at-oxTrustUserType }

-- X-ORIGIN: "Gluu created attribute"
oxTrusthonorificPrefix ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxTrusthonorificPrefix"}
  ID                        id-at-oxTrusthonorificPrefix }

-- X-ORIGIN: "Gluu created attribute"
oxTrusthonorificSuffix ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxTrusthonorificSuffix"}
  ID                        id-at-oxTrusthonorificSuffix }

-- X-ORIGIN: "Gluu created attribute"
oxTrustx509Certificate ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxTrustx509Certificate"}
  ID                        id-at-oxTrustx509Certificate }

-- X-ORIGIN: "Gluu created attribute"
oxType ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxType"}
  LDAP-DESC                 "ox type"
  ID                        id-at-oxType }

-- X-ORIGIN: "Gluu created attribute"
oxUmaPermission ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxUmaPermission"}
  LDAP-DESC                 "ox uma permission"
  ID                        id-at-oxUmaPermission }

-- X-ORIGIN: "Gluu created attribute"
oxUrl ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxUrl"}
  LDAP-DESC                 "ox url"
  ID                        id-at-oxUrl }

-- X-ORIGIN: "Gluu created attribute"
oxX509PEM ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxX509PEM"}
  LDAP-DESC                 "x509 in PEM format"
  ID                        id-at-oxX509PEM }

-- X-ORIGIN: "Gluu created attribute"
oxX509URL ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxX509URL"}
  LDAP-DESC                 "x509 URL"
  ID                        id-at-oxX509URL }

-- X-ORIGIN: "Gluu created attribute"
passwordResetAllowed ATTRIBUTE ::= {
  WITH SYNTAX               BOOLEAN
  EQUALITY MATCHING RULE    booleanMatch
  LDAP-SYNTAX               boolean.&id
  LDAP-NAME                 {"passwordResetAllowed"}
  LDAP-DESC                 "Is password reset mechanics allowed"
  ID                        id-at-passwordResetAllowed }

-- X-ORIGIN: "Persistent ID reserved for SAML"
persistentId ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"persistentId"}
  LDAP-DESC                 "PersistentId"
  ID                        id-at-persistentId }

-- X-ORIGIN: "Gluu created attribute"
personInum ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"personInum"}
  LDAP-DESC                 "Inum of a person"
  ID                        id-at-personInum }

-- X-ORIGIN: "Gluu created attribute"
primaryKeyAttrName ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"primaryKeyAttrName"}
  LDAP-DESC                 "Primary Key Attribute Name"
  ID                        id-at-primaryKeyAttrName }

-- X-ORIGIN: "Gluu created attribute"
primaryKeyValue ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"primaryKeyValue"}
  LDAP-DESC                 "Primary Key Value"
  ID                        id-at-primaryKeyValue }

-- X-ORIGIN: "Gluu created attribute"
proStoresToken ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"proStoresToken"}
  ID                        id-at-proStoresToken }

-- X-ORIGIN: "Gluu created attribute"
programmingLanguage ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"programmingLanguage"}
  LDAP-DESC                 "programming language"
  ID                        id-at-programmingLanguage }

-- X-ORIGIN: "Gluu created attribute"
prostoresTimestamp ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"prostoresTimestamp"}
  ID                        id-at-prostoresTimestamp }

-- X-ORIGIN: "Gluu created attribute"
registrationDate ATTRIBUTE ::= {
  WITH SYNTAX               GeneralizedTime
  EQUALITY MATCHING RULE    generalizedTimeMatch
  ORDERING MATCHING RULE    generalizedTimeOrderingMatch
  LDAP-SYNTAX               generalizedTime.&id
  LDAP-NAME                 {"registrationDate"}
  LDAP-DESC                 "Registration date"
  ID                        id-at-registrationDate }

-- X-ORIGIN: "Gluu created attribute"
role ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"role"}
  LDAP-DESC                 "Role"
  ID                        id-at-role }

-- X-ORIGIN: "Gluu created attribute"
scimAuthMode ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"scimAuthMode"}
  LDAP-DESC                 "SCIM Authorization mode"
  ID                        id-at-scimAuthMode }

-- X-ORIGIN: "Gluu created attribute"
scimGroup ATTRIBUTE ::= {
  WITH SYNTAX               DistinguishedName
  EQUALITY MATCHING RULE    distinguishedNameMatch
  LDAP-SYNTAX               dn.&id
  LDAP-NAME                 {"scimGroup"}
  LDAP-DESC                 "scim Group"
  ID                        id-at-scimGroup }

-- X-ORIGIN: "Gluu created attribute"
scimStatus ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"scimStatus"}
  LDAP-DESC                 "scim status"
  ID                        id-at-scimStatus }

-- X-ORIGIN: "Gluu created attribute"
secondaryKeyAttrName ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"secondaryKeyAttrName"}
  LDAP-DESC                 "Secondary Key Attribute Name"
  ID                        id-at-secondaryKeyAttrName }

-- X-ORIGIN: "Gluu created attribute"
secondaryKeyValue ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"secondaryKeyValue"}
  LDAP-DESC                 "Secondary Key Value"
  ID                        id-at-secondaryKeyValue }

-- X-ORIGIN: "Gluu created attribute"
secretAnswer ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"secretAnswer"}
  LDAP-DESC                 "Secret Answer"
  ID                        id-at-secretAnswer }

-- X-ORIGIN: "Gluu created attribute"
secretQuestion ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"secretQuestion"}
  LDAP-DESC                 "Secret Question"
  ID                        id-at-secretQuestion }

-- X-ORIGIN: "Gluu created attribute"
softwareVersion ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"softwareVersion"}
  ID                        id-at-softwareVersion }

-- X-ORIGIN: "Gluu created attribute"
sourceRelationalXdiStatement ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"sourceRelationalXdiStatement"}
  LDAP-DESC                 "OX SourceRelationalXdiStatement"
  ID                        id-at-sourceRelationalXdiStatement }

-- X-ORIGIN: "Gluu created attribute"
targetRelationalXdiStatement ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"targetRelationalXdiStatement"}
  LDAP-DESC                 "OX TargetRelationalXdiStatement"
  ID                        id-at-targetRelationalXdiStatement }

-- X-ORIGIN: "Gluu created attribute"
tertiaryKeyAttrName ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"tertiaryKeyAttrName"}
  LDAP-DESC                 "Tertiary Key Attribute Name"
  ID                        id-at-tertiaryKeyAttrName }

-- X-ORIGIN: "Gluu created attribute"
tertiaryKeyValue ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"tertiaryKeyValue"}
  LDAP-DESC                 "Tertiary Key Value"
  ID                        id-at-tertiaryKeyValue }

-- X-ORIGIN: "Gluu created attribute"
transientId ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"transientId"}
  LDAP-DESC                 "TransientId"
  ID                        id-at-transientId }

-- X-ORIGIN: "Gluu created attribute"
url ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"url"}
  ID                        id-at-url }

-- X-ORIGIN: "Gluu created attribute"
urn ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"urn"}
  ID                        id-at-urn }

-- X-ORIGIN: "Gluu created attribute"
x ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"x"}
  LDAP-DESC                 "OX XRI Component"
  ID                        id-at-x }

-- X-ORIGIN: "Gluu created attribute"
xdiStatement ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"xdiStatement"}
  LDAP-DESC                 "OX xdiStatement"
  ID                        id-at-xdiStatement }

-- X-ORIGIN: "Gluu created attribute"
xri ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"xri"}
  LDAP-DESC                 "OX XRI address"
  ID                        id-at-xri }

-- X-ORIGIN: "OpenID Connect 1.0 Standard Claim"
middleName ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"middleName", "oxTrustMiddleName"}
  LDAP-DESC                 "Middle name(s)"
  ID                        id-at-middleName }

-- X-ORIGIN: "OpenID Connect 1.0 Standard Claim"
nickname ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"nickname", "oxTrustnickname"}
  LDAP-DESC                 "Casual name of the End-User"
  ID                        id-at-nickname }

-- X-ORIGIN: "OpenID Connect 1.0 Standard Claim"
preferredUsername ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"preferredUsername"}
  LDAP-DESC                 "Shorthand Name"
  ID                        id-at-preferredUsername }

-- X-ORIGIN: "OpenID Connect 1.0 Standard Claim"
profile ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"profile"}
  LDAP-DESC                 "Profile page URL of the person"
  ID                        id-at-profile }

-- X-ORIGIN: "OpenID Connect 1.0 Standard Claim"
picture ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"picture", "photo1"}
  LDAP-DESC                 "Profile picture URL of the person"
  ID                        id-at-picture }

-- X-ORIGIN: "OpenID Connect 1.0 Standard Claim"
website ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"website"}
  LDAP-DESC                 "Web page or blog URL of the person"
  ID                        id-at-website }

-- X-ORIGIN: "OpenID Connect 1.0 Standard Claim"
emailVerified ATTRIBUTE ::= {
  WITH SYNTAX               BOOLEAN
  EQUALITY MATCHING RULE    booleanMatch
  LDAP-SYNTAX               boolean.&id
  LDAP-NAME                 {"emailVerified"}
  LDAP-DESC                 "True if the e-mail address of the person has been verified; otherwise false"
  ID                        id-at-emailVerified }

-- X-ORIGIN: "OpenID Connect 1.0 Standard Claim"
gender ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gender"}
  LDAP-DESC                 "Gender of the person either female or male"
  ID                        id-at-gender }

-- X-ORIGIN: "OpenID Connect 1.0 Standard Claim"
birthdate ATTRIBUTE ::= {
  WITH SYNTAX               GeneralizedTime
  EQUALITY MATCHING RULE    generalizedTimeMatch
  ORDERING MATCHING RULE    generalizedTimeOrderingMatch
  LDAP-SYNTAX               generalizedTime.&id
  LDAP-NAME                 {"birthdate"}
  LDAP-DESC                 "Birthday of the person, represented as an ISO 8601:2004 [ISO8601‑2004] YYYY-MM-DD format"
  ID                        id-at-birthdate }

-- X-ORIGIN: "OpenID Connect 1.0 Standard Claim"
zoneinfo ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"zoneinfo", "timezone"}
  LDAP-DESC                 "Time zone database representing the End-Users time zone. For example, Europe/Paris or America/Los_Angeles"
  ID                        id-at-zoneinfo }

-- X-ORIGIN: "OpenID Connect 1.0 Standard Claim"
locale ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"locale", "oxTrustLocale"}
  LDAP-DESC                 "Locale of the person, represented as a BCP47 [RFC5646] language tag"
  ID                        id-at-locale }

-- X-ORIGIN: "Gluu created attribute"
phoneNumberVerified ATTRIBUTE ::= {
  WITH SYNTAX               BOOLEAN
  EQUALITY MATCHING RULE    booleanMatch
  LDAP-SYNTAX               boolean.&id
  LDAP-NAME                 {"phoneNumberVerified"}
  LDAP-DESC                 "True if the phone number of the person has been verified, otherwise false"
  ID                        id-at-phoneNumberVerified }

-- X-ORIGIN: "OpenID Connect 1.0 Standard Claim"
address ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"address"}
  LDAP-DESC                 "OpenID Connect formatted JSON object representing the address of the person"
  ID                        id-at-address }

-- X-ORIGIN: "OpenID Connect 1.0 Standard Claim"
updatedAt ATTRIBUTE ::= {
  WITH SYNTAX               GeneralizedTime
  EQUALITY MATCHING RULE    generalizedTimeMatch
  ORDERING MATCHING RULE    generalizedTimeOrderingMatch
  LDAP-SYNTAX               generalizedTime.&id
  LDAP-NAME                 {"updatedAt"}
  LDAP-DESC                 "Time the information of the person was last updated. Seconds from 1970-01-01T0:0:0Z"
  ID                        id-at-updatedAt }

-- X-ORIGIN: "OpenID Connect 1.0 Standard Claim"
gluuRegExp ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuRegExp"}
  LDAP-DESC                 "Regular expression used to validate attribute data"
  ID                        id-at-gluuRegExp }

-- X-ORIGIN: "OpenID Connect 1.0 Standard Claim"
gluuTooltip ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuTooltip"}
  LDAP-DESC                 "Custom tooltip to be shown on the UI"
  ID                        id-at-gluuTooltip }

-- X-ORIGIN: "Gluu created attribute"
oxModuleProperty ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxModuleProperty"}
  LDAP-DESC                 "Module property"
  ID                        id-at-oxModuleProperty }

-- X-ORIGIN: "Gluu created attribute"
oxConfigurationProperty ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxConfigurationProperty"}
  LDAP-DESC                 "Configuration property"
  ID                        id-at-oxConfigurationProperty }

-- X-ORIGIN: "Gluu created attribute"
oxAuthSessionAttribute ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthSessionAttribute"}
  LDAP-DESC                 "oxAuthSessionAttribute"
  ID                        id-at-oxAuthSessionAttribute }

-- X-ORIGIN: "Gluu created attribute"
researchAndScholarshipEnabled ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"researchAndScholarshipEnabled"}
  LDAP-DESC                 "Trust relationship attribute to show that InCommon R&S activated"
  ID                        id-at-researchAndScholarshipEnabled }

-- X-ORIGIN: "Gluu created attribute"
oxStartDate ATTRIBUTE ::= {
  WITH SYNTAX               GeneralizedTime
  EQUALITY MATCHING RULE    generalizedTimeMatch
  ORDERING MATCHING RULE    generalizedTimeOrderingMatch
  LDAP-SYNTAX               generalizedTime.&id
  LDAP-NAME                 {"oxStartDate"}
  LDAP-DESC                 "Start date"
  ID                        id-at-oxStartDate }

-- X-ORIGIN: "Gluu created attribute"
oxEndDate ATTRIBUTE ::= {
  WITH SYNTAX               GeneralizedTime
  EQUALITY MATCHING RULE    generalizedTimeMatch
  ORDERING MATCHING RULE    generalizedTimeOrderingMatch
  LDAP-SYNTAX               generalizedTime.&id
  LDAP-NAME                 {"oxEndDate"}
  LDAP-DESC                 "End date"
  ID                        id-at-oxEndDate }

-- X-ORIGIN: "Gluu created attribute"
oxApplicationType ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxApplicationType"}
  LDAP-DESC                 "Application type"
  ID                        id-at-oxApplicationType }

-- X-ORIGIN: "Gluu created attribute"
oxMetricType ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxMetricType"}
  LDAP-DESC                 "Metric type"
  ID                        id-at-oxMetricType }

-- X-ORIGIN: "Gluu created attribute"
oxData ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxData"}
  LDAP-DESC                 "OX data"
  ID                        id-at-oxData }

-- X-ORIGIN: "Gluu created attribute"
dat ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"dat"}
  LDAP-DESC                 "OX data"
  ID                        id-at-dat }

-- X-ORIGIN: "Gluu created attribute"
oxCodeChallenge ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxCodeChallenge"}
  LDAP-DESC                 "OX PKCE code challenge"
  ID                        id-at-oxCodeChallenge }

-- X-ORIGIN: "Gluu created attribute"
chlng ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"chlng"}
  LDAP-DESC                 "OX PKCE code challenge"
  ID                        id-at-chlng }

-- X-ORIGIN: "Gluu created attribute"
chlngMth ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"chlngMth"}
  LDAP-DESC                 "OX PKCE code challenge method"
  ID                        id-at-chlngMth }

-- X-ORIGIN: "Gluu created attribute"
oxSectorIdentifier ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxSectorIdentifier"}
  LDAP-DESC                 "ox Sector Identifier"
  ID                        id-at-oxSectorIdentifier }

-- X-ORIGIN: "Gluu created attribute"
oxPersistClientAuthorizations ATTRIBUTE ::= {
  WITH SYNTAX               BOOLEAN
  EQUALITY MATCHING RULE    booleanMatch
  LDAP-SYNTAX               boolean.&id
  LDAP-NAME                 {"oxPersistClientAuthorizations"}
  LDAP-DESC                 "ox Persist Client Authorizations"
  ID                        id-at-oxPersistClientAuthorizations }

-- X-ORIGIN: "Gluu created attribute"
oxTrustConfImportPerson ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxTrustConfImportPerson"}
  LDAP-DESC                 "oxTrust Import Person Configuration"
  ID                        id-at-oxTrustConfImportPerson }

-- X-ORIGIN: "Gluu created attribute"
oxSessionStateId ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxSessionStateId"}
  LDAP-DESC                 "oxSessionStateId"
  ID                        id-at-oxSessionStateId }

-- X-ORIGIN: "Gluu created attribute"
ssnId ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"ssnId"}
  LDAP-DESC                 "oxAuth Session DN"
  ID                        id-at-ssnId }

-- X-ORIGIN: "Gluu created attribute"
oxPasswordExpirationDate ATTRIBUTE ::= {
  WITH SYNTAX               GeneralizedTime
  EQUALITY MATCHING RULE    generalizedTimeMatch
  ORDERING MATCHING RULE    generalizedTimeOrderingMatch
  LDAP-SYNTAX               generalizedTime.&id
  LDAP-NAME                 {"oxPasswordExpirationDate"}
  LDAP-DESC                 "Password Expiration date, represented as an ISO 8601 (YYYY-MM-DD) format"
  ID                        id-at-oxPasswordExpirationDate }

-- X-ORIGIN: "Gluu created attribute"
oxCountInvalidLogin ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxCountInvalidLogin"}
  LDAP-DESC                 "Invalid login attempts count"
  ID                        id-at-oxCountInvalidLogin }

-- X-ORIGIN: "Gluu created attribute"
gluuIMAPData ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuIMAPData"}
  LDAP-DESC                 "This data has information about your imap connection"
  ID                        id-at-gluuIMAPData }

-- X-ORIGIN: "Gluu created attribute"
gluuPassportConfiguration ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuPassportConfiguration"}
  LDAP-DESC                 "oxTrust Passport Strategy Configuration"
  ID                        id-at-gluuPassportConfiguration }

-- X-ORIGIN: "Gluu created attribute"
gluuPassportEnabled ATTRIBUTE ::= {
  WITH SYNTAX               BOOLEAN
  EQUALITY MATCHING RULE    booleanMatch
  LDAP-SYNTAX               boolean.&id
  LDAP-NAME                 {"gluuPassportEnabled"}
  ID                        id-at-gluuPassportEnabled }

-- X-ORIGIN: "Gluu created attribute"
gluuRadiusEnabled ATTRIBUTE ::= {
  WITH SYNTAX               BOOLEAN
  EQUALITY MATCHING RULE    booleanMatch
  LDAP-SYNTAX               boolean.&id
  LDAP-NAME                 {"gluuRadiusEnabled"}
  ID                        id-at-gluuRadiusEnabled }

-- X-ORIGIN: "Gluu created attribute"
gluuSamlEnabled ATTRIBUTE ::= {
  WITH SYNTAX               BOOLEAN
  EQUALITY MATCHING RULE    booleanMatch
  LDAP-SYNTAX               boolean.&id
  LDAP-NAME                 {"gluuSamlEnabled"}
  ID                        id-at-gluuSamlEnabled }

-- X-ORIGIN: "Gluu created attribute"
oxValidation ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxValidation"}
  LDAP-DESC                 "This data has information about attribute Validation"
  ID                        id-at-oxValidation }

-- X-ORIGIN: "Gluu created attribute"
gluuEntityType ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuEntityType"}
  LDAP-DESC                 "This data has information about TR EntityType"
  ID                        id-at-gluuEntityType }

-- X-ORIGIN: "Gluu created attribute"
oxPPID ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxPPID"}
  LDAP-DESC                 "Persistent Pairwise ID for OpenID Connect"
  ID                        id-at-oxPPID }

-- X-ORIGIN: "Gluu created attribute"
oxAuthSessionId ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthSessionId"}
  LDAP-DESC                 "oxAuth Session Id"
  ID                        id-at-oxAuthSessionId }

-- X-ORIGIN: "Gluu created attribute"
oxCacheConfiguration ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxCacheConfiguration"}
  LDAP-DESC                 "Cache configuration"
  ID                        id-at-oxCacheConfiguration }

-- X-ORIGIN: "Gluu created attribute"
oxLogConfigLocation ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxLogConfigLocation"}
  LDAP-DESC                 "Path to external log4j2.xml"
  ID                        id-at-oxLogConfigLocation }

-- X-ORIGIN: "Gluu created attribute"
oxIncludeClaimsInIdToken ATTRIBUTE ::= {
  WITH SYNTAX               BOOLEAN
  EQUALITY MATCHING RULE    booleanMatch
  LDAP-SYNTAX               boolean.&id
  LDAP-NAME                 {"oxIncludeClaimsInIdToken"}
  LDAP-DESC                 "ox Include Claims In Id Token"
  ID                        id-at-oxIncludeClaimsInIdToken }

-- X-ORIGIN: "Gluu created attribute"
oxClaimValues ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxClaimValues"}
  LDAP-DESC                 "Claim Values"
  ID                        id-at-oxClaimValues }

-- X-ORIGIN: "Gluu created attribute"
oxClaimRedirectURI ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxClaimRedirectURI"}
  LDAP-DESC                 "Claim Redirect URI"
  ID                        id-at-oxClaimRedirectURI }

-- X-ORIGIN: "Gluu created attribute"
oxAttributes ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAttributes"}
  LDAP-DESC                 "Attributes"
  ID                        id-at-oxAttributes }

-- X-ORIGIN: "Gluu created attribute"
attr ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"attr"}
  LDAP-DESC                 "Attributes"
  ID                        id-at-attr }

-- X-ORIGIN: "Gluu created attribute"
userRandomKey ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"userRandomKey"}
  LDAP-DESC                 "Attributes"
  ID                        id-at-userRandomKey }

-- X-ORIGIN: "Gluu created attribute"
oxRefreshTokenLifetime ATTRIBUTE ::= {
  WITH SYNTAX               INTEGER
  EQUALITY MATCHING RULE    integerMatch
  LDAP-SYNTAX               integer.&id
  LDAP-NAME                 {"oxRefreshTokenLifetime"}
  LDAP-DESC                 "Lifetime of refresh token"
  ID                        id-at-oxRefreshTokenLifetime }

-- X-ORIGIN: "Gluu created attribute"
oxTrustConfAttributeResolver ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxTrustConfAttributeResolver"}
  LDAP-DESC                 "oxTrust Attribute Resolver"
  ID                        id-at-oxTrustConfAttributeResolver }

-- X-ORIGIN: "Gluu created attribute"
oxAuthPermissionGranted ATTRIBUTE ::= {
  WITH SYNTAX               BOOLEAN
  EQUALITY MATCHING RULE    booleanMatch
  LDAP-SYNTAX               boolean.&id
  LDAP-NAME                 {"oxAuthPermissionGranted"}
  LDAP-DESC                 "oxAuth Permission Granted"
  ID                        id-at-oxAuthPermissionGranted }

-- X-ORIGIN: "Gluu created attribute"
oxNickName ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxNickName"}
  LDAP-DESC                 "oxNickName"
  ID                        id-at-oxNickName }

-- X-ORIGIN: "Gluu created attribute"
oxDeviceNotificationConf ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxDeviceNotificationConf"}
  LDAP-DESC                 "Extended push notification configuration"
  ID                        id-at-oxDeviceNotificationConf }

-- X-ORIGIN: "Gluu created attribute"
clms ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"clms"}
  LDAP-DESC                 "oxAuth Claims"
  ID                        id-at-clms }

-- X-ORIGIN: "Gluu created attribute"
oxDisabled ATTRIBUTE ::= {
  WITH SYNTAX               BOOLEAN
  EQUALITY MATCHING RULE    booleanMatch
  LDAP-SYNTAX               boolean.&id
  LDAP-NAME                 {"oxDisabled"}
  LDAP-DESC                 "Status of client"
  ID                        id-at-oxDisabled }

-- X-ORIGIN: "Gluu created attribute"
oxWebKeysSettings ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxWebKeysSettings"}
  LDAP-DESC                 "oxAuth Web Keys Configuration"
  ID                        id-at-oxWebKeysSettings }

-- X-ORIGIN: "Gluu created attribute"
oxScopeExpression ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxScopeExpression"}
  LDAP-DESC                 "Scope expression"
  ID                        id-at-oxScopeExpression }

-- X-ORIGIN: "Gluu created attribute"
oxPreferredMethod ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxPreferredMethod"}
  LDAP-DESC                 "Gluu Casa - preferred method to use for user authentication"
  ID                        id-at-oxPreferredMethod }

-- X-ORIGIN: "Gluu created attribute"
oxOTPDevices ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxOTPDevices"}
  LDAP-DESC                 "Gluu Casa - Json representation of OTP devices. Complementary to oxExternalUid attribute"
  ID                        id-at-oxOTPDevices }

-- X-ORIGIN: "Gluu created attribute"
oxMobileDevices ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxMobileDevices"}
  LDAP-DESC                 "Gluu Casa - Json representation of mobile devices. Complementary to mobile attribute"
  ID                        id-at-oxMobileDevices }

-- X-ORIGIN: "Gluu created attribute"
oxdId ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxdId"}
  LDAP-DESC                 "oxd Id"
  ID                        id-at-oxdId }

-- X-ORIGIN: "Gluu created attribute"
oxAuthAuthorizedOrigins ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthAuthorizedOrigins"}
  LDAP-DESC                 "oxAuth Authorized Origins"
  ID                        id-at-oxAuthAuthorizedOrigins }

-- X-ORIGIN: "Gluu created attribute"
oxStrongAuthPolicy ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxStrongAuthPolicy"}
  LDAP-DESC                 "Gluu Casa - 2FA Enforcement Policy for User"
  ID                        id-at-oxStrongAuthPolicy }

-- X-ORIGIN: "Gluu created attribute"
oxTrustedDevicesInfo ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxTrustedDevicesInfo"}
  LDAP-DESC                 "Gluu Casa - List of devices with which strong authentication may be skipped"
  ID                        id-at-oxTrustedDevicesInfo }

-- X-ORIGIN: "Gluu created attribute"
tknBndCnf ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"tknBndCnf"}
  LDAP-DESC                 "oxauth - Token Binding Id Hash"
  ID                        id-at-tknBndCnf }

-- X-ORIGIN: "Gluu created attribute"
oxUnlinkedExternalUids ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxUnlinkedExternalUids"}
  LDAP-DESC                 "Gluu Casa - List of unlinked social accounts (ie disabled oxExternalUids)"
  ID                        id-at-oxUnlinkedExternalUids }

-- X-ORIGIN: "Gluu created attribute"
oxAccessTokenAsJwt ATTRIBUTE ::= {
  WITH SYNTAX               BOOLEAN
  EQUALITY MATCHING RULE    booleanMatch
  LDAP-SYNTAX               boolean.&id
  LDAP-NAME                 {"oxAccessTokenAsJwt"}
  LDAP-DESC                 "oxauth - indicator whether to return access token as JWT"
  ID                        id-at-oxAccessTokenAsJwt }

-- X-ORIGIN: "Gluu created attribute"
oxAccessTokenSigningAlg ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAccessTokenSigningAlg"}
  LDAP-DESC                 "oxauth - access token signing algorithm"
  ID                        id-at-oxAccessTokenSigningAlg }

-- X-ORIGIN: "Gluu created attribute"
oxRegistrationData ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxRegistrationData"}
  LDAP-DESC                 "oxRegistrationData"
  ID                        id-at-oxRegistrationData }

-- X-ORIGIN: "Gluu created attribute"
oxAuthenticationData ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthenticationData"}
  LDAP-DESC                 "oxAuthenticationData"
  ID                        id-at-oxAuthenticationData }

-- X-ORIGIN: "Gluu created attribute"
oxPublicKeyId ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxPublicKeyId"}
  LDAP-DESC                 "oxPublicKeyId"
  ID                        id-at-oxPublicKeyId }

-- X-ORIGIN: "Gluu created attribute"
oxAccessTokenLifetime ATTRIBUTE ::= {
  WITH SYNTAX               INTEGER
  EQUALITY MATCHING RULE    integerMatch
  LDAP-SYNTAX               integer.&id
  LDAP-NAME                 {"oxAccessTokenLifetime"}
  LDAP-DESC                 "Lifetime of access token"
  ID                        id-at-oxAccessTokenLifetime }

-- X-ORIGIN: "Gluu created attribute"
oxSoftwareId ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxSoftwareId"}
  LDAP-DESC                 "Software Identifier"
  ID                        id-at-oxSoftwareId }

-- X-ORIGIN: "Gluu created attribute"
oxSoftwareVersion ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxSoftwareVersion"}
  LDAP-DESC                 "Software Version"
  ID                        id-at-oxSoftwareVersion }

-- X-ORIGIN: "Gluu created attribute"
oxSoftwareStatement ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxSoftwareStatement"}
  LDAP-DESC                 "Software Statement"
  ID                        id-at-oxSoftwareStatement }

-- X-ORIGIN: "Gluu created attribute"
oxRptAsJwt ATTRIBUTE ::= {
  WITH SYNTAX               BOOLEAN
  EQUALITY MATCHING RULE    booleanMatch
  LDAP-SYNTAX               boolean.&id
  LDAP-NAME                 {"oxRptAsJwt"}
  LDAP-DESC                 "oxRptAsJwt"
  ID                        id-at-oxRptAsJwt }

-- X-ORIGIN: "Gluu created attribute"
oxCodeChallengeHash ATTRIBUTE ::= {
  WITH SYNTAX               INTEGER
  EQUALITY MATCHING RULE    integerMatch
  LDAP-SYNTAX               integer.&id
  LDAP-NAME                 {"oxCodeChallengeHash"}
  LDAP-DESC                 "OX code challenge hash"
  ID                        id-at-oxCodeChallengeHash }

-- X-ORIGIN: "Gluu created attribute"
del ATTRIBUTE ::= {
  WITH SYNTAX               BOOLEAN
  EQUALITY MATCHING RULE    booleanMatch
  LDAP-SYNTAX               boolean.&id
  LDAP-NAME                 {"del"}
  LDAP-DESC                 "del"
  ID                        id-at-del }

-- X-ORIGIN: "Gluu created attribute"
oxEnabled ATTRIBUTE ::= {
  WITH SYNTAX               BOOLEAN
  EQUALITY MATCHING RULE    booleanMatch
  LDAP-SYNTAX               boolean.&id
  LDAP-NAME                 {"oxEnabled"}
  LDAP-DESC                 "Status of the entry, used by many objectclasses"
  ID                        id-at-oxEnabled }

-- X-ORIGIN: "Gluu created attribute"
oxAlias ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAlias"}
  LDAP-DESC                 "oxAlias"
  ID                        id-at-oxAlias }

-- X-ORIGIN: "Gluu created attribute"
oxTrustLogoPath ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxTrustLogoPath"}
  LDAP-DESC                 "oxTrustLogoPath"
  ID                        id-at-oxTrustLogoPath }

-- X-ORIGIN: "Gluu created attribute"
oxTrustFaviconPath ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxTrustFaviconPath"}
  LDAP-DESC                 "oxTrustFaviconPath"
  ID                        id-at-oxTrustFaviconPath }

-- X-ORIGIN: "Gluu created attribute"
oxAuthLogoPath ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthLogoPath"}
  LDAP-DESC                 "oxAuthLogoPath"
  ID                        id-at-oxAuthLogoPath }

-- X-ORIGIN: "Gluu created attribute"
oxAuthFaviconPath ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthFaviconPath"}
  LDAP-DESC                 "oxAuthFaviconPath"
  ID                        id-at-oxAuthFaviconPath }

-- X-ORIGIN: "Gluu created attribute"
idpLogoPath ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"idpLogoPath"}
  LDAP-DESC                 "idpLogoPath"
  ID                        id-at-idpLogoPath }

-- X-ORIGIN: "Gluu created attribute"
idpFaviconPath ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"idpFaviconPath"}
  LDAP-DESC                 "idpFaviconPath"
  ID                        id-at-idpFaviconPath }

-- X-ORIGIN: "Gluu created attribute"
parent ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"parent"}
  LDAP-DESC                 "parent"
  ID                        id-at-parent }

-- X-ORIGIN: "Gluu created attribute"
classRef ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"classRef"}
  LDAP-DESC                 "classRef"
  ID                        id-at-classRef }

-- X-ORIGIN: "Gluu created attribute"
gluuSmtpServerTrust ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuSmtpServerTrust"}
  LDAP-DESC                 "Trust SMTP server"
  ID                        id-at-gluuSmtpServerTrust }

-- "pattern" is an ASN.1 reserved word; suffixed -type.
-- X-ORIGIN: "Gluu created attribute"
pattern-type ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"pattern"}
  LDAP-DESC                 "pattern"
  ID                        id-at-pattern-type }

-- X-ORIGIN: "Gluu created attribute"
oxAuthBackchannelTokenDeliveryMode ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthBackchannelTokenDeliveryMode"}
  LDAP-DESC                 "oxAuth Backchannel Token Delivery Mode"
  ID                        id-at-oxAuthBackchannelTokenDeliveryMode }

-- X-ORIGIN: "Gluu created attribute"
oxAuthBackchannelClientNotificationEndpoint ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthBackchannelClientNotificationEndpoint"}
  LDAP-DESC                 "oxAuth Backchannel Client Notification Endpoint"
  ID                        id-at-oxAuthBackchannelClientNotificationEndpoint }

-- X-ORIGIN: "Gluu created attribute"
oxAuthBackchannelAuthenticationRequestSigningAlg ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthBackchannelAuthenticationRequestSigningAlg"}
  LDAP-DESC                 "oxAuth Backchannel Authentication Request Signing Alg"
  ID                        id-at-oxAuthBackchannelAuthenticationRequestSigningAlg }

-- X-ORIGIN: "Gluu created attribute"
oxAuthBackchannelUserCodeParameter ATTRIBUTE ::= {
  WITH SYNTAX               BOOLEAN
  EQUALITY MATCHING RULE    caseIgnoreMatch
  SUBSTRINGS MATCHING RULE  caseIgnoreSubstringsMatch
  LDAP-SYNTAX               boolean.&id
  LDAP-NAME                 {"oxAuthBackchannelUserCodeParameter"}
  LDAP-DESC                 "oxAuth Backchannel User Code Parameter"
  ID                        id-at-oxAuthBackchannelUserCodeParameter }

-- X-ORIGIN: "Gluu created attribute"
oxAuthBackchannelDeviceRegistrationToken ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthBackchannelDeviceRegistrationToken"}
  LDAP-DESC                 "oxAuth Backchannel Device Registration Token"
  ID                        id-at-oxAuthBackchannelDeviceRegistrationToken }

-- X-ORIGIN: "Gluu created attribute"
oxAuthBackchannelUserCode ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxAuthBackchannelUserCode"}
  LDAP-DESC                 "oxAuth Backchannel User Code"
  ID                        id-at-oxAuthBackchannelUserCode }

-- X-ORIGIN: "Gluu created attribute"
oxDocumentStoreConfiguration ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"oxDocumentStoreConfiguration"}
  LDAP-DESC                 "oxDocumentStoreConfiguration"
  ID                        id-at-oxDocumentStoreConfiguration }

-- X-ORIGIN: "Gluu created attribute"
gluuConfDynamic ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuConfDynamic"}
  LDAP-DESC                 "Gluu Dynamic Configuration"
  ID                        id-at-gluuConfDynamic }

-- X-ORIGIN: "Gluu created attribute"
gluuConfStatic ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"gluuConfStatic"}
  LDAP-DESC                 "Gluu Static Configuration"
  ID                        id-at-gluuConfStatic }

-- X-ORIGIN: "Gluu created attribute"
authReqId ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"authReqId"}
  LDAP-DESC                 "Authentication request id"
  ID                        id-at-authReqId }

-- X-ORIGIN: "Gluu created attribute"
sid ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"sid"}
  LDAP-DESC                 "Session Identifier"
  ID                        id-at-sid }

-- X-ORIGIN: "Gluu created attribute"
jansId ATTRIBUTE ::= {
  WITH SYNTAX               UnboundedDirectoryString
  EQUALITY MATCHING RULE    caseIgnoreMatch
  SUBSTRINGS MATCHING RULE  caseIgnoreSubstringsMatch
  LDAP-SYNTAX               directoryString.&id
  LDAP-NAME                 {"jansId"}
  LDAP-DESC                 "jans id"
  ID                        id-at-jansId }

-- Object classes

-- X-ORIGIN: "Gluu created objectclass"
pairwiseIdentifier OBJECT-CLASS ::= {
  SUBCLASS OF               { top }
  MUST CONTAIN              { objectClass }
  MAY CONTAIN               { oxId
                              | oxSectorIdentifier
                              | oxAuthClientId
                              | oxAuthUserId }
  LDAP-NAME                 {"pairwiseIdentifier"}
  ID                        id-oc-pairwiseIdentifier }

-- X-ORIGIN: "Gluu created objectclass"
gluuPerson OBJECT-CLASS ::= {
  SUBCLASS OF               { top }
  MUST CONTAIN              { objectClass }
  MAY CONTAIN               { oxAssociatedClient
                              | countryName
                              | displayName
                              | givenName
                              | gluuManagedOrganizations
                              | gluuOptOuts
                              | gluuStatus
                              | gluuWhitePagesListed
                              | iname
                              | inum
                              | mail
                              | gluuSLAManager
                              | memberOf
                              | organizationName
                              | oxAuthPersistentJWT
                              | oxCreationTimestamp
                              | oxExternalUid
                              | oxOTPCache
                              | oxLastLogonTime
                              | oxTrustActive
                              | oxTrustAddresses
                              | oxTrustEmail
                              | oxTrustEntitlements
                              | oxTrustExternalId
                              | oxTrustImsValue
                              | oxTrustMetaCreated
                              | oxTrustMetaLastModified
                              | oxTrustMetaLocation
                              | oxTrustMetaVersion
                              | oxTrustNameFormatted
                              | oxTrustPhoneValue
                              | oxTrustPhotos
                              | oxTrustProfileURL
                              | oxTrustRole
                              | oxTrustTitle
                              | oxTrustUserType
                              | oxTrusthonorificPrefix
                              | oxTrusthonorificSuffix
                              | oxTrustx509Certificate
                              | oxPasswordExpirationDate
                              | persistentId
                              | middleName
                              | nickname
                              | preferredUsername
                              | profile
                              | picture
                              | website
                              | emailVerified
                              | gender
                              | birthdate
                              | zoneinfo
                              | locale
                              | phoneNumberVerified
                              | address
                              | updatedAt
                              | preferredLanguage
                              | role
                              | secretAnswer
                              | secretQuestion
                              | seeAlso
                              | surname
                              | commonName
                              | transientId
                              | uid
                              | userPassword
                              | stateOrProvinceName
                              | streetAddress
                              | localityName
                              | oxCountInvalidLogin
                              | oxEnrollmentCode
                              | gluuIMAPData
                              | oxPPID
                              | oxGuid
                              | userRandomKey
                              | oxPreferredMethod
                              | userCertificate
                              | oxOTPDevices
                              | oxMobileDevices
                              | oxStrongAuthPolicy
                              | oxTrustedDevicesInfo
                              | oxUnlinkedExternalUids
                              | oxAuthBackchannelDeviceRegistrationToken
                              | oxAuthBackchannelUserCode }
  LDAP-NAME                 {"gluuPerson"}
  ID                        id-oc-gluuPerson }

-- X-ORIGIN: "Gluu created objectclass"
gluuGroup OBJECT-CLASS ::= {
  SUBCLASS OF               { top }
  MUST CONTAIN              { objectClass }
  MAY CONTAIN               { countryName
                              | description
                              | displayName
                              | gluuGroupType
                              | gluuGroupVisibility
                              | gluuStatus
                              | iname
                              | inum
                              | member
                              | organizationName
                              | owner
                              | seeAlso
                              | oxTrustMetaCreated
                              | oxTrustMetaLastModified
                              | oxTrustMetaLocation
                              | oxTrustMetaVersion }
  LDAP-NAME                 {"gluuGroup"}
  ID                        id-oc-gluuGroup }

-- X-ORIGIN: "Gluu created objectclass"
gluuOrganization OBJECT-CLASS ::= {
  SUBCLASS OF               { top }
  MUST CONTAIN              { objectClass }
  MAY CONTAIN               { countryName
                              | county
                              | deployedAppliances
                              | description
                              | displayName
                              | gluuAddPersonCapability
                              | gluuAdditionalUsers
                              | gluuApplianceUpdateRequestList
                              | gluuCustomMessage
                              | gluuFaviconImage
                              | gluuFederationHostingEnabled
                              | gluuInvoiceNo
                              | gluuLogoImage
                              | gluuManageIdentityPermission
                              | gluuManager
                              | gluuManagerGroup
                              | gluuOrgShortName
                              | gluuPaidUntil
                              | gluuPaymentProcessorTimestamp
                              | gluuProStoresUser
                              | gluuStatus
                              | gluuTempFaviconImage
                              | gluuThemeColor
                              | gluuWhitePagesEnabled
                              | iname
                              | inum
                              | localityName
                              | mail
                              | memberOf
                              | nonProfit
                              | organizationName
                              | oxCreationTimestamp
                              | oxLinkLinktrack
                              | oxLinktrackEnabled
                              | oxLinktrackLogin
                              | oxLinktrackPassword
                              | oxRegistrationConfiguration
                              | postalCode
                              | proStoresToken
                              | prostoresTimestamp
                              | scimAuthMode
                              | scimGroup
                              | scimStatus
                              | stateOrProvinceName
                              | streetAddress
                              | telephoneNumber
                              | title
                              | uid
                              | userPassword
                              | oxTrustLogoPath
                              | oxTrustFaviconPath
                              | oxAuthLogoPath
                              | oxAuthFaviconPath
                              | idpLogoPath
                              | idpFaviconPath }
  LDAP-NAME                 {"gluuOrganization"}
  ID                        id-oc-gluuOrganization }

-- X-ORIGIN: "Gluu created objectclass"
gluuConfiguration OBJECT-CLASS ::= {
  SUBCLASS OF               { top }
  MUST CONTAIN              { objectClass }
  MAY CONTAIN               { blowfishPassword
                              | countryName
                              | organizationalUnitName
                              | description
                              | displayName
                              | gluuAdditionalBandwidth
                              | gluuAdditionalMemory
                              | gluuApplianceDnsServer
                              | gluuAppliancePollingInterval
                              | gluuBandwidthRX
                              | gluuBandwidthTX
                              | gluuDSstatus
                              | gluuFederationHostingEnabled
                              | gluuHTTPstatus
                              | gluuHostname
                              | gluuInvoiceNo
                              | gluuLastUpdate
                              | gluuLifeRay
                              | gluuManageIdentityPermission
                              | gluuManager
                              | gluuMaxLogSize
                              | gluuOrgProfileMgt
                              | gluuPaidUntil
                              | gluuPaymentProcessorTimestamp
                              | gluuPrivate
                              | gluuPublishIdpMetadata
                              | gluuResizeInitiated
                              | gluuSPTR
                              | gluuScimEnabled
                              | gluuShibAssertionsIssued
                              | gluuShibFailedAuth
                              | gluuShibSecurityEvents
                              | gluuShibSuccessfulAuths
                              | oxTrustEmail
                              | gluuSmtpFromEmailAddress
                              | gluuSmtpFromName
                              | gluuSmtpHost
                              | gluuSmtpPassword
                              | gluuSmtpPort
                              | gluuSmtpRequiresAuthentication
                              | gluuSmtpRequiresSsl
                              | gluuSmtpUserName
                              | gluuSslExpiry
                              | gluuStatus
                              | gluuTargetRAM
                              | gluuUrl
                              | gluuVDSenabled
                              | gluuVDSstatus
                              | gluuVdsCacheRefreshEnabled
                              | gluuVdsCacheRefreshLastUpdate
                              | gluuVdsCacheRefreshLastUpdateCount
                              | gluuVdsCacheRefreshPollingInterval
                              | gluuVdsCacheRefreshProblemCount
                              | gluuWhitePagesEnabled
                              | iname
                              | inum
                              | inumFN
                              | organizationName
                              | oxAuthenticationMode
                              | oxTrustAuthenticationMode
                              | oxIDPAuthentication
                              | oxLogViewerConfig
                              | oxLogConfigLocation
                              | oxSmtpConfiguration
                              | oxCacheConfiguration
                              | oxDocumentStoreConfiguration
                              | oxTrustStoreCert
                              | oxTrustStoreConf
                              | passwordResetAllowed
                              | softwareVersion
                              | userPassword
                              | oxTrustCacheRefreshServerIpAddress
                              | gluuPassportEnabled
                              | gluuRadiusEnabled
                              | gluuSamlEnabled
                              | gluuSmtpServerTrust }
  LDAP-NAME                 {"gluuConfiguration"}
  ID                        id-oc-gluuConfiguration }

-- X-ORIGIN: "Gluu created objectclass"
gluuAttribute OBJECT-CLASS ::= {
  SUBCLASS OF               { top }
  MUST CONTAIN              { objectClass }
  MAY CONTAIN               { description
                              | displayName
                              | gluuAttributeEditType
                              | gluuAttributeName
                              | gluuAttributeOrigin
                              | gluuAttributeSystemEditType
                              | gluuAttributeType
                              | oxAuthClaimName
                              | gluuAttributeUsageType
                              | gluuAttributeViewType
                              | gluuCategory
                              | gluuSAML1URI
                              | gluuSAML2URI
                              | gluuStatus
                              | iname
                              | inum
                              | oxMultivaluedAttribute
                              | oxNameIdType
                              | oxSCIMCustomAttribute
                              | oxSourceAttribute
                              | seeAlso
                              | urn
                              | gluuRegExp
                              | gluuTooltip
                              | oxValidation }
  LDAP-NAME                 {"gluuAttribute"}
  ID                        id-oc-gluuAttribute }

-- X-ORIGIN: "Gluu created objectclass"
gluuSAMLconfig OBJECT-CLASS ::= {
  SUBCLASS OF               { top }
  MUST CONTAIN              { objectClass }
  MAY CONTAIN               { description
                              | displayName
                              | federationRules
                              | gluuContainerFederation
                              | gluuEntityId
                              | gluuIsFederation
                              | gluuProfileConfiguration
                              | gluuReleasedAttribute
                              | gluuRulesAccepted
                              | gluuSAMLMetaDataFilter
                              | gluuSAMLTrustEngine
                              | gluuSAMLmaxRefreshDelay
                              | gluuSAMLspMetaDataFN
                              | gluuSAMLspMetaDataSourceType
                              | gluuSAMLspMetaDataURL
                              | gluuSpecificRelyingPartyConfig
                              | gluuStatus
                              | gluuTrustContact
                              | gluuTrustDeconstruction
                              | gluuValidationLog
                              | gluuValidationStatus
                              | iname
                              | inum
                              | organizationName
                              | oxAuthPostLogoutRedirectURI
                              | url
                              | researchAndScholarshipEnabled
                              | gluuEntityType }
  LDAP-NAME                 {"gluuSAMLconfig"}
  ID                        id-oc-gluuSAMLconfig }

-- X-ORIGIN: "Gluu created objectclass"
gluuInumMap OBJECT-CLASS ::= {
  SUBCLASS OF               { top }
  MUST CONTAIN              { objectClass }
  MAY CONTAIN               { gluuStatus
                              | inum
                              | primaryKeyAttrName
                              | primaryKeyValue
                              | secondaryKeyAttrName
                              | secondaryKeyValue
                              | tertiaryKeyAttrName
                              | tertiaryKeyValue }
  LDAP-NAME                 {"gluuInumMap"}
  ID                        id-oc-gluuInumMap }

-- X-ORIGIN: "Gluu created objectclass"
gluuInvoice OBJECT-CLASS ::= {
  SUBCLASS OF               { top }
  MUST CONTAIN              { objectClass }
  MAY CONTAIN               { gluuInvoiceAmount
                              | gluuInvoiceDate
                              | gluuInvoiceLineItemName
                              | gluuInvoiceNumber
                              | gluuInvoiceProductNumber
                              | gluuInvoiceQuantity
                              | gluuInvoiceStatus
                              | inum }
  LDAP-NAME                 {"gluuInvoice"}
  ID                        id-oc-gluuInvoice }

-- X-ORIGIN: "Gluu created objectclass"
gluuPasswordResetRequest OBJECT-CLASS ::= {
  SUBCLASS OF               { top }
  MUST CONTAIN              { objectClass }
  MAY CONTAIN               { creationDate
                              | oxGuid
                              | personInum }
  LDAP-NAME                 {"gluuPasswordResetRequest"}
  ID                        id-oc-gluuPasswordResetRequest }

-- X-ORIGIN: "Gluu created objectclass"
oxLink OBJECT-CLASS ::= {
  SUBCLASS OF               { top }
  MUST CONTAIN              { objectClass }
  MAY CONTAIN               { description
                              | oxGuid
                              | oxLinkCreator
                              | oxLinkExpirationDate
                              | oxLinkLinktrack
                              | oxLinkModerated
                              | oxLinkModerators
                              | oxLinkPending }
  LDAP-NAME                 {"oxLink"}
  ID                        id-oc-oxLink }

-- X-ORIGIN: "Gluu created objectclass"
vdapcontainer OBJECT-CLASS ::= {
  SUBCLASS OF               { top }
  MUST CONTAIN              { objectClass }
  MAY CONTAIN               { organizationalUnitName }
  LDAP-NAME                 {"vdapcontainer"}
  ID                        id-oc-vdapcontainer }

-- X-ORIGIN: "Gluu created objectclass"
vdDirectoryView OBJECT-CLASS ::= {
  SUBCLASS OF               { top }
  MUST CONTAIN              { objectClass }
  MAY CONTAIN               { organizationName }
  LDAP-NAME                 {"vdDirectoryView"}
  ID                        id-oc-vdDirectoryView }

-- X-ORIGIN: "Gluu created objectclass"
vdlabel OBJECT-CLASS ::= {
  SUBCLASS OF               { top }
  MUST CONTAIN              { objectClass }
  MAY CONTAIN               { organizationName }
  LDAP-NAME                 {"vdlabel"}
  ID                        id-oc-vdlabel }

-- X-ORIGIN: "Gluu created objectclass"
oxEntry OBJECT-CLASS ::= {
  SUBCLASS OF               { top }
  MUST CONTAIN              { objectClass }
  MAY CONTAIN               { displayName
                              | iname
                              | inum }
  LDAP-NAME                 {"oxEntry"}
  ID                        id-oc-oxEntry }

-- X-ORIGIN: "Gluu created objectclass"
oxNode OBJECT-CLASS ::= {
  SUBCLASS OF               { top }
  MUST CONTAIN              { objectClass }
  MAY CONTAIN               { organizationalOwner
                              | owner
                              | sourceRelationalXdiStatement
                              | targetRelationalXdiStatement
                              | x
                              | xdiStatement
                              | xri }
  LDAP-NAME                 {"oxNode"}
  ID                        id-oc-oxNode }

-- X-ORIGIN: "Gluu created objectclass"
oxAuthClient OBJECT-CLASS ::= {
  SUBCLASS OF               { top }
  MUST CONTAIN              { objectClass }
  MAY CONTAIN               { associatedPerson
                              | displayName
                              | description
                              | inum
                              | oxAuthAppType
                              | oxAuthClientIdIssuedAt
                              | oxAuthClientSecret
                              | oxAuthClientSecretExpiresAt
                              | exp
                              | del
                              | oxAuthClientURI
                              | oxAuthContact
                              | oxAuthDefaultAcrValues
                              | oxAuthDefaultMaxAge
                              | oxAuthGrantType
                              | oxAuthIdTokenEncryptedResponseAlg
                              | oxAuthIdTokenEncryptedResponseEnc
                              | oxAuthIdTokenSignedResponseAlg
                              | oxAuthInitiateLoginURI
                              | oxAuthJwksURI
                              | oxAuthJwks
                              | oxAuthLogoURI
                              | oxAuthPolicyURI
                              | oxAuthPostLogoutRedirectURI
                              | oxAuthRedirectURI
                              | oxAuthRegistrationAccessToken
                              | oxAuthRequestObjectSigningAlg
                              | oxAuthRequestObjectEncryptionAlg
                              | oxAuthRequestObjectEncryptionEnc
                              | oxAuthRequestURI
                              | oxAuthRequireAuthTime
                              | oxAuthResponseType
                              | oxAuthScope
                              | oxAuthClaim
                              | oxAuthSectorIdentifierURI
                              | oxAuthSignedResponseAlg
                              | oxAuthSubjectType
                              | oxAuthTokenEndpointAuthMethod
                              | oxAuthTokenEndpointAuthSigningAlg
                              | oxAuthTosURI
                              | oxAuthTrustedClient
                              | oxAuthUserInfoEncryptedResponseAlg
                              | oxAuthUserInfoEncryptedResponseEnc
                              | oxAuthExtraConf
                              | oxClaimRedirectURI
                              | oxLastAccessTime
                              | oxLastLogonTime
                              | oxPersistClientAuthorizations
                              | oxIncludeClaimsInIdToken
                              | oxRefreshTokenLifetime
                              | oxDisabled
                              | oxAuthLogoutURI
                              | oxAuthLogoutSessionRequired
                              | oxdId
                              | oxAuthAuthorizedOrigins
                              | tknBndCnf
                              | oxAccessTokenAsJwt
                              | oxAccessTokenSigningAlg
                              | oxAccessTokenLifetime
                              | oxSoftwareId
                              | oxSoftwareVersion
                              | oxSoftwareStatement
                              | oxRptAsJwt
                              | oxAttributes
                              | oxAuthBackchannelTokenDeliveryMode
                              | oxAuthBackchannelClientNotificationEndpoint
                              | oxAuthBackchannelAuthenticationRequestSigningAlg
                              | oxAuthBackchannelUserCodeParameter }
  LDAP-NAME                 {"oxAuthClient"}
  ID                        id-oc-oxAuthClient }

-- X-ORIGIN: "Gluu created objectclass"
oxAuthCustomScope OBJECT-CLASS ::= {
  SUBCLASS OF               { top }
  MUST CONTAIN              { objectClass }
  MAY CONTAIN               { defaultScope
                              | description
                              | displayName
                              | inum
                              | oxScopeType
                              | oxAuthClaim
                              | oxScriptDn
                              | oxAuthGroupClaims
                              | oxId
                              | oxIconUrl
                              | oxUmaPolicyScriptDn
                              | oxAttributes
                              | exp
                              | del }
  LDAP-NAME                 {"oxAuthCustomScope"}
  ID                        id-oc-oxAuthCustomScope }

-- disambiguated oxAuthSessionId to oxAuthSessionId-2 inside LdapOx.
-- X-ORIGIN: "Gluu created objectclass"
oxAuthSessionId-2 OBJECT-CLASS ::= {
  SUBCLASS OF               { top }
  MUST CONTAIN              { objectClass }
  MAY CONTAIN               { oxId
                              | sid
                              | creationDate
                              | exp
                              | del
                              | oxLastAccessTime
                              | oxAuthUserDN
                              | authnTime
                              | oxState
                              | oxSessionState
                              | oxAuthPermissionGranted
                              | oxAsJwt
                              | oxJwt
                              | oxAuthPermissionGrantedMap
                              | oxInvolvedClients
                              | oxAuthSessionAttribute }
  LDAP-NAME                 {"oxAuthSessionId"}
  ID                        id-oc-oxAuthSessionId-2 }

-- X-ORIGIN: "Gluu created objectclass"
oxAuthConfiguration OBJECT-CLASS ::= {
  SUBCLASS OF               { top }
  MUST CONTAIN              { objectClass }
  MAY CONTAIN               { organizationalUnitName
                              | oxAuthConfDynamic
                              | oxAuthConfErrors
                              | oxAuthConfStatic
                              | oxAuthConfWebKeys
                              | oxRevision
                              | oxWebKeysSettings }
  LDAP-NAME                 {"oxAuthConfiguration"}
  ID                        id-oc-oxAuthConfiguration }

-- X-ORIGIN: "Gluu created objectclass"
oxTrustConfiguration OBJECT-CLASS ::= {
  SUBCLASS OF               { top }
  MUST CONTAIN              { objectClass }
  MAY CONTAIN               { organizationalUnitName
                              | oxTrustConfApplication
                              | oxTrustConfCacheRefresh
                              | oxRevision
                              | oxTrustConfImportPerson
                              | oxTrustConfAttributeResolver }
  LDAP-NAME                 {"oxTrustConfiguration"}
  ID                        id-oc-oxTrustConfiguration }

-- X-ORIGIN: "Gluu created objectclass"
oxApplicationConfiguration OBJECT-CLASS ::= {
  SUBCLASS OF               { top }
  MUST CONTAIN              { objectClass }
  MAY CONTAIN               { organizationalUnitName
                              | oxConfApplication
                              | oxRevision }
  LDAP-NAME                 {"oxApplicationConfiguration"}
  ID                        id-oc-oxApplicationConfiguration }

-- X-ORIGIN: "Gluu created objectclass"
oxUmaResource OBJECT-CLASS ::= {
  SUBCLASS OF               { top }
  MUST CONTAIN              { objectClass }
  MAY CONTAIN               { displayName
                              | inum
                              | owner
                              | oxAssociatedClient
                              | oxAuthUmaScope
                              | oxFaviconImage
                              | oxGroup
                              | oxId
                              | oxResource
                              | oxRevision
                              | oxType
                              | oxScopeExpression
                              | iat
                              | exp
                              | del
                              | description }
  LDAP-NAME                 {"oxUmaResource"}
  ID                        id-oc-oxUmaResource }

-- X-ORIGIN: "Gluu created objectclass"
oxUmaResourcePermission OBJECT-CLASS ::= {
  SUBCLASS OF               { top }
  MUST CONTAIN              { objectClass }
  MAY CONTAIN               { exp
                              | del
                              | oxAuthUmaScope
                              | oxConfigurationCode
                              | oxResourceSetId
                              | oxAttributes
                              | oxTicket
                              | oxStatus }
  LDAP-NAME                 {"oxUmaResourcePermission"}
  ID                        id-oc-oxUmaResourcePermission }

-- X-ORIGIN: "Gluu created objectclass"
oxAuthGrant OBJECT-CLASS ::= {
  SUBCLASS OF               { top }
  MUST CONTAIN              { objectClass }
  MAY CONTAIN               { grtId
                              | iat }
  LDAP-NAME                 {"oxAuthGrant"}
  ID                        id-oc-oxAuthGrant }

-- X-ORIGIN: "Gluu created objectclass"
token OBJECT-CLASS ::= {
  SUBCLASS OF               { top }
  MUST CONTAIN              { objectClass }
  MAY CONTAIN               { authnTime
                              | authzCode
                              | iat
                              | exp
                              | del
                              | grtId
                              | grtTyp
                              | jwtReq
                              | nnc
                              | scp
                              | tknCde
                              | tknTyp
                              | oxAuthUserId
                              | clnId
                              | acr
                              | uuid
                              | chlng
                              | chlngMth
                              | clms
                              | ssnId
                              | attr
                              | tknBndCnf }
  LDAP-NAME                 {"token"}
  ID                        id-oc-token }

-- X-ORIGIN: "Gluu created objectclass"
oxAuthUmaRPT OBJECT-CLASS ::= {
  SUBCLASS OF               { top }
  MUST CONTAIN              { objectClass }
  MAY CONTAIN               { authnTime
                              | clnId
                              | iat
                              | exp
                              | del
                              | tknCde
                              | oxAuthUserId
                              | oxUmaPermission
                              | uuid }
  LDAP-NAME                 {"oxAuthUmaRPT"}
  ID                        id-oc-oxAuthUmaRPT }

-- X-ORIGIN: "Gluu created objectclass"
oxLiteralNode OBJECT-CLASS ::= {
  SUBCLASS OF               { top }
  MUST CONTAIN              { objectClass }
  MAY CONTAIN               { literalBinaryValue
                              | literalValue
                              | organizationalOwner
                              | owner
                              | targetRelationalXdiStatement
                              | x
                              | xdiStatement
                              | xri }
  LDAP-NAME                 {"oxLiteralNode"}
  ID                        id-oc-oxLiteralNode }

-- X-ORIGIN: "Gluu created objectclass"
oxProxConfiguration OBJECT-CLASS ::= {
  SUBCLASS OF               { top }
  MUST CONTAIN              { objectClass }
  MAY CONTAIN               { organizationalUnitName
                              | oxProxConf
                              | oxScriptDn }
  LDAP-NAME                 {"oxProxConfiguration"}
  ID                        id-oc-oxProxConfiguration }

-- X-ORIGIN: "Gluu created objectclass"
oxProxOp OBJECT-CLASS ::= {
  SUBCLASS OF               { top }
  MUST CONTAIN              { objectClass }
  MAY CONTAIN               { countryName
                              | displayName
                              | inum
                              | localityName
                              | oxDomain
                              | oxId
                              | oxX509PEM
                              | oxX509URL }
  LDAP-NAME                 {"oxProxOp"}
  ID                        id-oc-oxProxOp }

-- X-ORIGIN: "Gluu created objectclass"
oxProxClient OBJECT-CLASS ::= {
  SUBCLASS OF               { top }
  MUST CONTAIN              { objectClass }
  MAY CONTAIN               { displayName
                              | inum
                              | oxProxyClaimMapping
                              | oxProxyScope
                              | oxProxyToOpClientMapping }
  LDAP-NAME                 {"oxProxClient"}
  ID                        id-oc-oxProxClient }

-- X-ORIGIN: "Gluu created objectclass"
oxProxAccessToken OBJECT-CLASS ::= {
  SUBCLASS OF               { top }
  MUST CONTAIN              { objectClass }
  MAY CONTAIN               { iat
                              | exp
                              | del
                              | oxProxyAccessToken
                              | oxProxyClientId }
  LDAP-NAME                 {"oxProxAccessToken"}
  ID                        id-oc-oxProxAccessToken }

-- disambiguated oxScript to oxScript-2 inside LdapOx.
-- X-ORIGIN: "Gluu created objectclass"
oxScript-2 OBJECT-CLASS ::= {
  SUBCLASS OF               { top }
  MUST CONTAIN              { objectClass }
  MAY CONTAIN               { inum
                              | oxScript
                              | oxScriptType }
  LDAP-NAME                 {"oxScript"}
  ID                        id-oc-oxScript-2 }

-- disambiguated oxPushApplication to oxPushApplication-2 inside LdapOx.
-- X-ORIGIN: "Gluu created objectclass"
oxPushApplication-2 OBJECT-CLASS ::= {
  SUBCLASS OF               { top }
  MUST CONTAIN              { objectClass }
  MAY CONTAIN               { displayName
                              | oxId
                              | oxName
                              | oxPushApplicationConf }
  LDAP-NAME                 {"oxPushApplication"}
  ID                        id-oc-oxPushApplication-2 }

-- X-ORIGIN: "Gluu created objectclass"
oxPushDevice OBJECT-CLASS ::= {
  SUBCLASS OF               { top }
  MUST CONTAIN              { objectClass }
  MAY CONTAIN               { oxAuthUserId
                              | oxId
                              | oxPushApplication
                              | oxPushDeviceConf
                              | oxType }
  LDAP-NAME                 {"oxPushDevice"}
  ID                        id-oc-oxPushDevice }

-- X-ORIGIN: "Gluu created objectclass"
oxCustomScript OBJECT-CLASS ::= {
  SUBCLASS OF               { top }
  MUST CONTAIN              { objectClass }
  MAY CONTAIN               { inum
                              | displayName
                              | description
                              | oxScript
                              | oxScriptType
                              | programmingLanguage
                              | oxModuleProperty
                              | oxConfigurationProperty
                              | oxLevel
                              | oxRevision
                              | oxEnabled
                              | oxScriptError
                              | oxAlias }
  LDAP-NAME                 {"oxCustomScript"}
  ID                        id-oc-oxCustomScript }

-- X-ORIGIN: "Gluu created objectclass"
oxDeviceRegistration OBJECT-CLASS ::= {
  SUBCLASS OF               { top }
  MUST CONTAIN              { objectClass }
  MAY CONTAIN               { oxId
                              | displayName
                              | description
                              | oxDeviceKeyHandle
                              | oxDeviceHashCode
                              | oxApplication
                              | oxDeviceRegistrationConf
                              | oxDeviceNotificationConf
                              | oxNickName
                              | oxDeviceData
                              | oxCounter
                              | oxStatus
                              | del
                              | exp
                              | personInum
                              | creationDate
                              | oxLastAccessTime
                              | oxTrustMetaLastModified
                              | oxTrustMetaLocation
                              | oxTrustMetaVersion }
  LDAP-NAME                 {"oxDeviceRegistration"}
  ID                        id-oc-oxDeviceRegistration }

-- X-ORIGIN: "Gluu created objectclass"
oxU2fRequest OBJECT-CLASS ::= {
  SUBCLASS OF               { top }
  MUST CONTAIN              { objectClass }
  MAY CONTAIN               { oxId
                              | oxRequestId
                              | oxRequest
                              | oxSessionStateId
                              | del
                              | exp
                              | personInum
                              | creationDate }
  LDAP-NAME                 {"oxU2fRequest"}
  ID                        id-oc-oxU2fRequest }

-- X-ORIGIN: "Gluu created objectclass"
oxMetric OBJECT-CLASS ::= {
  SUBCLASS OF               { top }
  MUST CONTAIN              { objectClass }
  MAY CONTAIN               { uniqueIdentifier
                              | oxStartDate
                              | oxEndDate
                              | oxApplicationType
                              | oxMetricType
                              | creationDate
                              | del
                              | exp
                              | oxData
                              | oxHost }
  LDAP-NAME                 {"oxMetric"}
  ID                        id-oc-oxMetric }

-- X-ORIGIN: "Gluu created objectclass"
oxClientAuthorization OBJECT-CLASS ::= {
  SUBCLASS OF               { top }
  MUST CONTAIN              { objectClass }
  MAY CONTAIN               { oxId
                              | oxAuthClientId
                              | oxAuthUserId
                              | exp
                              | del
                              | oxAuthScope }
  LDAP-NAME                 {"oxClientAuthorization"}
  ID                        id-oc-oxClientAuthorization }

-- disambiguated oxSectorIdentifier to oxSectorIdentifier-2 inside LdapOx.
-- X-ORIGIN: "Gluu created objectclass"
oxSectorIdentifier-2 OBJECT-CLASS ::= {
  SUBCLASS OF               { top }
  MUST CONTAIN              { objectClass }
  MAY CONTAIN               { oxId
                              | description
                              | oxAuthRedirectURI
                              | oxAuthClientId }
  LDAP-NAME                 {"oxSectorIdentifier"}
  ID                        id-oc-oxSectorIdentifier-2 }

-- X-ORIGIN: "Gluu created objectclass"
oxPassportConfiguration OBJECT-CLASS ::= {
  SUBCLASS OF               { top }
  MUST CONTAIN              { objectClass }
  MAY CONTAIN               { organizationalUnitName
                              | gluuPassportConfiguration
                              | gluuStatus }
  LDAP-NAME                 {"oxPassportConfiguration"}
  ID                        id-oc-oxPassportConfiguration }

-- X-ORIGIN: "Gluu created objectclass"
oxShibbolethCASProtocolConfiguration OBJECT-CLASS ::= {
  SUBCLASS OF               { top }
  MUST CONTAIN              { objectClass }
  MAY CONTAIN               { organizationalUnitName
                              | uniqueIdentifier
                              | inum
                              | oxConfApplication
                              | oxRevision }
  LDAP-NAME                 {"oxShibbolethCASProtocolConfiguration"}
  ID                        id-oc-oxShibbolethCASProtocolConfiguration }

-- X-ORIGIN: "Gluu created objectclass"
oxAuthUmaPCT OBJECT-CLASS ::= {
  SUBCLASS OF               { top }
  MUST CONTAIN              { objectClass }
  MAY CONTAIN               { clnId
                              | iat
                              | exp
                              | del
                              | tknCde
                              | oxClaimValues }
  LDAP-NAME                 {"oxAuthUmaPCT"}
  ID                        id-oc-oxAuthUmaPCT }

-- X-ORIGIN: "Gluu created objectclass"
cache OBJECT-CLASS ::= {
  SUBCLASS OF               { top }
  MUST CONTAIN              { objectClass }
  MAY CONTAIN               { uuid
                              | iat
                              | exp
                              | del
                              | dat }
  LDAP-NAME                 {"cache"}
  ID                        id-oc-cache }

-- X-ORIGIN: "Gluu created objectclass"
oxFido2AuthenticationEntry OBJECT-CLASS ::= {
  SUBCLASS OF               { top }
  MUST CONTAIN              { objectClass }
  MAY CONTAIN               { oxId
                              | creationDate
                              | oxSessionStateId
                              | oxCodeChallenge
                              | personInum
                              | oxAuthenticationData
                              | oxStatus }
  LDAP-NAME                 {"oxFido2AuthenticationEntry"}
  ID                        id-oc-oxFido2AuthenticationEntry }

-- X-ORIGIN: "Gluu created objectclass"
oxFido2RegistrationEntry OBJECT-CLASS ::= {
  SUBCLASS OF               { top }
  MUST CONTAIN              { objectClass }
  MAY CONTAIN               { oxId
                              | creationDate
                              | displayName
                              | oxSessionStateId
                              | oxCodeChallenge
                              | oxCodeChallengeHash
                              | oxPublicKeyId
                              | personInum
                              | oxRegistrationData
                              | oxDeviceNotificationConf
                              | oxCounter
                              | oxStatus }
  LDAP-NAME                 {"oxFido2RegistrationEntry"}
  ID                        id-oc-oxFido2RegistrationEntry }

-- X-ORIGIN: "Gluu created objectclass"
samlAcr OBJECT-CLASS ::= {
  SUBCLASS OF               { top }
  MUST CONTAIN              { objectClass }
  MAY CONTAIN               { parent
                              | classRef
                              | inum }
  LDAP-NAME                 {"samlAcr"}
  ID                        id-oc-samlAcr }

-- X-ORIGIN: "Gluu created objectclass"
gluuOxtrustStat OBJECT-CLASS ::= {
  SUBCLASS OF               { top }
  MUST CONTAIN              { objectClass }
  MAY CONTAIN               { gluuFreeDiskSpace
                              | gluuFreeMemory
                              | gluuFreeSwap
                              | gluuGroupCount
                              | gluuIpAddress
                              | gluuLoadAvg
                              | gluuPersonCount
                              | gluuSystemUptime
                              | uniqueIdentifier }
  LDAP-NAME                 {"gluuOxtrustStat"}
  ID                        id-oc-gluuOxtrustStat }

-- X-ORIGIN: "Gluu created objectclass"
gluuApplicationConfiguration OBJECT-CLASS ::= {
  SUBCLASS OF               { top }
  MUST CONTAIN              { objectClass }
  MAY CONTAIN               { organizationalUnitName
                              | gluuConfDynamic
                              | gluuConfStatic
                              | oxRevision }
  LDAP-NAME                 {"gluuApplicationConfiguration"}
  ID                        id-oc-gluuApplicationConfiguration }

-- X-ORIGIN: "Gluu created objectclass"
oxExpiredObject OBJECT-CLASS ::= {
  SUBCLASS OF               { top }
  MUST CONTAIN              { objectClass }
  MAY CONTAIN               { oxId
                              | dat
                              | iat
                              | exp
                              | oxType }
  LDAP-NAME                 {"oxExpiredObject"}
  ID                        id-oc-oxExpiredObject }

-- X-ORIGIN: "Gluu created objectclass"
oxRp OBJECT-CLASS ::= {
  SUBCLASS OF               { top }
  MUST CONTAIN              { objectClass }
  MAY CONTAIN               { oxId
                              | dat }
  LDAP-NAME                 {"oxRp"}
  ID                        id-oc-oxRp }

-- X-ORIGIN: "Gluu created objectclass"
cibaRequest OBJECT-CLASS ::= {
  SUBCLASS OF               { top }
  MUST CONTAIN              { objectClass }
  MAY CONTAIN               { authReqId
                              | clnId
                              | oxAuthUserId
                              | creationDate
                              | exp
                              | oxStatus }
  LDAP-NAME                 {"cibaRequest"}
  ID                        id-oc-cibaRequest }

-- X-ORIGIN: "Gluu created objectclass"
jansStatEntry OBJECT-CLASS ::= {
  SUBCLASS OF               { top }
  MUST CONTAIN              { objectClass }
  MAY CONTAIN               { jansId
                              | dat
                              | attr }
  LDAP-NAME                 {"jansStatEntry"}
  ID                        id-oc-jansStatEntry }
END
