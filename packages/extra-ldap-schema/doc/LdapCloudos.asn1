-- Derived from data/ldap-schema/cloudos.ldif
-- Upstream: https://github.com/cloudstead/cloudos-apps/blob/8f0abf71d6751c1e6f4950f2ac9fdcace6a21fe7/apps/kolab/files/99cloudos.ldif#L11
-- This module is a container for LDAP schema. It has no module identifier.
-- X- extension fields from the LDAP schema are comments. USAGE userApplications and structural KIND are omitted because they are the defaults.
-- LDAP {length} bounds on directory strings are DirectoryString{n}. Bounds on IA5String, PrintableString, NumericString, and OCTET STRING are SIZE (1..n). Other bounds stay comments because the LDAP figure is an encoded-length hint.
LdapCloudos DEFINITIONS ::=
BEGIN

IMPORTS

  ATTRIBUTE, OBJECT-CLASS, top
    FROM InformationFramework
      {joint-iso-itu-t ds(5) module(1) informationFramework(1) 9} WITH SUCCESSORS

  boolean, booleanMatch, caseIgnoreIA5Match, caseIgnoreIA5SubstringsMatch,
    ia5String, numericString
    FROM SelectedAttributeTypes
      {joint-iso-itu-t ds(5) module(1) selectedAttributeTypes(5) 9} WITH SUCCESSORS ;

-- Object identifiers

id-at-ctime OBJECT IDENTIFIER ::= { 1 3 6 1 4 1 46577 100 1 }
id-at-resetPasswordToken OBJECT IDENTIFIER ::= { 1 3 6 1 4 1 46577 100 2 }
id-at-resetPasswordTokenCtime OBJECT IDENTIFIER ::= { 1 3 6 1 4 1 46577 100 3 }
id-at-emailVerificationCode OBJECT IDENTIFIER ::= { 1 3 6 1 4 1 46577 100 4 }
id-at-emailVerificationCodeCtime OBJECT IDENTIFIER ::= { 1 3 6 1 4 1 46577 100 5 }
id-at-emailVerified OBJECT IDENTIFIER ::= { 1 3 6 1 4 1 46577 100 6 }
id-at-mobilePhoneCountryCode OBJECT IDENTIFIER ::= { 1 3 6 1 4 1 46577 100 7 }
id-at-mobilePhone OBJECT IDENTIFIER ::= { 1 3 6 1 4 1 46577 100 8 }
id-at-admin OBJECT IDENTIFIER ::= { 1 3 6 1 4 1 46577 100 9 }
id-at-suspended OBJECT IDENTIFIER ::= { 1 3 6 1 4 1 46577 100 10 }
id-at-twoFactor OBJECT IDENTIFIER ::= { 1 3 6 1 4 1 46577 100 11 }
id-at-twoFactorAuthId OBJECT IDENTIFIER ::= { 1 3 6 1 4 1 46577 100 12 }
id-at-lastLogin OBJECT IDENTIFIER ::= { 1 3 6 1 4 1 46577 100 13 }
id-at-storageQuota OBJECT IDENTIFIER ::= { 1 3 6 1 4 1 46577 100 14 }
id-at-mirror OBJECT IDENTIFIER ::= { 1 3 6 1 4 1 46577 100 15 }
id-at-entryUUID OBJECT IDENTIFIER ::= { 1 3 6 1 4 1 46577 100 16 }
id-oc-cloudosInetOrgPerson OBJECT IDENTIFIER ::= { 1 3 6 1 4 1 46577 200 1 }
id-oc-cloudosGroupOfUniqueNames OBJECT IDENTIFIER ::= { 1 3 6 1 4 1 46577 200 2 }

-- Attribute types

ctime ATTRIBUTE ::= {
  WITH SYNTAX               IA5String(SIZE (1..256))
  EQUALITY MATCHING RULE    caseIgnoreIA5Match
  SUBSTRINGS MATCHING RULE  caseIgnoreIA5SubstringsMatch
  LDAP-SYNTAX               ia5String.&id
  LDAP-NAME                 {"ctime"}
  LDAP-DESC                 "Token used to verify password reset"
  ID                        id-at-ctime }

resetPasswordToken ATTRIBUTE ::= {
  WITH SYNTAX               IA5String(SIZE (1..256))
  EQUALITY MATCHING RULE    caseIgnoreIA5Match
  SUBSTRINGS MATCHING RULE  caseIgnoreIA5SubstringsMatch
  LDAP-SYNTAX               ia5String.&id
  LDAP-NAME                 {"resetPasswordToken"}
  LDAP-DESC                 "Token used to verify password reset"
  ID                        id-at-resetPasswordToken }

resetPasswordTokenCtime ATTRIBUTE ::= {
  WITH SYNTAX               NumericString(SIZE (1..256))
  LDAP-SYNTAX               numericString.&id
  LDAP-NAME                 {"resetPasswordTokenCtime"}
  LDAP-DESC                 "When was the reset token set"
  ID                        id-at-resetPasswordTokenCtime }

emailVerificationCode ATTRIBUTE ::= {
  WITH SYNTAX               IA5String(SIZE (1..256))
  EQUALITY MATCHING RULE    caseIgnoreIA5Match
  SUBSTRINGS MATCHING RULE  caseIgnoreIA5SubstringsMatch
  LDAP-SYNTAX               ia5String.&id
  LDAP-NAME                 {"emailVerificationCode"}
  LDAP-DESC                 "Token used to verify email"
  ID                        id-at-emailVerificationCode }

emailVerificationCodeCtime ATTRIBUTE ::= {
  WITH SYNTAX               NumericString(SIZE (1..256))
  LDAP-SYNTAX               numericString.&id
  LDAP-NAME                 {"emailVerificationCodeCtime"}
  LDAP-DESC                 "When was the email token set"
  ID                        id-at-emailVerificationCodeCtime }

emailVerified ATTRIBUTE ::= {
  WITH SYNTAX               BOOLEAN
  EQUALITY MATCHING RULE    booleanMatch
  LDAP-SYNTAX               boolean.&id
  LDAP-NAME                 {"emailVerified"}
  LDAP-DESC                 "The email address has been verified"
  ID                        id-at-emailVerified }

mobilePhoneCountryCode ATTRIBUTE ::= {
  WITH SYNTAX               NumericString(SIZE (1..8))
  LDAP-SYNTAX               numericString.&id
  LDAP-NAME                 {"mobilePhoneCountryCode"}
  LDAP-DESC                 "Mobile phone country code"
  ID                        id-at-mobilePhoneCountryCode }

mobilePhone ATTRIBUTE ::= {
  WITH SYNTAX               NumericString(SIZE (1..256))
  LDAP-SYNTAX               numericString.&id
  LDAP-NAME                 {"mobilePhone"}
  LDAP-DESC                 "Mobile phone number"
  ID                        id-at-mobilePhone }

admin ATTRIBUTE ::= {
  WITH SYNTAX               BOOLEAN
  EQUALITY MATCHING RULE    booleanMatch
  LDAP-SYNTAX               boolean.&id
  LDAP-NAME                 {"admin"}
  LDAP-DESC                 "If true, this account is a CloudOs Admin"
  ID                        id-at-admin }

suspended ATTRIBUTE ::= {
  WITH SYNTAX               BOOLEAN
  EQUALITY MATCHING RULE    booleanMatch
  LDAP-SYNTAX               boolean.&id
  LDAP-NAME                 {"suspended"}
  LDAP-DESC                 "If true, this account is suspended in CloudOs"
  ID                        id-at-suspended }

twoFactor ATTRIBUTE ::= {
  WITH SYNTAX               BOOLEAN
  EQUALITY MATCHING RULE    booleanMatch
  LDAP-SYNTAX               boolean.&id
  LDAP-NAME                 {"twoFactor"}
  LDAP-DESC                 "If true, this account is enabled for 2-factor authentication"
  ID                        id-at-twoFactor }

twoFactorAuthId ATTRIBUTE ::= {
  WITH SYNTAX               IA5String(SIZE (1..256))
  EQUALITY MATCHING RULE    caseIgnoreIA5Match
  SUBSTRINGS MATCHING RULE  caseIgnoreIA5SubstringsMatch
  LDAP-SYNTAX               ia5String.&id
  LDAP-NAME                 {"twoFactorAuthId"}
  LDAP-DESC                 "User token with third-party 2-factor authentication service"
  ID                        id-at-twoFactorAuthId }

lastLogin ATTRIBUTE ::= {
  WITH SYNTAX               IA5String(SIZE (1..30))
  LDAP-SYNTAX               ia5String.&id
  LDAP-NAME                 {"lastLogin"}
  LDAP-DESC                 "Most recent login, formatted as YYYY-MM-DD HH:mm:ss"
  ID                        id-at-lastLogin }

storageQuota ATTRIBUTE ::= {
  WITH SYNTAX               NumericString(SIZE (1..50))
  LDAP-SYNTAX               numericString.&id
  LDAP-NAME                 {"storageQuota"}
  LDAP-DESC                 "Storage quota in bytes. Should be larger than mailQuota"
  ID                        id-at-storageQuota }

mirror ATTRIBUTE ::= {
  WITH SYNTAX               IA5String(SIZE (1..256))
  LDAP-SYNTAX               ia5String.&id
  LDAP-NAME                 {"mirror"}
  LDAP-DESC                 "Instructs CloudOs to merge the members of the referenced group into this one. The relationship is one-way. A group may pull from multiple mirrors."
  ID                        id-at-mirror }

entryUUID ATTRIBUTE ::= {
  WITH SYNTAX               IA5String(SIZE (1..40))
  LDAP-SYNTAX               ia5String.&id
  LDAP-NAME                 {"entryUUID"}
  LDAP-DESC                 "The UUID of the object in the CloudOs system."
  ID                        id-at-entryUUID }

-- Object classes

cloudosInetOrgPerson OBJECT-CLASS ::= {
  SUBCLASS OF               { top }
  KIND                      auxiliary
  MAY CONTAIN               { entryUUID
                              | ctime
                              | resetPasswordToken
                              | resetPasswordTokenCtime
                              | emailVerified
                              | emailVerificationCode
                              | emailVerificationCodeCtime
                              | mobilePhoneCountryCode
                              | mobilePhone
                              | admin
                              | suspended
                              | twoFactor
                              | twoFactorAuthId
                              | lastLogin
                              | storageQuota }
  LDAP-NAME                 {"cloudosInetOrgPerson"}
  LDAP-DESC                 "cloudos Internet Organizational Person"
  ID                        id-oc-cloudosInetOrgPerson }

cloudosGroupOfUniqueNames OBJECT-CLASS ::= {
  SUBCLASS OF               { top }
  KIND                      auxiliary
  MAY CONTAIN               { entryUUID
                              | mirror
                              | storageQuota }
  LDAP-NAME                 {"cloudosGroupOfUniqueNames"}
  LDAP-DESC                 "cloudos group of names"
  ID                        id-oc-cloudosGroupOfUniqueNames }
END
