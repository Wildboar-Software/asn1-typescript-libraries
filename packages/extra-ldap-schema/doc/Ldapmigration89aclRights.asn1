-- Derived from data/ldap-schema/ldapmigration/89acl-rights.ldif
-- This module is a container for LDAP schema. It has no module identifier.
-- X- extension fields from the LDAP schema are comments. USAGE userApplications and structural KIND are omitted because they are the defaults.
Ldapmigration89aclRights DEFINITIONS ::=
BEGIN

IMPORTS

  ATTRIBUTE
    FROM InformationFramework
      {joint-iso-itu-t ds(5) module(1) informationFramework(1) 9} WITH SUCCESSORS

  directoryString, UnboundedDirectoryString
    FROM SelectedAttributeTypes
      {joint-iso-itu-t ds(5) module(1) selectedAttributeTypes(5) 9} WITH SUCCESSORS ;

-- Object identifiers

id-at-aclRights OBJECT IDENTIFIER ::= { 1 3 6 1 4 1 42 2 27 9 1 39 }
id-at-aclRightsInfo OBJECT IDENTIFIER ::= { 1 3 6 1 4 1 42 2 27 9 1 40 }

-- Attribute types

-- X-DS-USE: "internal"
-- X-ORIGIN: "Sun ONE Directory Server"
aclRights ATTRIBUTE ::= {
  WITH SYNTAX               UnboundedDirectoryString
  NO USER MODIFICATION      TRUE
  USAGE                     directoryOperation
  LDAP-SYNTAX               directoryString.&id
  LDAP-NAME                 {"aclRights"}
  LDAP-DESC                 "Sun ONE defined attribute type"
  ID                        id-at-aclRights }

-- X-DS-USE: "internal"
-- X-ORIGIN: "Sun ONE Directory Server"
aclRightsInfo ATTRIBUTE ::= {
  WITH SYNTAX               UnboundedDirectoryString
  NO USER MODIFICATION      TRUE
  USAGE                     directoryOperation
  LDAP-SYNTAX               directoryString.&id
  LDAP-NAME                 {"aclRightsInfo"}
  LDAP-DESC                 "Sun ONE defined attribute type"
  ID                        id-at-aclRightsInfo }
END
