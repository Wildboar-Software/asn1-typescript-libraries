-- Derived from data/ldap-schema/ispenv.schema
-- Upstream: https://github.com/fln/gnarwl/blob/a4861bea0f40ab54d6f8ba4084e589030f338c43/doc/ISPEnv.schema#L78
-- This module is a container for LDAP schema. It has no module identifier.
-- X- extension fields from the LDAP schema are comments. USAGE userApplications and structural KIND are omitted because they are the defaults.
-- LDAP {length} bounds on directory strings are DirectoryString{n}. Bounds on IA5String, PrintableString, NumericString, and OCTET STRING are SIZE (1..n). Other bounds stay comments because the LDAP figure is an encoded-length hint.
LdapIspenv DEFINITIONS ::=
BEGIN

IMPORTS

  ATTRIBUTE, OBJECT-CLASS, top
    FROM InformationFramework
      {joint-iso-itu-t ds(5) module(1) informationFramework(1) 9} WITH SUCCESSORS

  boolean, booleanMatch, caseExactMatch, caseIgnoreIA5Match,
    caseIgnoreIA5SubstringsMatch, caseIgnoreMatch, commonName, dc, description,
    directoryString, facsimileTelephoneNumber, ia5String, integer,
    numericStringMatch, owner, postalAddress, postalCode, streetAddress,
    telephoneNumber, uid, UnboundedDirectoryString
    FROM SelectedAttributeTypes
      {joint-iso-itu-t ds(5) module(1) selectedAttributeTypes(5) 9} WITH SUCCESSORS

  userPassword
    FROM AuthenticationFramework
      {joint-iso-itu-t ds(5) module(1) authenticationFramework(7) 9} WITH SUCCESSORS

  caseExactIA5SubstringsMatch
    FROM OpenLDAP
      {iso(1) identified-organization(3) dod(6) internet(1) private(4) enterprise(1) wildboar(56490) module(1) openldap(28)} WITH SUCCESSORS

  mail
    FROM LdapSchema2ldifCore ;

-- Object identifiers

id-at-vacationActive OBJECT IDENTIFIER ::= { 1 3 6 1 4 1 11048 1 1 1 1 }
id-at-webAccess OBJECT IDENTIFIER ::= { 1 3 6 1 4 1 11048 1 1 1 2 }
id-at-vacationInfo OBJECT IDENTIFIER ::= { 1 3 6 1 4 1 11048 1 1 1 3 }
id-at-vacationStart OBJECT IDENTIFIER ::= { 1 3 6 1 4 1 11048 1 1 1 4 }
id-at-vacationEnd OBJECT IDENTIFIER ::= { 1 3 6 1 4 1 11048 1 1 1 5 }
id-at-maildropPlace OBJECT IDENTIFIER ::= { 1 3 6 1 4 1 11048 1 1 1 6 }
id-at-mailForward OBJECT IDENTIFIER ::= { 1 3 6 1 4 1 11048 1 1 1 7 }
id-at-proxyHost OBJECT IDENTIFIER ::= { 1 3 6 1 4 1 11048 1 1 1 8 }
id-at-mailHost OBJECT IDENTIFIER ::= { 1 3 6 1 4 1 11048 1 1 1 9 }
id-at-vacationForward OBJECT IDENTIFIER ::= { 1 3 6 1 4 1 11048 1 1 1 10 }
id-at-custID OBJECT IDENTIFIER ::= { 1 3 6 1 4 1 11048 1 1 1 11 }
id-at-billPaid OBJECT IDENTIFIER ::= { 1 3 6 1 4 1 11048 1 1 1 12 }
id-at-note OBJECT IDENTIFIER ::= { 1 3 6 1 4 1 11048 1 1 1 13 }
id-at-uucpHost OBJECT IDENTIFIER ::= { 1 3 6 1 4 1 11048 1 1 1 14 }
id-at-type OBJECT IDENTIFIER ::= { 1 3 6 1 4 1 11048 1 1 1 15 }
id-at-status OBJECT IDENTIFIER ::= { 1 3 6 1 4 1 11048 1 1 1 16 }
id-at-dunningCounter OBJECT IDENTIFIER ::= { 1 3 6 1 4 1 11048 1 1 1 17 }
id-at-price OBJECT IDENTIFIER ::= { 1 3 6 1 4 1 11048 1 1 1 18 }
id-at-currency OBJECT IDENTIFIER ::= { 1 3 6 1 4 1 11048 1 1 1 19 }
id-at-payperiod OBJECT IDENTIFIER ::= { 1 3 6 1 4 1 11048 1 1 1 20 }
id-at-payday OBJECT IDENTIFIER ::= { 1 3 6 1 4 1 11048 1 1 1 21 }
id-at-productcode OBJECT IDENTIFIER ::= { 1 3 6 1 4 1 11048 1 1 1 22 }
id-oc-vacation OBJECT IDENTIFIER ::= { 1 3 6 1 4 1 11048 1 1 2 1 }
id-oc-mailAccount OBJECT IDENTIFIER ::= { 1 3 6 1 4 1 11048 1 1 2 2 }
id-oc-caretaker OBJECT IDENTIFIER ::= { 1 3 6 1 4 1 11048 1 1 2 3 }
id-oc-proxyAccount OBJECT IDENTIFIER ::= { 1 3 6 1 4 1 11048 1 1 2 4 }
id-oc-customer OBJECT IDENTIFIER ::= { 1 3 6 1 4 1 11048 1 1 2 5 }
id-oc-genericAccount OBJECT IDENTIFIER ::= { 1 3 6 1 4 1 11048 1 1 2 6 }
id-oc-uucpAccount OBJECT IDENTIFIER ::= { 1 3 6 1 4 1 11048 1 1 2 7 }
id-oc-metaInfo OBJECT IDENTIFIER ::= { 1 3 6 1 4 1 11048 1 1 2 8 }
id-oc-accountable OBJECT IDENTIFIER ::= { 1 3 6 1 4 1 11048 1 1 2 9 }

-- Attribute types

vacationActive ATTRIBUTE ::= {
  WITH SYNTAX               BOOLEAN
  EQUALITY MATCHING RULE    booleanMatch
  SINGLE VALUE              TRUE
  LDAP-SYNTAX               boolean.&id
  LDAP-NAME                 {"vacationActive"}
  LDAP-DESC                 "A flag, signalling if the corresponding user is on vacation right now"
  ID                        id-at-vacationActive }

webAccess ATTRIBUTE ::= {
  WITH SYNTAX               BOOLEAN
  EQUALITY MATCHING RULE    booleanMatch
  SINGLE VALUE              TRUE
  LDAP-SYNTAX               boolean.&id
  LDAP-NAME                 {"webAccess"}
  LDAP-DESC                 "A flag, signalling if the corresponding user is allowed to access the web (through the proxy)"
  ID                        id-at-webAccess }

vacationInfo ATTRIBUTE ::= {
  WITH SYNTAX               UnboundedDirectoryString
  EQUALITY MATCHING RULE    caseExactIA5SubstringsMatch
  SINGLE VALUE              TRUE
  LDAP-SYNTAX               directoryString.&id
  LDAP-NAME                 {"vacationInfo"}
  LDAP-DESC                 "Absentee note"
  ID                        id-at-vacationInfo }

vacationStart ATTRIBUTE ::= {
  WITH SYNTAX               UnboundedDirectoryString
  EQUALITY MATCHING RULE    caseExactIA5SubstringsMatch
  SINGLE VALUE              TRUE
  LDAP-SYNTAX               directoryString.&id
  LDAP-NAME                 {"vacationStart"}
  LDAP-DESC                 "Start of vacation"
  ID                        id-at-vacationStart }

vacationEnd ATTRIBUTE ::= {
  WITH SYNTAX               UnboundedDirectoryString
  EQUALITY MATCHING RULE    caseExactIA5SubstringsMatch
  SINGLE VALUE              TRUE
  LDAP-SYNTAX               directoryString.&id
  LDAP-NAME                 {"vacationEnd"}
  LDAP-DESC                 "End of vacation"
  ID                        id-at-vacationEnd }

maildropPlace ATTRIBUTE ::= {
  WITH SYNTAX               UnboundedDirectoryString
  EQUALITY MATCHING RULE    caseExactMatch
  LDAP-SYNTAX               directoryString.&id
  LDAP-NAME                 {"maildropPlace"}
  LDAP-DESC                 "Where the users mail is stored"
  ID                        id-at-maildropPlace }

mailForward ATTRIBUTE ::= {
  WITH SYNTAX               IA5String(SIZE (1..256))
  EQUALITY MATCHING RULE    caseIgnoreIA5Match
  SUBSTRINGS MATCHING RULE  caseIgnoreIA5SubstringsMatch
  LDAP-SYNTAX               ia5String.&id
  LDAP-NAME                 {"mailForward"}
  LDAP-DESC                 "Address to forward email to"
  ID                        id-at-mailForward }

proxyHost ATTRIBUTE ::= {
  WITH SYNTAX               IA5String(SIZE (1..256))
  EQUALITY MATCHING RULE    caseIgnoreIA5Match
  LDAP-SYNTAX               ia5String.&id
  LDAP-NAME                 {"proxyHost"}
  LDAP-DESC                 "Fully qualified hostname of a proxyserver"
  ID                        id-at-proxyHost }

mailHost ATTRIBUTE ::= {
  WITH SYNTAX               IA5String(SIZE (1..256))
  EQUALITY MATCHING RULE    caseIgnoreIA5Match
  LDAP-SYNTAX               ia5String.&id
  LDAP-NAME                 {"mailHost"}
  LDAP-DESC                 "Fully qualified hostname of a mailserver"
  ID                        id-at-mailHost }

vacationForward ATTRIBUTE ::= {
  WITH SYNTAX               IA5String(SIZE (1..256))
  EQUALITY MATCHING RULE    caseIgnoreIA5Match
  SUBSTRINGS MATCHING RULE  caseIgnoreIA5SubstringsMatch
  LDAP-SYNTAX               ia5String.&id
  LDAP-NAME                 {"vacationForward"}
  LDAP-DESC                 "Where to forward mails to, while on vacation"
  ID                        id-at-vacationForward }

custID ATTRIBUTE ::= {
  WITH SYNTAX               UnboundedDirectoryString
  EQUALITY MATCHING RULE    caseExactMatch
  LDAP-SYNTAX               directoryString.&id
  LDAP-NAME                 {"custID"}
  LDAP-DESC                 "Unique ID value to identify a specific customer"
  ID                        id-at-custID }

billPaid ATTRIBUTE ::= {
  WITH SYNTAX               BOOLEAN
  EQUALITY MATCHING RULE    booleanMatch
  SINGLE VALUE              TRUE
  LDAP-SYNTAX               boolean.&id
  LDAP-NAME                 {"billPaid"}
  LDAP-DESC                 "Flag signalling, whether the customer has paid the bill"
  ID                        id-at-billPaid }

note ATTRIBUTE ::= {
  WITH SYNTAX               UnboundedDirectoryString
  EQUALITY MATCHING RULE    caseIgnoreMatch
  LDAP-SYNTAX               directoryString.&id
  LDAP-NAME                 {"note"}
  LDAP-DESC                 "A generic note"
  ID                        id-at-note }

uucpHost ATTRIBUTE ::= {
  WITH SYNTAX               IA5String(SIZE (1..256))
  EQUALITY MATCHING RULE    caseIgnoreIA5Match
  LDAP-SYNTAX               ia5String.&id
  LDAP-NAME                 {"uucpHost"}
  LDAP-DESC                 "Next hop in a uucp network"
  ID                        id-at-uucpHost }

type ATTRIBUTE ::= {
  WITH SYNTAX               UnboundedDirectoryString
  EQUALITY MATCHING RULE    caseExactMatch
  LDAP-SYNTAX               directoryString.&id
  LDAP-NAME                 {"type"}
  LDAP-DESC                 "For classifying an entry without using an objectclass"
  ID                        id-at-type }

status ATTRIBUTE ::= {
  WITH SYNTAX               UnboundedDirectoryString
  EQUALITY MATCHING RULE    caseExactMatch
  LDAP-SYNTAX               directoryString.&id
  LDAP-NAME                 {"status"}
  LDAP-DESC                 "For adding status information to an entry"
  ID                        id-at-status }

dunningCounter ATTRIBUTE ::= {
  WITH SYNTAX               INTEGER
  EQUALITY MATCHING RULE    numericStringMatch
  LDAP-SYNTAX               integer.&id
  LDAP-NAME                 {"dunningCounter"}
  LDAP-DESC                 "How many times the bill was not paid"
  ID                        id-at-dunningCounter }

price ATTRIBUTE ::= {
  WITH SYNTAX               IA5String
  EQUALITY MATCHING RULE    caseIgnoreMatch
  LDAP-SYNTAX               ia5String.&id
  LDAP-NAME                 {"price"}
  LDAP-DESC                 "How much to charge for a specific resource"
  ID                        id-at-price }

currency ATTRIBUTE ::= {
  WITH SYNTAX               IA5String
  EQUALITY MATCHING RULE    caseIgnoreMatch
  LDAP-SYNTAX               ia5String.&id
  LDAP-NAME                 {"currency"}
  LDAP-DESC                 "The currency, payment is expected in"
  ID                        id-at-currency }

payperiod ATTRIBUTE ::= {
  WITH SYNTAX               IA5String
  EQUALITY MATCHING RULE    caseIgnoreMatch
  LDAP-SYNTAX               ia5String.&id
  LDAP-NAME                 {"payperiod"}
  LDAP-DESC                 "The timeperiod, recurring payment is expected in"
  ID                        id-at-payperiod }

payday ATTRIBUTE ::= {
  WITH SYNTAX               IA5String
  EQUALITY MATCHING RULE    caseIgnoreMatch
  LDAP-SYNTAX               ia5String.&id
  LDAP-NAME                 {"payday"}
  LDAP-DESC                 "On which day payment is expected"
  ID                        id-at-payday }

productcode ATTRIBUTE ::= {
  WITH SYNTAX               IA5String
  EQUALITY MATCHING RULE    caseIgnoreMatch
  SINGLE VALUE              TRUE
  LDAP-SYNTAX               ia5String.&id
  LDAP-NAME                 {"productcode"}
  LDAP-DESC                 "Articlegroup identifier"
  ID                        id-at-productcode }

-- Object classes

-- initial capital of "Vacation" lowercased so the assignment is a valuereference.
vacation OBJECT-CLASS ::= {
  SUBCLASS OF               { top }
  KIND                      auxiliary
  MUST CONTAIN              { vacationActive }
  MAY CONTAIN               { vacationInfo
                              | vacationStart
                              | vacationEnd
                              | vacationForward }
  LDAP-NAME                 {"Vacation"}
  LDAP-DESC                 "Users vacation status information"
  ID                        id-oc-vacation }

mailAccount OBJECT-CLASS ::= {
  SUBCLASS OF               { top }
  KIND                      auxiliary
  MUST CONTAIN              { uid
                              | userPassword
                              | maildropPlace
                              | mail }
  MAY CONTAIN               { mailForward
                              | mailHost }
  LDAP-NAME                 {"mailAccount"}
  LDAP-DESC                 "Emailaccount, associated with a user"
  ID                        id-oc-mailAccount }

caretaker OBJECT-CLASS ::= {
  SUBCLASS OF               { top }
  MUST CONTAIN              { uid
                              | userPassword }
  MAY CONTAIN               { description
                              | owner }
  LDAP-NAME                 {"caretaker"}
  LDAP-DESC                 "For implementing administrative access control. This objectclass should be used to allow programs to bind to the LDAP tree."
  ID                        id-oc-caretaker }

proxyAccount OBJECT-CLASS ::= {
  SUBCLASS OF               { top }
  KIND                      auxiliary
  MUST CONTAIN              { webAccess
                              | uid
                              | userPassword }
  MAY CONTAIN               { proxyHost }
  LDAP-NAME                 {"proxyAccount"}
  LDAP-DESC                 "Account for accessing the proxy server"
  ID                        id-oc-proxyAccount }

-- MAY fax: LDAP name "fax" was taken as facsimileTelephoneNumber. schema2ldif/core.schema lists it on 2.5.4.23, which is already facsimileTelephoneNumber in SelectedAttributeTypes.
customer OBJECT-CLASS ::= {
  SUBCLASS OF               { top }
  MUST CONTAIN              { commonName }
  MAY CONTAIN               { custID
                              | postalAddress
                              | telephoneNumber
                              | facsimileTelephoneNumber
                              | streetAddress
                              | postalCode
                              | description
                              | mail }
  LDAP-NAME                 {"customer"}
  LDAP-DESC                 "Customer information (container class)"
  ID                        id-oc-customer }

genericAccount OBJECT-CLASS ::= {
  SUBCLASS OF               { top }
  KIND                      auxiliary
  MUST CONTAIN              { uid
                              | userPassword }
  LDAP-NAME                 {"genericAccount"}
  LDAP-DESC                 "The most abstract form of an account"
  ID                        id-oc-genericAccount }

uucpAccount OBJECT-CLASS ::= {
  SUBCLASS OF               { top }
  KIND                      auxiliary
  MUST CONTAIN              { uid
                              | userPassword
                              | dc
                              | uucpHost }
  LDAP-NAME                 {"uucpAccount"}
  LDAP-DESC                 "All data that is needed for a UUCP link"
  ID                        id-oc-uucpAccount }

metaInfo OBJECT-CLASS ::= {
  SUBCLASS OF               { top }
  KIND                      auxiliary
  MAY CONTAIN               { note
                              | type
                              | status
                              | commonName
                              | description }
  LDAP-NAME                 {"metaInfo"}
  LDAP-DESC                 "Easy way to bind additional information to an entry without deploying a specific objectclass"
  ID                        id-oc-metaInfo }

accountable OBJECT-CLASS ::= {
  SUBCLASS OF               { top }
  KIND                      auxiliary
  MAY CONTAIN               { billPaid
                              | price
                              | currency
                              | payperiod
                              | payday
                              | dunningCounter
                              | productcode }
  LDAP-NAME                 {"accountable"}
  LDAP-DESC                 "Marks a resource (an entry) as being subject to payment"
  ID                        id-oc-accountable }
END
