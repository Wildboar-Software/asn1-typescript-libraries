-- Derived from data/ldap-schema/qmail.new.schema
-- This module is a container for LDAP schema. It has no module identifier.
-- X- extension fields from the LDAP schema are comments. USAGE userApplications and structural KIND are omitted because they are the defaults.
-- 28 elements were omitted because their OIDs are already defined. See CONVERSION-REPORT.txt.
-- LDAP {length} bounds on directory strings are DirectoryString{n}. Bounds on IA5String, PrintableString, NumericString, and OCTET STRING are SIZE (1..n). Other bounds stay comments because the LDAP figure is an encoded-length hint.
LdapQmailNew DEFINITIONS ::=
BEGIN

IMPORTS

  ATTRIBUTE, DistinguishedName, distinguishedNameMatch, OBJECT-CLASS, top
    FROM InformationFramework
      {joint-iso-itu-t ds(5) module(1) informationFramework(1) 9} WITH SUCCESSORS

  caseIgnoreIA5Match, caseIgnoreIA5SubstringsMatch, dn, ia5String, integer,
    integerMatch, numericString, numericStringMatch
    FROM SelectedAttributeTypes
      {joint-iso-itu-t ds(5) module(1) selectedAttributeTypes(5) 9} WITH SUCCESSORS ;

-- Object identifiers

id-at-qmailAccountPurge OBJECT IDENTIFIER ::= { 1 3 6 1 4 1 7914 1 2 1 14 }
id-at-qladnmanager OBJECT IDENTIFIER ::= { 1 3 6 1 4 1 7914 1 4 1 1 }
id-at-qlaDomainList OBJECT IDENTIFIER ::= { 1 3 6 1 4 1 7914 1 4 1 2 }
id-at-qlaUidPrefix OBJECT IDENTIFIER ::= { 1 3 6 1 4 1 7914 1 4 1 3 }
id-at-qlaQmailUid OBJECT IDENTIFIER ::= { 1 3 6 1 4 1 7914 1 4 1 4 }
id-at-qlaQmailGid OBJECT IDENTIFIER ::= { 1 3 6 1 4 1 7914 1 4 1 5 }
id-at-qlaMailMStorePrefix OBJECT IDENTIFIER ::= { 1 3 6 1 4 1 7914 1 4 1 6 }
id-at-qlaMailQuotaSize OBJECT IDENTIFIER ::= { 1 3 6 1 4 1 7914 1 4 1 7 }
id-at-qlaMailQuotaCount OBJECT IDENTIFIER ::= { 1 3 6 1 4 1 7914 1 4 1 8 }
id-at-qlaMailSizeMax OBJECT IDENTIFIER ::= { 1 3 6 1 4 1 7914 1 4 1 9 }
id-at-qlaMailHostList OBJECT IDENTIFIER ::= { 1 3 6 1 4 1 7914 1 4 1 10 }
id-oc-qldapAdmin OBJECT IDENTIFIER ::= { 1 3 6 1 4 1 7914 1 4 2 1 }

-- Attribute types

qmailAccountPurge ATTRIBUTE ::= {
  WITH SYNTAX               NumericString
  EQUALITY MATCHING RULE    numericStringMatch
  SINGLE VALUE              TRUE
  LDAP-SYNTAX               numericString.&id
  LDAP-NAME                 {"qmailAccountPurge"}
  LDAP-DESC                 "The earliest date when a mailMessageStore will be purged"
  ID                        id-at-qmailAccountPurge }

qladnmanager ATTRIBUTE ::= {
  WITH SYNTAX               DistinguishedName
  EQUALITY MATCHING RULE    distinguishedNameMatch
  LDAP-SYNTAX               dn.&id
  LDAP-NAME                 {"qladnmanager"}
  ID                        id-at-qladnmanager }

qlaDomainList ATTRIBUTE ::= {
  WITH SYNTAX               IA5String(SIZE (1..256))
  EQUALITY MATCHING RULE    caseIgnoreIA5Match
  SUBSTRINGS MATCHING RULE  caseIgnoreIA5SubstringsMatch
  LDAP-SYNTAX               ia5String.&id
  LDAP-NAME                 {"qlaDomainList"}
  ID                        id-at-qlaDomainList }

qlaUidPrefix ATTRIBUTE ::= {
  WITH SYNTAX               IA5String(SIZE (1..256))
  EQUALITY MATCHING RULE    caseIgnoreIA5Match
  SUBSTRINGS MATCHING RULE  caseIgnoreIA5SubstringsMatch
  SINGLE VALUE              TRUE
  LDAP-SYNTAX               ia5String.&id
  LDAP-NAME                 {"qlaUidPrefix"}
  ID                        id-at-qlaUidPrefix }

qlaQmailUid ATTRIBUTE ::= {
  WITH SYNTAX               INTEGER
  EQUALITY MATCHING RULE    integerMatch
  SINGLE VALUE              TRUE
  LDAP-SYNTAX               integer.&id
  LDAP-NAME                 {"qlaQmailUid"}
  ID                        id-at-qlaQmailUid }

qlaQmailGid ATTRIBUTE ::= {
  WITH SYNTAX               INTEGER
  EQUALITY MATCHING RULE    integerMatch
  SINGLE VALUE              TRUE
  LDAP-SYNTAX               integer.&id
  LDAP-NAME                 {"qlaQmailGid"}
  ID                        id-at-qlaQmailGid }

qlaMailMStorePrefix ATTRIBUTE ::= {
  WITH SYNTAX               IA5String(SIZE (1..256))
  EQUALITY MATCHING RULE    caseIgnoreIA5Match
  SUBSTRINGS MATCHING RULE  caseIgnoreIA5SubstringsMatch
  SINGLE VALUE              TRUE
  LDAP-SYNTAX               ia5String.&id
  LDAP-NAME                 {"qlaMailMStorePrefix"}
  ID                        id-at-qlaMailMStorePrefix }

qlaMailQuotaSize ATTRIBUTE ::= {
  WITH SYNTAX               INTEGER
  EQUALITY MATCHING RULE    integerMatch
  SINGLE VALUE              TRUE
  LDAP-SYNTAX               integer.&id
  LDAP-NAME                 {"qlaMailQuotaSize"}
  ID                        id-at-qlaMailQuotaSize }

qlaMailQuotaCount ATTRIBUTE ::= {
  WITH SYNTAX               INTEGER
  EQUALITY MATCHING RULE    integerMatch
  SINGLE VALUE              TRUE
  LDAP-SYNTAX               integer.&id
  LDAP-NAME                 {"qlaMailQuotaCount"}
  ID                        id-at-qlaMailQuotaCount }

qlaMailSizeMax ATTRIBUTE ::= {
  WITH SYNTAX               INTEGER
  EQUALITY MATCHING RULE    integerMatch
  SINGLE VALUE              TRUE
  LDAP-SYNTAX               integer.&id
  LDAP-NAME                 {"qlaMailSizeMax"}
  ID                        id-at-qlaMailSizeMax }

qlaMailHostList ATTRIBUTE ::= {
  WITH SYNTAX               IA5String(SIZE (1..256))
  EQUALITY MATCHING RULE    caseIgnoreIA5Match
  SUBSTRINGS MATCHING RULE  caseIgnoreIA5SubstringsMatch
  LDAP-SYNTAX               ia5String.&id
  LDAP-NAME                 {"qlaMailHostList"}
  ID                        id-at-qlaMailHostList }

-- Object classes

qldapAdmin OBJECT-CLASS ::= {
  SUBCLASS OF               { top }
  KIND                      auxiliary
  MUST CONTAIN              { qladnmanager
                              | qlaDomainList
                              | qlaMailMStorePrefix
                              | qlaMailHostList }
  MAY CONTAIN               { qlaUidPrefix
                              | qlaQmailUid
                              | qlaQmailGid
                              | qlaMailQuotaSize
                              | qlaMailQuotaCount
                              | qlaMailSizeMax }
  LDAP-NAME                 {"qldapAdmin"}
  LDAP-DESC                 "QMail-LDAP Subtree Admin"
  ID                        id-oc-qldapAdmin }
END
