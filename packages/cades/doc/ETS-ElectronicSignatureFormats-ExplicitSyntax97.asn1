-- Sourced from https://www.etsi.org/deliver/etsi_ts/101700_101799/101733/02.02.01_60/ts_101733v020201p.pdf
-- ETSI TS 101 733 V2.2.1 (2013-04)

ETS-ElectronicSignatureFormats-ExplicitSyntax97
    { iso(1) member-body(2) us(840) rsadsi(113549) pkcs(1) pkcs-9(9) smime(16)
    id-mod(0) eSignature-explicit97(29) }
DEFINITIONS EXPLICIT TAGS ::=
BEGIN

    -- EXPORTS All

IMPORTS
    -- Cryptographic Message Syntax (CMS): RFC 3852
    ContentInfo, ContentType, id-data, id-signedData, SignedData,
    EncapsulatedContentInfo, SignerInfo,
    id-contentType, id-messageDigest, MessageDigest, id-signingTime, SigningTime,
    id-countersignature, Countersignature
        FROM CryptographicMessageSyntax2004
        { iso(1) member-body(2) us(840) rsadsi(113549) pkcs(1) pkcs-9(9)
        smime(16) modules(0) cms-2004(24) }

    -- ESS Defined attributes: ESS Update
    -- RFC 5035 (Adding CertID Algorithm Agility)
    id-aa-signingCertificate, SigningCertificate, IssuerSerial,
    id-aa-contentReference, ContentReference, id-aa-contentIdentifier,
    ContentIdentifier, id-aa-signingCertificateV2
        FROM ExtendedSecurityServices-2006
        { iso(1) member-body(2) us(840) rsadsi(113549) pkcs(1) pkcs-9(9)
        smime(16) modules(0) id-mod-ess-2006(30) }

    -- Internet X.509 Public Key Infrastructure - Certificate and CRL Profile: RFC 3280
    Certificate, AlgorithmIdentifier, CertificateList, Name,
    Attribute
        FROM PKIX1Explicit88
        { iso(1) identified-organization(3) dod(6) internet(1)
        security(5) mechanisms(5) pkix(7) id-mod(0) id-pkix1-explicit(18) }

    GeneralNames, GeneralName, PolicyInformation
        FROM PKIX1Implicit88
        { iso(1) identified-organization(3) dod(6) internet(1) security(5)
        mechanisms(5) pkix(7) id-mod(0) id-pkix1-implicit(19) }

    -- Internet Attribute Certificate Profile for Authorization: RFC 3281
    AttributeCertificate
        FROM PKIXAttributeCertificate
        { iso(1) identified-organization(3) dod(6) internet(1)
        security(5) mechanisms(5) pkix(7) id-mod(0) id-mod-attribute-cert(12) }

    -- OCSP RFC 2560
    BasicOCSPResponse, ResponderID
        FROM OCSP { iso(1) identified-organization(3) dod(6) internet(1)
        security(5) mechanisms(5) pkix(7) id-mod(0) id-mod-ocsp(14) }

    -- RFC 3161 Internet X.509 Public Key Infrastructure
    -- Time-Stamp Protocol
    TimeStampToken
        FROM PKIXTSP { iso(1) identified-organization(3) dod(6) internet(1)
        security(5) mechanisms(5) pkix(7) id-mod(0) id-mod-tsp(13) }

    -- Evidence Record Syntax RFC 4998
    EvidenceRecord
        FROM ERS
        { iso(1) identified-organization(3) dod(6) internet(1) security(5)
        mechanisms(5) ltans(11) id-mod(0) id-mod-ers88(2) id-mod-ers88-v1(1) }

    -- X.520
    DirectoryString {}
        FROM SelectedAttributeTypes
        { joint-iso-itu-t ds(5) module(1) selectedAttributeTypes(5) 4 }
    ;
-- Definitions of Object Identifier arcs used in the present document
-- ==================================================================
-- OID used referencing electronic signature mechanisms based on the present document
-- for use with the IDUP API (see Annex D)
id-etsi-es-IDUP-Mechanism-v1 OBJECT IDENTIFIER ::= {
    itu-t(0)
    identified-organization(4)
    etsi(0)
    electronic-signature-standard (1733)
    part1 (1)
    idupMechanism (4)
    etsiESv1(1) }

id-etsi-es-attributes OBJECT IDENTIFIER ::= {
    itu-t(0)
    identified-organization(4)
    etsi(0)
    electronic-signature-standard (1733)
    attributes(2) }

-- Basic ES Attributes Defined in the present document
-- ===================================================
-- CMS Attributes defined in the present document
-- OtherSigningCertificate - deprecated
id-aa-ets-otherSigCert OBJECT IDENTIFIER ::= {
    iso(1)
    member-body(2)
    us(840)
    rsadsi(113549)
    pkcs(1)
    pkcs9(9)
    smime(16)
    id-aa(2)
    19 }

OtherSigningCertificate ::= SEQUENCE {
    certs       SEQUENCE OF OtherCertID,
    policies    SEQUENCE OF PolicyInformation OPTIONAL
    -- NOT USED IN THE PRESENT DOCUMENT
    }

OtherCertID ::= SEQUENCE {
    otherCertHash   OtherHash,
    issuerSerial    IssuerSerial OPTIONAL }

OtherHash ::= CHOICE {
    sha1Hash    OtherHashValue, -- This contains a SHA-1 hash
    otherHash   OtherHashAlgAndValue }

-- Policy ES Attributes Defined in the present document
-- ====================================================
-- Mandatory Basic Electronic Signature Attributes, plus in addition.
-- Signature Policy Identifier
id-aa-ets-sigPolicyId OBJECT IDENTIFIER ::= {
    iso(1)
    member-body(2)
    us(840)
    rsadsi(113549)
    pkcs(1)
    pkcs9(9)
    smime(16)
    id-aa(2)
    15 }

SignaturePolicyIdentifier ::= CHOICE {
    signaturePolicyId           SignaturePolicyId,
    signaturePolicyImplied      SignaturePolicyImplied
    -- not used in this version
    }

SignaturePolicyId ::= SEQUENCE {
    sigPolicyId             SigPolicyId,
    sigPolicyHash           SigPolicyHash,
    sigPolicyQualifiers     SEQUENCE SIZE (1..MAX) OF SigPolicyQualifierInfo OPTIONAL }

SignaturePolicyImplied ::= NULL

SigPolicyId ::= OBJECT IDENTIFIER

SigPolicyHash ::= OtherHashAlgAndValue

OtherHashAlgAndValue ::= SEQUENCE {
    hashAlgorithm       AlgorithmIdentifier,
    hashValue           OtherHashValue }

OtherHashValue ::= OCTET STRING

SigPolicyQualifierInfo ::= SEQUENCE {
    sigPolicyQualifierId    SIG-POLICY-QUALIFIER.&id({SupportedSigPolicyQualifiers}),
    qualifier               SIG-POLICY-QUALIFIER.&Qualifier
        ({SupportedSigPolicyQualifiers}{@sigPolicyQualifierId}) OPTIONAL }

SupportedSigPolicyQualifiers SIG-POLICY-QUALIFIER ::= {
    noticeToUser
    | pointerToSigPolSpec }

SIG-POLICY-QUALIFIER ::= CLASS {
    &id OBJECT IDENTIFIER UNIQUE,
    &Qualifier OPTIONAL }
WITH SYNTAX {
    SIG-POLICY-QUALIFIER-ID &id
    [SIG-QUALIFIER-TYPE &Qualifier] }

noticeToUser SIG-POLICY-QUALIFIER ::= {
    SIG-POLICY-QUALIFIER-ID     id-spq-ets-unotice
    SIG-QUALIFIER-TYPE          SPUserNotice }

pointerToSigPolSpec SIG-POLICY-QUALIFIER ::= {
    SIG-POLICY-QUALIFIER-ID     id-spq-ets-uri
    SIG-QUALIFIER-TYPE          SPuri }

id-spq-ets-uri OBJECT IDENTIFIER ::= {
    iso(1)
    member-body(2)
    us(840)
    rsadsi(113549)
    pkcs(1)
    pkcs9(9)
    smime(16)
    id-spq(5)
    1 }

SPuri ::= IA5String

id-spq-ets-unotice OBJECT IDENTIFIER ::= {
    iso(1)
    member-body(2)
    us(840)
    rsadsi(113549)
    pkcs(1)
    pkcs9(9)
    smime(16)
    id-spq(5)
    2 }

SPUserNotice ::= SEQUENCE {
    noticeRef       NoticeReference OPTIONAL,
    explicitText    DisplayText OPTIONAL }

NoticeReference ::= SEQUENCE {
    organization    DisplayText,
    noticeNumbers   SEQUENCE OF INTEGER }

DisplayText ::= CHOICE {
    visibleString       VisibleString (SIZE (1..200)),
    bmpString           BMPString (SIZE (1..200)),
    utf8String          UTF8String (SIZE (1..200)) }

-- Optional Electronic Signature Attributes
-- Commitment Type
id-aa-ets-commitmentType OBJECT IDENTIFIER ::= {
    iso(1)
    member-body(2)
    us(840)
    rsadsi(113549)
    pkcs(1)
    pkcs-9(9)
    smime(16)
    id-aa(2)
    16 }

CommitmentTypeIndication ::= SEQUENCE {
    commitmentTypeId            CommitmentTypeIdentifier,
    commitmentTypeQualifier     SEQUENCE SIZE (1..MAX) OF CommitmentTypeQualifier OPTIONAL }

CommitmentTypeIdentifier ::= OBJECT IDENTIFIER

CommitmentTypeQualifier ::= SEQUENCE {
    commitmentQualifierId       COMMITMENT-QUALIFIER.&id,
    qualifier                   COMMITMENT-QUALIFIER.&Qualifier OPTIONAL }

COMMITMENT-QUALIFIER ::= CLASS {
    &id OBJECT IDENTIFIER UNIQUE,
    &Qualifier OPTIONAL }
WITH SYNTAX {
    COMMITMENT-QUALIFIER-ID &id
    [COMMITMENT-TYPE &Qualifier] }

id-cti-ets-proofOfOrigin    OBJECT IDENTIFIER ::= {
    iso(1) member-body(2) us(840) rsadsi(113549) pkcs(1) pkcs-9(9) smime(16) cti(6) 1}
id-cti-ets-proofOfReceipt   OBJECT IDENTIFIER ::= {
    iso(1) member-body(2) us(840) rsadsi(113549) pkcs(1) pkcs-9(9) smime(16) cti(6) 2}
id-cti-ets-proofOfDelivery  OBJECT IDENTIFIER ::= {
    iso(1) member-body(2) us(840) rsadsi(113549) pkcs(1) pkcs-9(9) smime(16) cti(6) 3}
id-cti-ets-proofOfSender    OBJECT IDENTIFIER ::= {
    iso(1) member-body(2) us(840) rsadsi(113549) pkcs(1) pkcs-9(9) smime(16) cti(6) 4}
id-cti-ets-proofOfApproval  OBJECT IDENTIFIER ::= {
    iso(1) member-body(2) us(840) rsadsi(113549) pkcs(1) pkcs-9(9) smime(16) cti(6) 5}
id-cti-ets-proofOfCreation  OBJECT IDENTIFIER ::= {
    iso(1) member-body(2) us(840) rsadsi(113549) pkcs(1) pkcs-9(9) smime(16) cti(6) 6}


-- Signer Location
id-aa-ets-signerLocation OBJECT IDENTIFIER ::= {
    iso(1)
    member-body(2)
    us(840)
    rsadsi(113549)
    pkcs(1)
    pkcs-9(9)
    smime(16)
    id-aa(2)
    17 }

SignerLocation ::= SEQUENCE {
    -- at least one of the following shall be present
    countryName [0] DirectoryString OPTIONAL,
    -- As used to name a Country in X.500
    localityName [1] DirectoryString OPTIONAL,
    -- As used to name a locality in X.500
    postalAdddress [2] PostalAddress OPTIONAL }

PostalAddress ::= SEQUENCE SIZE(1..6) OF DirectoryString{maxSize}

-- maxSize parametrization as specified in X.683
-- Signer Attributes
id-aa-ets-signerAttr OBJECT IDENTIFIER ::= {
    iso(1)
    member-body(2)
    us(840)
    rsadsi(113549)
    pkcs(1)
    pkcs-9(9)
    smime(16)
    id-aa(2)
    18 }

SignerAttribute ::= SEQUENCE OF CHOICE {
    claimedAttributes       [0] ClaimedAttributes,
    certifiedAttributes     [1] CertifiedAttributes }

ClaimedAttributes ::= SEQUENCE OF Attribute

CertifiedAttributes ::= AttributeCertificate -- as defined in RFC 3281: see clause 4.1.

-- Content Timestamp
id-aa-ets-contentTimestamp OBJECT IDENTIFIER ::= {
    iso(1)
    member-body(2)
    us(840)
    rsadsi(113549)
    pkcs(1)
    pkcs-9(9)
    smime(16)
    id-aa(2)
    20 }

ContentTimestamp::= TimeStampToken

-- Mime type
id-aa-ets-mimeType OBJECT IDENTIFIER ::= {
    itu-t(0)
    identified-organization(4)
    etsi(0)
    electronic-signature-standard(1733)
    attributes(2)
    1 }

MimeType ::= UTF8String

-- Signature Timestamp
id-aa-signatureTimeStampToken OBJECT IDENTIFIER ::= {
    iso(1)
    member-body(2)
    us(840)
    rsadsi(113549)
    pkcs(1)
    pkcs-9(9)
    smime(16)
    id-aa(2)
    14 }

SignatureTimeStampToken ::= TimeStampToken

-- Complete Certificate Refs.
id-aa-ets-certificateRefs OBJECT IDENTIFIER ::= {
    iso(1)
    member-body(2)
    us(840)
    rsadsi(113549)
    pkcs(1)
    pkcs-9(9)
    smime(16)
    id-aa(2)
    21 }

CompleteCertificateRefs ::= SEQUENCE OF OtherCertID

-- Complete Revocation Refs
id-aa-ets-revocationRefs OBJECT IDENTIFIER ::= {
    iso(1)
    member-body(2)
    us(840)
    rsadsi(113549)
    pkcs(1)
    pkcs-9(9)
    smime(16)
    id-aa(2)
    22 }

CompleteRevocationRefs ::= SEQUENCE OF CrlOcspRef

CrlOcspRef ::= SEQUENCE {
    crlids      [0] CRLListID OPTIONAL,
    ocspids     [1] OcspListID OPTIONAL,
    otherRev    [2] OtherRevRefs OPTIONAL }

CRLListID ::= SEQUENCE {
    crls        SEQUENCE OF CrlValidatedID }

CrlValidatedID ::= SEQUENCE {
    crlHash         OtherHash,
    crlIdentifier   CrlIdentifier OPTIONAL }

CrlIdentifier ::= SEQUENCE {
    crlissuer       Name,
    crlIssuedTime   UTCTime,
    crlNumber       INTEGER OPTIONAL }

OcspListID ::= SEQUENCE {
    ocspResponses   SEQUENCE OF OcspResponsesID }

OcspResponsesID ::= SEQUENCE {
    ocspIdentifier      OcspIdentifier,
    ocspRepHash         OtherHash OPTIONAL }

OcspIdentifier ::= SEQUENCE {
    ocspResponderID     ResponderID, -- As in OCSP response data
    producedAt          GeneralizedTime -- As in OCSP response data
    }

OtherRevRefs ::= SEQUENCE {
    otherRevRefType     OTHER-REVOCATION-REF.&id,
    otherRevRefs        SEQUENCE OF OTHER-REVOCATION-REF.&Type }

OTHER-REVOCATION-REF ::= CLASS {
    &Type,
    &id OBJECT IDENTIFIER UNIQUE
} WITH SYNTAX {
    WITH SYNTAX &Type
    ID &id
}

-- Certificate Values
id-aa-ets-certValues OBJECT IDENTIFIER ::= {
    iso(1)
    member-body(2)
    us(840)
    rsadsi(113549)
    pkcs(1)
    pkcs-9(9)
    smime(16)
    id-aa(2)
    23 }

CertificateValues ::= SEQUENCE OF Certificate

-- Certificate Revocation Values
id-aa-ets-revocationValues OBJECT IDENTIFIER ::= {
    iso(1)
    member-body(2)
    us(840)
    rsadsi(113549)
    pkcs(1)
    pkcs-9(9)
    smime(16)
    id-aa(2)
    24 }

RevocationValues ::= SEQUENCE {
    crlVals         [0] SEQUENCE OF CertificateList OPTIONAL,
    ocspVals        [1] SEQUENCE OF BasicOCSPResponse OPTIONAL,
    otherRevVals    [2] OtherRevVals OPTIONAL}

OtherRevVals ::= SEQUENCE {
    otherRevValType     OTHER-REVOCATION-VAL.&id,
    otherRevVals        SEQUENCE OF OTHER-REVOCATION-REF.&Type }

OTHER-REVOCATION-VAL ::= CLASS {
    &Type,
    &id OBJECT IDENTIFIER UNIQUE
} WITH SYNTAX {
    WITH SYNTAX &Type
    ID &id
}

-- CAdES-C Timestamp
id-aa-ets-escTimeStamp OBJECT IDENTIFIER ::= {
    iso(1)
    member-body(2)
    us(840)
    rsadsi(113549)
    pkcs(1)
    pkcs-9(9)
    smime(16)
    id-aa(2)
    25 }

ESCTimeStampToken ::= TimeStampToken

-- Time-Stamped Certificates and CRLs
id-aa-ets-certCRLTimestamp OBJECT IDENTIFIER ::= {
    iso(1)
    member-body(2)
    us(840)
    rsadsi(113549)
    pkcs(1)
    pkcs-9(9)
    smime(16)
    id-aa(2)
    26 }

TimestampedCertsCRLs ::= TimeStampToken

-- Archive Timestamp
id-aa-ets-archiveTimestampV2 OBJECT IDENTIFIER ::= {
    iso(1)
    member-body(2)
    us(840)
    rsadsi(113549)
    pkcs(1)
    pkcs-9(9)
    smime(16)
    id-aa(2)
    48 }

ArchiveTimeStampToken ::= TimeStampToken

-- archive-time-stamp-v3 attribute
id-aa-ets-archiveTimestampV3 OBJECT IDENTIFIER ::= {
    itu-t(0)
    identified-organization(4)
    etsi(0)
    electronic-signature-standard(1733)
    attributes(2)
    4 }

-- ats-hash-index attribute
id-aa-ATSHashIndex OBJECT IDENTIFIER ::= {
    itu-t(0)
    identified-organization(4)
    etsi(0)
    electronic-signature-standard(1733)
    attributes(2)
    5 }

ATSHashIndex ::= SEQUENCE {
    hashIndAlgorithm        AlgorithmIdentifier DEFAULT {algorithm id-sha256},
    certificatesHashIndex   SEQUENCE OF OCTET STRING,
    crlsHashIndex           SEQUENCE OF OCTET STRING,
    unsignedAttrsHashIndex  SEQUENCE OF OCTET STRING }

-- Long-Term Validation attribute
id-aa-ets-longTermValidation OBJECT IDENTIFIER ::= {
    itu-t(0)
    identified-organization(4)
    etsi(0)
    electronic-signature-standard(1733)
    attributes(2)
    2 }

LongTermValidation ::= SEQUENCE {
    poeDate         GeneralizedTime,
    poeValue        CHOICE {
        timeStamp       [0] EXPLICIT TimeStampToken,
        evidenceRecord  [1] EXPLICIT EvidenceRecord
    } OPTIONAL,
    extraCertificates   [0] IMPLICIT CertificateSet OPTIONAL,
    extraRevocation     [1] IMPLICIT RevocationInfoChoices OPTIONAL }

-- Attribute certificate references
id-aa-ets-attrCertificateRefs OBJECT IDENTIFIER ::= {
    iso(1)
    member-body(2)
    us(840)
    rsadsi(113549)
    pkcs(1)
    pkcs-9(9)
    smime(16)
    id-aa(2)
    44 }

AttributeCertificateRefs ::= SEQUENCE OF OtherCertID

-- Attribute revocation references
id-aa-ets-attrRevocationRefs OBJECT IDENTIFIER ::= {
    iso(1)
    member-body(2)
    us(840)
    rsadsi(113549)
    pkcs(1)
    pkcs-9(9)
    smime(16)
    id-aa(2)
    45 }

AttributeRevocationRefs ::= SEQUENCE OF CrlOcspRef

END
