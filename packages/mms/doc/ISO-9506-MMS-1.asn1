ISO-9506-MMS-1
{iso standard 9506 part(2) mms-abstract-syntax-version1(1)}
DEFINITIONS ::=
BEGIN
EXPORTS AlternateAccess, AttachToEventCondition, AttachToSemaphore,
        ConfirmedServiceRequest, Data, EE-State, FileName, Identifier, Integer8,
        Integer32, MMSString, MMS255String, ObjectName, TimeOfDay, TypeSpecification,
        Unsigned32, Unsigned8, VariableSpecification;

IMPORTS

        ApplicationReference, Authentication-value
                FROM MMS-Environment-1
                {iso standard 9506 part(2) mms-environment-version1(4) }

        ObtainFile-Request, ObtainFile-Response, ObtainFile-Error,
        FileOpen-Request, FileOpen-Response, FileRead-Request, FileRead-Response,
        FileClose-Request, FileClose-Response, FileRename-Request, FileRename-Response,
        FileRename-Error, FileDelete-Request, FileDelete-Response,
        FileDirectory-Request, FileDirectory-Response, DefineScatteredAccess-Request,
        DefineScatteredAccess-Response, ScatteredAccessDescription,
        GetScatteredAccessAttributes-Request, GetScatteredAccessAttributes-Response
                FROM ISO-9506-MMS-1A
                {iso standard 9506 part(2) mms-annex-version1(3) }

        AccessCondition, AdditionalCBBOptions, AdditionalSupportOptions,
        Address, AlarmAckRule, Control-State, DomainState, EC-State, EC-Class,
        EE-Duration, EE-Class, EventTime, Journal-Variable, LogicalStatus, Modifier,
        normalPriority, normalSeverity, ParameterSupportOptions, PhysicalStatus,
        Priority, ProgramInvocationState, Running-Mode, ServiceSupportOptions, Severity,
        Transitions, TypeDescription, ULState, VMDState
                FROM MMS-Object-Module-1
                {iso standard 9506 part(1) mms-object-model-version1(2) }
        ;

/*
This is a deviation from ISO 9506.
*/
ProblematicThereforeAnyType ::= TYPE-IDENTIFIER.&Type

Nullable{T} ::= CHOICE {
       present T,
       absent NULL
}

-- This is a type contrived to handle situations where a field
-- can be conditionally encoded on zero content octets if NULL.
-- For example, handling this:
-- defineEcl                     [0] DefineEventConditionList-Error,
-- defineEcl                     [0] IMPLICIT NULL,
ImplicitNullable{T} ::= SEQUENCE {
        present T OPTIONAL
}

/*
MMSpdu ::= CHOICE {
    confirmed-RequestPDU       [0] IMPLICIT Confirmed-RequestPDU,
    confirmed-ResponsePDU      [1] IMPLICIT Confirmed-ResponsePDU,
    confirmed-ErrorPDU         [2] IMPLICIT Confirmed-ErrorPDU,
    unconfirmed-PDU            [3] IMPLICIT Unconfirmed-PDU,
    unconfirmed-PDU            [3] IMPLICIT NULL,
    rejectPDU                  [4] IMPLICIT RejectPDU,
    cancel-RequestPDU          [5] IMPLICIT Cancel-RequestPDU,
    cancel-ResponsePDU         [6] IMPLICIT Cancel-ResponsePDU,
    cancel-ErrorPDU            [7] IMPLICIT Cancel-ErrorPDU,
    cancel-RequestPDU          [5] IMPLICIT NULL,
    cancel-ResponsePDU         [6] IMPLICIT NULL,
    cancel-ErrorPDU            [7] IMPLICIT NULL,
    initiate-RequestPDU        [8] IMPLICIT Initiate-RequestPDU,
    initiate-ResponsePDU       [9] IMPLICIT Initiate-ResponsePDU,
    initiate-ErrorPDU          [10] IMPLICIT Initiate-ErrorPDU,
    conclude-RequestPDU        [11] IMPLICIT Conclude-RequestPDU,
    conclude-ResponsePDU       [12] IMPLICIT Conclude-ResponsePDU,
    conclude-ErrorPDU          [13] IMPLICIT Conclude-ErrorPDU
}
*/

MMSpdu ::= CHOICE {
    confirmed-RequestPDU       [0] IMPLICIT Confirmed-RequestPDU,
    confirmed-ResponsePDU      [1] IMPLICIT Confirmed-ResponsePDU,
    confirmed-ErrorPDU         [2] IMPLICIT Confirmed-ErrorPDU,
    -- unconfirmed-PDU            [3] IMPLICIT Unconfirmed-PDU,
    -- unconfirmed-PDU            [3] IMPLICIT NULL,
    rejectPDU                  [4] IMPLICIT RejectPDU,
    -- cancel-RequestPDU          [5] IMPLICIT Cancel-RequestPDU,
    -- cancel-ResponsePDU         [6] IMPLICIT Cancel-ResponsePDU,
    -- cancel-ErrorPDU            [7] IMPLICIT Cancel-ErrorPDU,
    -- cancel-RequestPDU          [5] IMPLICIT NULL,
    -- cancel-ResponsePDU         [6] IMPLICIT NULL,
    -- cancel-ErrorPDU            [7] IMPLICIT NULL,
    initiate-RequestPDU        [8] IMPLICIT Initiate-RequestPDU,
    initiate-ResponsePDU       [9] IMPLICIT Initiate-ResponsePDU,
    initiate-ErrorPDU          [10] IMPLICIT Initiate-ErrorPDU,
    conclude-RequestPDU        [11] IMPLICIT Conclude-RequestPDU,
    conclude-ResponsePDU       [12] IMPLICIT Conclude-ResponsePDU,
    conclude-ErrorPDU          [13] IMPLICIT Conclude-ErrorPDU,
    ...
}

Confirmed-RequestPDU ::= SEQUENCE {
    invokeID                      Unsigned32,
    listOfModifiers               SEQUENCE OF Modifier OPTIONAL,
    service                       ConfirmedServiceRequest,
    ...,
    service-ext                   [79] Request-Detail OPTIONAL
    -- shall not be transmitted if value is the value
    -- of a tagged type derived from NULL
}

/*
ConfirmedServiceRequest ::= CHOICE {
    status   [0] IMPLICIT Status-Request,
    status   [0] IMPLICIT NULL,
    getNameList [1] IMPLICIT GetNameList-Request,
    getNameList [1] IMPLICIT NULL,
    identify    [2] IMPLICIT Identify-Request,
    identify    [2] IMPLICIT NULL,
    rename  [3] IMPLICIT Rename-Request,
    rename  [3] IMPLICIT NULL,
    read    [4] IMPLICIT Read-Request,
    read    [4] IMPLICIT NULL,
    write   [5] IMPLICIT Write-Request,
    write   [5] IMPLICIT NULL,
    getVariableAccessAttributes [6] GetVariableAccessAttributes-Request,
    getVariableAccessAttributes [6] IMPLICIT NULL,
    defineNamedVariable [7] IMPLICIT DefineNamedVariable-Request,
    defineNamedVariable [7] IMPLICIT NULL,
    -- [8] is reserved for a service defined in Annex E
    defineScatteredAccess   [8] IMPLICIT DefineScatteredAccess-Request,
    defineScatteredAccess   [8] IMPLICIT NULL,
    -- [9] is reserved for a service defined in Annex E
    getScatteredAccessAttributes    [9] GetScatteredAccessAttributes-Request,
    getScatteredAccessAttributes    [9] IMPLICIT NULL,
    deleteVariableAccess    [10] IMPLICIT DeleteVariableAccess-Request,
    deleteVariableAccess    [10] IMPLICIT NULL,
    defineNamedVariableList [11] IMPLICIT DefineNamedVariableList-Request,
    defineNamedVariableList [11] IMPLICIT NULL,
    getNamedVariableListAttributes  [12] GetNamedVariableListAttributes-Request,
    getNamedVariableListAttributes  [12] IMPLICIT NULL,
    deleteNamedVariableList [13] IMPLICIT DeleteNamedVariableList-Request,
    deleteNamedVariableList [13] IMPLICIT NULL,
    defineNamedType [14] IMPLICIT DefineNamedType-Request,
    defineNamedType [14] IMPLICIT NULL,
    getNamedTypeAttributes  [15] GetNamedTypeAttributes-Request,
    getNamedTypeAttributes  [15] IMPLICIT NULL,
    deleteNamedType [16] IMPLICIT DeleteNamedType-Request,
    deleteNamedType [16] IMPLICIT NULL,
    input   [17] IMPLICIT Input-Request,
    input   [17] IMPLICIT NULL,
    output  [18] IMPLICIT Output-Request,
    output  [18] IMPLICIT NULL,
    takeControl [19] IMPLICIT TakeControl-Request,
    takeControl [19] IMPLICIT NULL,
    relinquishControl   [20] IMPLICIT RelinquishControl-Request,
    relinquishControl   [20] IMPLICIT NULL,
    defineSemaphore     [21] IMPLICIT DefineSemaphore-Request,
    defineSemaphore     [21] IMPLICIT NULL,
    deleteSemaphore     [22] DeleteSemaphore-Request,
    deleteSemaphore     [22] IMPLICIT NULL,
    reportSemaphoreStatus   [23] ReportSemaphoreStatus-Request,
    reportSemaphoreStatus   [23] IMPLICIT NULL,
    reportPoolSemaphoreStatus   [24] IMPLICIT ReportPoolSemaphoreStatus-Request,
    reportPoolSemaphoreStatus   [24] IMPLICIT NULL,
    reportSemaphoreEntryStatus  [25] IMPLICIT ReportSemaphoreEntryStatus-Request,
    reportSemaphoreEntryStatus  [25] IMPLICIT NULL,
    initiateDownloadSequence    [26] IMPLICIT InitiateDownloadSequence-Request,
    initiateDownloadSequence    [26] IMPLICIT NULL,
    downloadSegment     [27] IMPLICIT DownloadSegment-Request,
    downloadSegment     [27] IMPLICIT NULL,
    terminateDownloadSequence   [28] IMPLICIT TerminateDownloadSequence-Request,
    terminateDownloadSequence   [28] IMPLICIT NULL,
    initiateUploadSequence  [29] IMPLICIT InitiateUploadSequence-Request,
    initiateUploadSequence  [29] IMPLICIT NULL,
    uploadSegment   [30] IMPLICIT UploadSegment-Request,
    uploadSegment   [30] IMPLICIT NULL,
    terminateUploadSequence [31] IMPLICIT TerminateUploadSequence-Request,
    terminateUploadSequence [31] IMPLICIT NULL,
    requestDomainDownload   [32] IMPLICIT RequestDomainDownload-Request,
    requestDomainDownload   [32] IMPLICIT NULL,
    requestDomainUpload [33] IMPLICIT RequestDomainUpload-Request,
    requestDomainUpload [33] IMPLICIT NULL,
    loadDomainContent   [34] IMPLICIT LoadDomainContent-Request,
    loadDomainContent   [34] IMPLICIT NULL,
    storeDomainContent  [35] IMPLICIT StoreDomainContent-Request,
    storeDomainContent  [35] IMPLICIT NULL,
    deleteDomain    [36] IMPLICIT DeleteDomain-Request,
    deleteDomain    [36] IMPLICIT NULL,
    getDomainAttributes [37] IMPLICIT GetDomainAttributes-Request,
    getDomainAttributes [37] IMPLICIT NULL,
    createProgramInvocation [38] IMPLICIT CreateProgramInvocation-Request,
    createProgramInvocation [38] IMPLICIT NULL,
    deleteProgramInvocation [39] IMPLICIT DeleteProgramInvocation-Request,
    deleteProgramInvocation [39] IMPLICIT NULL,
    start   [40] IMPLICIT Start-Request,
    start   [40] IMPLICIT NULL,
    stop    [41] IMPLICIT Stop-Request,
    stop    [41] IMPLICIT NULL,
    resume  [42] IMPLICIT Resume-Request,
    resume  [42] IMPLICIT NULL,
    reset   [43] IMPLICIT Reset-Request,
    reset   [43] IMPLICIT NULL,
    kill    [44] IMPLICIT Kill-Request,
    kill    [44] IMPLICIT NULL,
    getProgramInvocationAttributes  [45] IMPLICIT GetProgramInvocationAttributes-Request,
    getProgramInvocationAttributes  [45] IMPLICIT NULL,
    obtainFile  [46] IMPLICIT ObtainFile-Request,
    obtainFile  [46] IMPLICIT NULL,
    defineEventCondition    [47] IMPLICIT DefineEventCondition-Request,
    defineEventCondition    [47] IMPLICIT NULL,
    deleteEventCondition    [48] DeleteEventCondition-Request,
    deleteEventCondition    [48] IMPLICIT NULL,
    getEventConditionAttributes [49] GetEventConditionAttributes-Request,
    getEventConditionAttributes [49] IMPLICIT NULL,
    reportEventConditionStatus  [50] ReportEventConditionStatus-Request,
    reportEventConditionStatus  [50] IMPLICIT NULL,
    alterEventConditionMonitoring   [51] IMPLICIT AlterEventConditionMonitoring-Request,
    alterEventConditionMonitoring   [51] IMPLICIT NULL,
    triggerEvent    [52] IMPLICIT TriggerEvent-Request,
    triggerEvent    [52] IMPLICIT NULL,
    defineEventAction   [53] IMPLICIT DefineEventAction-Request,
    defineEventAction   [53] IMPLICIT NULL,
    deleteEventAction   [54] DeleteEventAction-Request,
    deleteEventAction   [54] IMPLICIT NULL,
    getEventActionAttributes    [55] GetEventActionAttributes-Request,
    getEventActionAttributes    [55] IMPLICIT NULL,
    reportEventActionStatus     [56] ReportEventActionStatus-Request,
    reportEventActionStatus     [56] IMPLICIT NULL,
    defineEventEnrollment   [57] IMPLICIT DefineEventEnrollment-Request,
    defineEventEnrollment   [57] IMPLICIT NULL,
    deleteEventEnrollment   [58] DeleteEventEnrollment-Request,
    deleteEventEnrollment   [58] IMPLICIT NULL,
    alterEventEnrollment    [59] IMPLICIT AlterEventEnrollment-Request,
    alterEventEnrollment    [59] IMPLICIT NULL,
    reportEventEnrollmentStatus [60] ReportEventEnrollmentStatus-Request,
    reportEventEnrollmentStatus [60] IMPLICIT NULL,
    getEventEnrollmentAttributes    [61] IMPLICIT GetEventEnrollmentAttributes-Request,
    getEventEnrollmentAttributes    [61] IMPLICIT NULL,
    acknowledgeEventNotification    [62] IMPLICIT AcknowledgeEventNotification-Request,
    acknowledgeEventNotification    [62] IMPLICIT NULL,
    getAlarmSummary [63] IMPLICIT GetAlarmSummary-Request,
    getAlarmSummary [63] IMPLICIT NULL,
    getAlarmEnrollmentSummary   [64] IMPLICIT GetAlarmEnrollmentSummary-Request,
    getAlarmEnrollmentSummary   [64] IMPLICIT NULL,
    readJournal [65] IMPLICIT ReadJournal-Request,
    readJournal [65] IMPLICIT NULL,
    writeJournal    [66] IMPLICIT WriteJournal-Request,
    writeJournal    [66] IMPLICIT NULL,
    initializeJournal   [67] IMPLICIT InitializeJournal-Request,
    initializeJournal   [67] IMPLICIT NULL,
    reportJournalStatus [68] ReportJournalStatus-Request,
    reportJournalStatus [68] IMPLICIT NULL,
    createJournal   [69] IMPLICIT CreateJournal-Request,
    createJournal   [69] IMPLICIT NULL,
    deleteJournal   [70] IMPLICIT DeleteJournal-Request,
    deleteJournal   [70] IMPLICIT NULL,
    getCapabilityList   [71] IMPLICIT GetCapabilityList-Request,
    getCapabilityList   [71] IMPLICIT NULL,
    -- choices [72] through [77] are reserved for use by services
    -- defined in annex D
    fileOpen    [72] IMPLICIT FileOpen-Request,
    fileOpen    [72] IMPLICIT NULL,
    fileRead    [73] IMPLICIT FileRead-Request,
    fileRead    [73] IMPLICIT NULL,
    fileClose   [74] IMPLICIT FileClose-Request,
    fileClose   [74] IMPLICIT NULL,
    fileRename  [75] IMPLICIT FileRename-Request,
    fileRename  [75] IMPLICIT NULL,
    fileDelete  [76] IMPLICIT FileDelete-Request,
    fileDelete  [76] IMPLICIT NULL,
    fileDirectory   [77] IMPLICIT FileDirectory-Request,
    fileDirectory   [77] IMPLICIT NULL,
    ...,
    additionalService   [78] AdditionalService-Request,
    -- choice [79] is reserved
    getDataExchangeAttributes   [80] GetDataExchangeAttributes-Request,
    -- Shall not appear in minor version 1
    exchangeData    [81] IMPLICIT ExchangeData-Request,
    -- Shall not appear in minor version 1
    defineAccessControlList [82] IMPLICIT DefineAccessControlList-Request,
    -- Shall not appear in minor version 1 or 2
    getAccessControlListAttributes  [83] GetAccessControlListAttributes-Request,
    -- Shall not appear in minor version 1 or 2
    reportAccessControlledObjects   [84] IMPLICIT ReportAccessControlledObjects-Request,
    -- Shall not appear in minor version 1 or 2
    deleteAccessControlList [85] IMPLICIT DeleteAccessControlList-Request,
    -- Shall not appear in minor version 1 or 2
    changeAccessControl [86] IMPLICIT ChangeAccessControl-Request,
    -- Shall not appear in minor version 1 or 2
    ...
}
*/
ConfirmedServiceRequest ::= CHOICE {
    additionalService   [78] AdditionalService-Request,
    -- choice [79] is reserved
    getDataExchangeAttributes   [80] GetDataExchangeAttributes-Request,
    -- Shall not appear in minor version 1
    exchangeData    [81] IMPLICIT ExchangeData-Request,
    -- Shall not appear in minor version 1
    defineAccessControlList [82] IMPLICIT DefineAccessControlList-Request,
    -- Shall not appear in minor version 1 or 2
    getAccessControlListAttributes  [83] GetAccessControlListAttributes-Request,
    -- Shall not appear in minor version 1 or 2
    reportAccessControlledObjects   [84] IMPLICIT ReportAccessControlledObjects-Request,
    -- Shall not appear in minor version 1 or 2
    deleteAccessControlList [85] IMPLICIT DeleteAccessControlList-Request,
    -- Shall not appear in minor version 1 or 2
    changeAccessControl [86] IMPLICIT ChangeAccessControl-Request,
    -- Shall not appear in minor version 1 or 2
    ...
}

/*
AdditionalService-Request ::= CHOICE {
    vMDStop [0] IMPLICIT VMDStop-Request,
    vMDStop [0] IMPLICIT NULL,
    vMDReset    [1] IMPLICIT VMDReset-Request,
    vMDReset    [1] IMPLICIT NULL,
    select  [2] IMPLICIT Select-Request,
    select  [2] IMPLICIT NULL,
    alterPI [3] IMPLICIT AlterProgramInvocationAttributes-Request,
    alterPI [3] IMPLICIT NULL,
    initiateUCLoad  [4] IMPLICIT InitiateUnitControlLoad-Request,
    initiateUCLoad  [4] IMPLICIT NULL,
    uCLoad  [5] IMPLICIT UnitControlLoadSegment-Request,
    uCLoad  [5] IMPLICIT NULL,
    uCUpload    [6] IMPLICIT UnitControlUpload-Request,
    uCUpload    [6] IMPLICIT NULL,
    startUC [7] IMPLICIT StartUnitControl-Request,
    startUC [7] IMPLICIT NULL,
    stopUC  [8] IMPLICIT StopUnitControl-Request,
    stopUC  [8] IMPLICIT NULL,
    createUC    [9] IMPLICIT CreateUnitControl-Request,
    createUC    [9] IMPLICIT NULL,
    addToUC [10] IMPLICIT AddToUnitControl-Request,
    addToUC [10] IMPLICIT NULL,
    removeFromUC    [11] IMPLICIT RemoveFromUnitControl-Request,
    removeFromUC    [11] IMPLICIT NULL,
    getUCAttributes [12] IMPLICIT GetUnitControlAttributes-Request,
    getUCAttributes [12] IMPLICIT NULL,
    loadUCFromFile  [13] IMPLICIT LoadUnitControlFromFile-Request,
    loadUCFromFile  [13] IMPLICIT NULL,
    storeUCToFile   [14] IMPLICIT StoreUnitControlToFile-Request,
    storeUCToFile   [14] IMPLICIT NULL,
    deleteUC    [15] IMPLICIT DeleteUnitControl-Request,
    deleteUC    [15] IMPLICIT NULL,
    defineECL   [16] DefineEventConditionList-Request,
    defineECL   [16] IMPLICIT NULL,
    deleteECL   [17] DeleteEventConditionList-Request,
    deleteECL   [17] IMPLICIT NULL,
    addECLReference [18] IMPLICIT AddEventConditionListReference-Request,
    addECLReference [18] IMPLICIT NULL,
    removeECLReference  [19] IMPLICIT RemoveEventConditionListReference-Request,
    removeECLReference  [19] IMPLICIT NULL,
    getECLAttributes    [20] GetEventConditionListAttributes-Request,
    getECLAttributes    [20] IMPLICIT NULL,
    reportECLStatus [21] IMPLICIT ReportEventConditionListStatus-Request,
    reportECLStatus [21] IMPLICIT NULL,
    alterECLMonitoring   [22] IMPLICIT AlterEventConditionListMonitoring-Request,
    alterECLMonitoring   [22] IMPLICIT NULL
}
*/

AdditionalService-Request ::= ProblematicThereforeAnyType

/*
Request-Detail ::= CHOICE {
    -- this choice shall be selected if the tag value of the
    -- ConfirmedServiceRequest does not match any of the tags below
    otherRequests                 NULL,
    createProgramInvocation [38] IMPLICIT CS-CreateProgramInvocation-Request,
    createProgramInvocation [38] IMPLICIT NULL,
    start   [40] IMPLICIT CS-Start-Request,
    start   [40] IMPLICIT NULL,
    resume  [42] IMPLICIT CS-Resume-Request,
    resume  [42] IMPLICIT NULL,
    defineEventCondition    [47] IMPLICIT CS-DefineEventCondition-Request,
    defineEventCondition    [47] IMPLICIT NULL,
    alterEventConditionMonitoring   [51] IMPLICIT CS-AlterEventConditionMonitoring-Request,
    alterEventConditionMonitoring   [51] IMPLICIT NULL,
    defineEventEnrollment   [57] IMPLICIT CS-DefineEventEnrollment-Request,
    defineEventEnrollment   [57] IMPLICIT NULL,
    alterEventEnrollment    [59] IMPLICIT CS-AlterEventEnrollment-Request,
    alterEventEnrollment    [59] IMPLICIT NULL
}
*/
Request-Detail ::= CHOICE {
    otherRequests NULL,
    ...
}

Unconfirmed-PDU ::= SEQUENCE {
    service          UnconfirmedService,
    ...,
    service-ext      [79] Unconfirmed-Detail OPTIONAL
    -- shall not be transmitted if value is the value
    -- of a tagged type derived from NULL
}

/*
UnconfirmedService ::= CHOICE {
    informationReport   [0] IMPLICIT InformationReport,
    informationReport   [0] IMPLICIT NULL,
    unsolicitedStatus   [1] IMPLICIT UnsolicitedStatus,
    unsolicitedStatus   [1] IMPLICIT NULL,
    eventNotification   [2] IMPLICIT EventNotification,
    eventNotification   [2] IMPLICIT NULL
}
*/
UnconfirmedService ::= ProblematicThereforeAnyType

Unconfirmed-Detail ::= CHOICE {
       -- this choice shall be selected if the tag value of the
       -- UnconfirmedService does not match any of the tags below
   otherRequests          NULL
,  eventNotification
       [2] IMPLICIT CS-EventNotification
   }

Confirmed-ResponsePDU ::= SEQUENCE {
   invokeID            Unsigned32,
   service             ConfirmedServiceResponse,
   ...,
   service-ext         [79] Response-Detail OPTIONAL
                    -- shall not be transmitted if value is the value
                    -- of a tagged type derived from NULL
   }

ConfirmedServiceResponse ::= CHOICE {
    /*
    status   [0] IMPLICIT Status-Response,
    status   [0] IMPLICIT RejectPDU,
    getNameList   [1] IMPLICIT GetNameList-Response,
    getNameList   [1] IMPLICIT RejectPDU,
    identify   [2] IMPLICIT Identify-Response,
    identify   [2] IMPLICIT RejectPDU,
    rename   [3] IMPLICIT Rename-Response,
    rename   [3] IMPLICIT RejectPDU,
    read   [4] IMPLICIT Read-Response,
    read   [4] IMPLICIT RejectPDU,
    write   [5] IMPLICIT Write-Response,
    write   [5] IMPLICIT RejectPDU,
    getVariableAccessAttributes   [6] IMPLICIT GetVariableAccessAttributes-Response,
    getVariableAccessAttributes   [6] IMPLICIT RejectPDU,
    defineNamedVariable   [7] IMPLICIT DefineNamedVariable-Response,
    defineNamedVariable   [7] IMPLICIT RejectPDU,
    defineScatteredAccess   [8] IMPLICIT DefineScatteredAccess-Response,
    defineScatteredAccess   [8] IMPLICIT RejectPDU,
    getScatteredAccessAttributes   [9] IMPLICIT GetScatteredAccessAttributes-Response,
    getScatteredAccessAttributes   [9] IMPLICIT RejectPDU,
    deleteVariableAccess   [10] IMPLICIT DeleteVariableAccess-Response,
    deleteVariableAccess   [10] IMPLICIT RejectPDU,
    defineNamedVariableList   [11] IMPLICIT DefineNamedVariableList-Response,
    defineNamedVariableList   [11] IMPLICIT RejectPDU,
    getNamedVariableListAttributes   [12] IMPLICIT GetNamedVariableListAttributes-Response,
    getNamedVariableListAttributes   [12] IMPLICIT RejectPDU,
    deleteNamedVariableList   [13] IMPLICIT DeleteNamedVariableList-Response,
    deleteNamedVariableList   [13] IMPLICIT RejectPDU,
    defineNamedType   [14] IMPLICIT DefineNamedType-Response,
    defineNamedType   [14] IMPLICIT RejectPDU,
    getNamedTypeAttributes  [15] IMPLICIT GetNamedTypeAttributes-Response,
    getNamedTypeAttributes   [15] IMPLICIT RejectPDU,
    deleteNamedType   [16] IMPLICIT DeleteNamedType-Response,
    deleteNamedType   [16] IMPLICIT RejectPDU,
    input   [17] IMPLICIT Input-Response,
    output   [18] IMPLICIT Output-Response,
    output   [18] IMPLICIT RejectPDU,
    takeControl   [19] TakeControl-Response,
    takeControl   [19] TakeControl-Response,
    relinquishControl   [20] IMPLICIT RelinquishControl-Response,
    relinquishControl   [20] IMPLICIT RejectPDU,
    relinquishControl [20] IMPLICIT RejectPDU,
    defineSemaphore   [21] IMPLICIT DefineSemaphore-Response,
    defineSemaphore   [21] IMPLICIT RejectPDU,
    deleteSemaphore   [22] IMPLICIT DeleteSemaphore-Response,
    deleteSemaphore   [22] IMPLICIT RejectPDU,
    reportSemaphoreStatus   [23] IMPLICIT ReportSemaphoreStatus-Response,
    reportSemaphoreStatus   [23] IMPLICIT RejectPDU,
    reportPoolSemaphoreStatus   [24] IMPLICIT ReportPoolSemaphoreStatus-Response,
    reportPoolSemaphoreStatus   [24] IMPLICIT RejectPDU,
    reportSemaphoreEntryStatus  [25] IMPLICIT ReportSemaphoreEntryStatus-Response,
    reportSemaphoreEntryStatus  [25] IMPLICIT RejectPDU,
    initiateDownloadSequence    [26] IMPLICIT InitiateDownloadSequence-Response,
    initiateDownloadSequence    [26] IMPLICIT RejectPDU,
    downloadSegment  [27] IMPLICIT DownloadSegment-Response,
    downloadSegment  [27] IMPLICIT RejectPDU,
    terminateDownloadSequence   [28] IMPLICIT TerminateDownloadSequence-Response,
    terminateDownloadSequence   [28] IMPLICIT RejectPDU,
    initiateUploadSequence  [29] IMPLICIT InitiateUploadSequence-Response,
    initiateUploadSequence  [29] IMPLICIT RejectPDU,
    uploadSegment       [30] IMPLICIT UploadSegment-Response,
    uploadSegment       [30] IMPLICIT RejectPDU,
    terminateUploadSequence  [31] IMPLICIT TerminateUploadSequence-Response,  
    terminateUploadSequence  [31] IMPLICIT RejectPDU,
    requestDomainDownload    [32] IMPLICIT RequestDomainDownload-Response,
    requestDomainDownload    [32] IMPLICIT RejectPDU,
    requestDomainUpload  [33] IMPLICIT RequestDomainUpload-Response,
    requestDomainUpload  [33] IMPLICIT RejectPDU,
    loadDomainContent    [34] IMPLICIT LoadDomainContent-Response,
    loadDomainContent    [34] IMPLICIT RejectPDU,
    storeDomainContent   [35] IMPLICIT StoreDomainContent-Response,
    storeDomainContent   [35] IMPLICIT RejectPDU,
    deleteDomain   [36] IMPLICIT DeleteDomain-Response,
    deleteDomain   [36] IMPLICIT RejectPDU,
    getDomainAttributes   [37] IMPLICIT GetDomainAttributes-Response,
    getDomainAttributes   [37] IMPLICIT RejectPDU,
    createProgramInvocation   [38] IMPLICIT CreateProgramInvocation-Response,
    createProgramInvocation   [38] IMPLICIT RejectPDU,
    deleteProgramInvocation   [39] IMPLICIT DeleteProgramInvocation-Response,
    deleteProgramInvocation   [39] IMPLICIT RejectPDU,
    start   [40] IMPLICIT Start-Response,
    start   [40] IMPLICIT RejectPDU,
    stop   [41] IMPLICIT Stop-Response,
    stop   [41] IMPLICIT RejectPDU,
    resume   [42] IMPLICIT Resume-Response,
    resume   [42] IMPLICIT RejectPDU,
    reset   [43] IMPLICIT Reset-Response,
    reset   [43] IMPLICIT RejectPDU,
    kill   [44] IMPLICIT Kill-Response,
    kill   [44] IMPLICIT RejectPDU,
    getProgramInvocationAttributes   [45] IMPLICIT GetProgramInvocationAttributes-Response,
    getProgramInvocationAttributes   [45] IMPLICIT RejectPDU,
    obtainFile   [46] IMPLICIT ObtainFile-Response,
    obtainFile   [46] IMPLICIT RejectPDU,
    defineEventCondition   [47] IMPLICIT DefineEventCondition-Response,
    defineEventCondition   [47] IMPLICIT RejectPDU,
    deleteEventCondition   [48] IMPLICIT DeleteEventCondition-Response,
    getEventConditionAttributes   [49] IMPLICIT GetEventConditionAttributes-Response,
    getEventConditionAttributes   [49] IMPLICIT RejectPDU,
    reportEventConditionStatus   [50] IMPLICIT ReportEventConditionStatus-Response,
    reportEventConditionStatus   [50] IMPLICIT RejectPDU,
    alterEventConditionMonitoring   [51] IMPLICIT AlterEventConditionMonitoring-Response,
    alterEventConditionMonitoring   [51] IMPLICIT RejectPDU,
    triggerEvent   [52] IMPLICIT TriggerEvent-Response,
    triggerEvent   [52] IMPLICIT RejectPDU,
    defineEventAction   [53] IMPLICIT DefineEventAction-Response,
    defineEventAction   [53] IMPLICIT RejectPDU,
    deleteEventAction   [54] IMPLICIT DeleteEventAction-Response,
    deleteEventAction   [54] IMPLICIT RejectPDU,
    getEventActionAttributes   [55] IMPLICIT GetEventActionAttributes-Response,
    getEventActionAttributes   [55] IMPLICIT RejectPDU,
    reportEventActionStatus   [56] IMPLICIT ReportEventActionStatus-Response,
    reportEventActionStatus   [56] IMPLICIT RejectPDU,
    defineEventEnrollment [57] IMPLICIT DefineEventEnrollment-Response,
    defineEventEnrollment [57] IMPLICIT RejectPDU,
    deleteEventEnrollment [58] IMPLICIT DeleteEventEnrollment-Response,
    deleteEventEnrollment [58] IMPLICIT RejectPDU,
    alterEventEnrollment [59] IMPLICIT AlterEventEnrollment-Response,
    alterEventEnrollment [59] IMPLICIT RejectPDU,
    reportEventEnrollmentStatus [60] IMPLICIT ReportEventEnrollmentStatus-Response,
    reportEventEnrollmentStatus [60] IMPLICIT RejectPDU,
    getEventEnrollmentAttributes [61] IMPLICIT GetEventEnrollmentAttributes-Response,
    getEventEnrollmentAttributes [61] IMPLICIT RejectPDU,
    acknowledgeEventNotification [62] IMPLICIT AcknowledgeEventNotification-Response,
    acknowledgeEventNotification [62] IMPLICIT RejectPDU,
    getAlarmSummary [63] IMPLICIT GetAlarmSummary-Response,
    getAlarmSummary [63] IMPLICIT RejectPDU,
    getAlarmEnrollmentSummary [64] IMPLICIT GetAlarmEnrollmentSummary-Response,
    getAlarmEnrollmentSummary [64] IMPLICIT RejectPDU,
    readJournal [65] IMPLICIT ReadJournal-Response,
    readJournal [65] IMPLICIT RejectPDU,
    writeJournal [66] IMPLICIT WriteJournal-Response,
    writeJournal [66] IMPLICIT RejectPDU,
    initializeJournal [67] IMPLICIT InitializeJournal-Response,
    initializeJournal [67] IMPLICIT RejectPDU,
    reportJournalStatus [68] IMPLICIT ReportJournalStatus-Response,
    reportJournalStatus [68] IMPLICIT RejectPDU,
    createJournal [69] IMPLICIT CreateJournal-Response,
    createJournal [69] IMPLICIT RejectPDU,
    deleteJournal [70] IMPLICIT DeleteJournal-Response,
    deleteJournal [70] IMPLICIT RejectPDU,
    getCapabilityList [71] IMPLICIT GetCapabilityList-Response,
    getCapabilityList [71] IMPLICIT RejectPDU,
-- choices [72] through [77] are reserved for use by services
-- defined in annex D
    fileOpen [72] IMPLICIT FileOpen-Response,
    fileOpen [72] IMPLICIT RejectPDU,
    fileRead [73] IMPLICIT FileRead-Response,
    fileRead [73] IMPLICIT RejectPDU,
    fileClose [74] IMPLICIT FileClose-Response,
    fileClose [74] IMPLICIT RejectPDU,
    fileRename [75] IMPLICIT FileRename-Response,
    fileRename [75] IMPLICIT RejectPDU,
    fileDelete [76] IMPLICIT FileDelete-Response,
    fileDelete [76] IMPLICIT RejectPDU,
    fileDirectory [77] IMPLICIT FileDirectory-Response,
    fileDirectory [77] IMPLICIT RejectPDU,
    ...,
    */
    additionalService [78] AdditionalService-Response,
    -- choice [79] is reserved
    getDataExchangeAttributes [80] GetDataExchangeAttributes-Response,
    -- Shall not appear in minor version 1
    exchangeData [81] IMPLICIT ExchangeData-Response,
    -- Shall not appear in minor version 1
    defineAccessControlList [82] IMPLICIT DefineAccessControlList-Response,
    -- Shall not appear in minor version 1 or 2
    getAccessControlListAttributes [83] IMPLICIT GetAccessControlListAttributes-Response,
    -- Shall not appear in minor version 1 or 2
    reportAccessControlledObjects [84] IMPLICIT ReportAccessControlledObjects-Response,
    -- Shall not appear in minor version 1 or 2
    deleteAccessControlList [85] IMPLICIT DeleteAccessControlList-Response,
    -- Shall not appear in minor version 1 or 2
    changeAccessControl [86] IMPLICIT ChangeAccessControl-Response,
    -- Shall not appear in minor version 1 or 2
   ...
}

/*
AdditionalService-Response ::= CHOICE {
    vMDStop              [0] IMPLICIT VMDStop-Response,
    vMDStop              [0] IMPLICIT RejectPDU,
    vMDReset             [1] IMPLICIT VMDReset-Response,
    vMDReset             [1] IMPLICIT RejectPDU,
    select               [2] IMPLICIT Select-Response,
    select               [2] IMPLICIT RejectPDU,
    alterPI              [3] IMPLICIT AlterProgramInvocationAttributes-Response,
    alterPI              [3] IMPLICIT RejectPDU,
    initiateUCLoad       [4] IMPLICIT InitiateUnitControlLoad-Response,
    initiateUCLoad       [4] IMPLICIT RejectPDU,
    uCLoad               [5] IMPLICIT UnitControlLoadSegment-Response,
    uCLoad               [5] IMPLICIT RejectPDU,
    uCUpload             [6] IMPLICIT UnitControlUpload-Response,
    uCUpload             [6] IMPLICIT RejectPDU,
    startUC              [7] IMPLICIT StartUnitControl-Response,
    startUC              [7] IMPLICIT RejectPDU,
    stopUC               [8] IMPLICIT StopUnitControl-Response,
    stopUC               [8] IMPLICIT RejectPDU,
    createUC             [9] IMPLICIT CreateUnitControl-Response,
    createUC             [9] IMPLICIT RejectPDU,
    addToUC              [10] IMPLICIT AddToUnitControl-Response,
    addToUC              [10] IMPLICIT RejectPDU,
    removeFromUC         [11] IMPLICIT RemoveFromUnitControl-Response,
    removeFromUC         [11] IMPLICIT RejectPDU,
    getUCAttributes      [12] IMPLICIT GetUnitControlAttributes-Response,
    getUCAttributes      [12] IMPLICIT RejectPDU,
    loadUCFromFile       [13] IMPLICIT LoadUnitControlFromFile-Response,
    loadUCFromFile       [13] IMPLICIT RejectPDU,
    storeUCToFile        [14] IMPLICIT StoreUnitControlToFile-Response,
    storeUCToFile        [14] IMPLICIT RejectPDU,
    deleteUC             [15] IMPLICIT DeleteUnitControl-Response,
    deleteUC             [15] IMPLICIT RejectPDU,
    defineECL            [16] IMPLICIT DefineEventConditionList-Response,
    defineECL            [16] IMPLICIT RejectPDU,
    deleteECL            [17] IMPLICIT DeleteEventConditionList-Response,
    deleteECL            [17] IMPLICIT RejectPDU,
    addECLReference      [18] IMPLICIT AddEventConditionListReference-Response,
    addECLReference      [18] IMPLICIT RejectPDU,
    removeECLReference   [19] IMPLICIT RemoveEventConditionListReference-Response,
    removeECLReference   [19] IMPLICIT RejectPDU,
    getECLAttributes     [20] IMPLICIT GetEventConditionListAttributes-Response,
    getECLAttributes     [20] IMPLICIT RejectPDU,
    reportECLStatus      [21] IMPLICIT ReportEventConditionListStatus-Response,
    reportECLStatus      [21] IMPLICIT RejectPDU,
    alterECLMonitoring   [22] IMPLICIT AlterEventConditionListMonitoring-Response,
    alterECLMonitoring   [22] IMPLICIT RejectPDU
}
*/
AdditionalService-Response ::= ProblematicThereforeAnyType

Response-Detail ::= CHOICE {
          -- this choice shall be selected if the tag value of the
          -- ConfirmedServiceResponse does not match any of the tags below
   otherRequests       NULL
,  status
       [0] CS-Status-Response
,  getProgramInvocationAttributes
       [45] IMPLICIT CS-GetProgramInvocationAttributes-Response
,  getEventConditionAttributes
       [49] IMPLICIT CS-GetEventConditionAttributes-Response
   }

Confirmed-ErrorPDU ::= SEQUENCE {
   invokeID                   [0] IMPLICIT Unsigned32,
   modifierPosition           [1] IMPLICIT Unsigned32 OPTIONAL,
   serviceError               [2] IMPLICIT ServiceError
   }

ServiceError ::= SEQUENCE {
   errorClass          [0] CHOICE {
   vmd-state                  [0] IMPLICIT INTEGER {
       other                            (0),
       vmd-state-conflict               (1),
       vmd-operational-problem          (2),
       domain-transfer-problem          (3),
       state-machine-id-invalid         (4)
   } (0..4),
   application-reference      [1] IMPLICIT INTEGER {
       other                            (0),
       application-unreachable          (1),
       connection-lost                  (2),
       application-reference-invalid    (3),
       context-unsupported              (4)
   } (0..4),
   definition                 [2] IMPLICIT INTEGER {
       other                            (0),
       object-undefined                 (1),
       invalid-address                  (2),
       type-unsupported                 (3),
       type-inconsistent                (4),
       object-exists                    (5),
       object-attribute-inconsistent    (6)
   } (0..6),
   resource                   [3] IMPLICIT INTEGER {
       other                            (0),
       memory-unavailable               (1),
       processor-resource-unavailable   (2),
       mass-storage-unavailable         (3),
       capability-unavailable           (4),
       capability-unknown               (5)
   } (0..5),
   service                    [4] IMPLICIT INTEGER {
       other                            (0),
       primitives-out-of-sequence       (1),
       object-state-conflict            (2),
                    -- Value 3 reserved for further definition
       continuation-invalid             (4),
       object-constraint-conflict       (5)
   } (0..5),
   service-preempt            [5] IMPLICIT INTEGER {
       other                            (0),
       timeout                          (1),
       deadlock                         (2),
       cancel                           (3)
   } (0..3),
   time-resolution            [6] IMPLICIT INTEGER {
       other                            (0),
       unsupportable-time-resolution    (1)
   } (0..1),
   access                     [7] IMPLICIT INTEGER {
       other                            (0),
       object-access-unsupported        (1),
       object-non-existent              (2),
       object-access-denied             (3),
       object-invalidated               (4)
   } (0..4),
   initiate                   [8] IMPLICIT INTEGER {
       other                            (0),
                    -- Values 1 and 2 are reserved for further definition
       max-services-outstanding-calling-insufficient     (3),
       max-services-outstanding-called-insufficient      (4),
       service-CBB-insufficient         (5),
       parameter-CBB-insufficient       (6),
       nesting-level-insufficient       (7)
   } (0..7),
   conclude                   [9] IMPLICIT INTEGER {
       other                            (0),
       further-communication-required   (1)
   } (0..1)
,  cancel                     [10] IMPLICIT INTEGER {
       other                            (0),
       invoke-id-unknown                (1),
       cancel-not-possible              (2)
   } (0..2)
,  cancel                     [10] IMPLICIT NULL
,  file                       [11] IMPLICIT INTEGER {
       other                            (0),
       filename-ambiguous               (1),
       file-busy                        (2),
       filename-syntax-error            (3),
       content-type-invalid             (4),
       position-invalid                 (5),
       file-access-denied               (6),
       file-non-existent                (7),
       duplicate-filename               (8),
       insufficient-space-in-filestore  (9)
   } (0..9)
,  file                       [11] IMPLICIT NULL
,  others                     [12] IMPLICIT INTEGER
 } ,
   additionalCode         [1] IMPLICIT INTEGER OPTIONAL,
   additionalDescription  [2] IMPLICIT VisibleString OPTIONAL,
   serviceSpecificInfo    [3] CHOICE {
       obtainFile                 [0] IMPLICIT ObtainFile-Error
,      obtainFile                 [0] IMPLICIT NULL
,      start                      [1] IMPLICIT Start-Error
,      start                      [1] IMPLICIT NULL
,      stop                       [2] IMPLICIT Stop-Error
,      stop                       [2] IMPLICIT NULL
,      resume                     [3] IMPLICIT Resume-Error
,      resume                     [3] IMPLICIT NULL
,      reset                      [4] IMPLICIT Reset-Error
,      reset                      [4] IMPLICIT NULL
,      deleteVariableAccess       [5] IMPLICIT DeleteVariableAccess-Error
,      deleteVariableAccess       [5] IMPLICIT NULL
,      deleteNamedVariableList    [6] IMPLICIT DeleteNamedVariableList-Error
,      deleteNamedVariableList    [6] IMPLICIT NULL
,      deleteNamedType            [7] IMPLICIT DeleteNamedType-Error
,      deleteNamedType            [7] IMPLICIT NULL
,      defineEventEnrollment-Error   [8] DefineEventEnrollment-Error
,      defineEventEnrollment-Error   [8] IMPLICIT NULL
       -- [9] Reserved for use by annex D
,  fileRename                    [9] IMPLICIT FileRename-Error
,  fileRename                    [9] IMPLICIT NULL
,      additionalService          [10] AdditionalService-Error
,      additionalService          [10] IMPLICIT NULL
,      changeAccessControl        [11] IMPLICIT ChangeAccessControl-Error
,      changeAccessControl        [11] IMPLICIT NULL
       } OPTIONAL
   }


AdditionalService-Error ::= CHOICE {
        defineEcl                     [0] IMPLICIT ImplicitNullable{DefineEventConditionList-Error},
        addECLReference               [1] IMPLICIT ImplicitNullable{AddEventConditionListReference-Error},
        removeECLReference            [2] IMPLICIT ImplicitNullable{RemoveEventConditionListReference-Error},
        initiateUC                    [3] IMPLICIT ImplicitNullable{InitiateUnitControl-Error},
        startUC                       [4] IMPLICIT StartUnitControl-Error,
        -- startUC                       [4] IMPLICIT NULL,
        stopUC                        [5] IMPLICIT StopUnitControl-Error,
        -- stopUC                        [5] IMPLICIT NULL,
        deleteUC                      [6] IMPLICIT ImplicitNullable{DeleteUnitControl-Error},
        loadUCFromFile                [7] IMPLICIT ImplicitNullable{LoadUnitControlFromFile-Error}
}

TimeOfDay ::= OCTET STRING (SIZE(4|6))
   -- Encoded as: '0000ttttttttttttttttttttttttttttdddddddddddddddd'B
maxIdentifier INTEGER ::= 32

Identifier ::= CHOICE {
       ifChar UTF8String (SIZE(1..maxIdentifier)),
       notChar VisibleString ( FROM
              ("A"|"a"|"B"|"b"|"C"|"c"|"D"|"d"|"E"|"e"|"F"|"f"|
              "G"|"g"|"H"|"h"|"I"|"i"|"J"|"j"|"K"|"k"|"L"|"l"|
              "M"|"m"|"N"|"n"|"O"|"o"|"P"|"p"|"Q"|"q"|"R"|"r"|
              "S"|"s"|"T"|"t"|"U"|"u"|"V"|"v"|"W"|"w"|"X"|"x"|
              "Y"|"y"|"Z"|"z"|"$"|"_"|"0"|"1"|"2"|"3"|"4"|"5"|
              "6"|"7"|"8"|"9") ) (SIZE(1..maxIdentifier))
}

Integer8 ::= INTEGER(-128..127)        -- range -128 <= i <= 127
Integer16 ::= INTEGER(-32768..32767)          -- range -32,768 <= i <= 32,767
Integer32 ::= INTEGER(-2147483648..2147483647)   -- range -2**31 <= i <= 2**31 - 1
Unsigned8 ::= INTEGER(0..127)             -- range 0 <= i <= 127
Unsigned16 ::= INTEGER(0..32767)          -- range 0 <= i <= 32767
Unsigned32 ::= INTEGER(0..2147483647)     -- range 0 <= i <= 2**31 - 1
ObjectName ::= CHOICE {
   vmd-specific     [0] IMPLICIT Identifier,
   domain-specific  [1] IMPLICIT SEQUENCE {
       domainID         Identifier,
       itemID           Identifier
       },
   aa-specific      [2] IMPLICIT Identifier
}

ObjectClass ::=    CHOICE {
   basicObjectClass       [0] IMPLICIT INTEGER {
       namedVariable          (0)
             -- value 1 is reserved for definition in Annex E
,      scatteredAccess        (1)
,      namedVariableList      (2)
,      namedType              (3)
,      semaphore              (4),
       eventCondition         (5),
       eventAction            (6),
       eventEnrollment        (7),
       journal                (8),
       domain                 (9),
       programInvocation      (10),
       operatorStation        (11),
       dataExchange           (12),
   -- Shall not appear in minor version 1
       accessControlList      (13)
   -- Shall not appear in minor version 1 or 2
       } (0..13),
   ...
,  csObjectClass          [1] IMPLICIT INTEGER {
       eventConditionList     (0),
       unitControl            (1) } (0..1)
   }

MMSString ::= CHOICE {
       ifChar UTF8String,
       notChar VisibleString
}

MMS255String ::= CHOICE {
       ifChar UTF8String (SIZE(1..255)),
       notChar VisibleString (SIZE(1..255))
}

FileName ::= SEQUENCE OF GraphicString

Initiate-RequestPDU ::= SEQUENCE {
   localDetailCalling                   [0] IMPLICIT Integer32 OPTIONAL,
   proposedMaxServOutstandingCalling    [1] IMPLICIT Integer16,
   proposedMaxServOutstandingCalled     [2] IMPLICIT Integer16,
   proposedDataStructureNestingLevel    [3] IMPLICIT Integer8 OPTIONAL,
   initRequestDetail                    [4] IMPLICIT SEQUENCE {
       proposedVersionNumber                [0] IMPLICIT Integer16,
       proposedParameterCBB                 [1] IMPLICIT ParameterSupportOptions,
       servicesSupportedCalling             [2] IMPLICIT ServiceSupportOptions ,
       ...
,      additionalSupportedCalling           [3] IMPLICIT AdditionalSupportOptions
,      additionalCbbSupportedCalling        [4] IMPLICIT AdditionalCBBOptions,
       privilegeClassIdentityCalling        [5] IMPLICIT VisibleString
       }
   }

Initiate-ResponsePDU ::= SEQUENCE {
   localDetailCalled                    [0] IMPLICIT Integer32 OPTIONAL,
   negotiatedMaxServOutstandingCalling  [1] IMPLICIT Integer16,
   negotiatedMaxServOutstandingCalled   [2] IMPLICIT Integer16,
   negotiatedDataStructureNestingLevel  [3] IMPLICIT Integer8 OPTIONAL,
   initResponseDetail                   [4] IMPLICIT SEQUENCE {
       negotiatedVersionNumber              [0] IMPLICIT Integer16,
       negotiatedParameterCBB               [1] IMPLICIT ParameterSupportOptions,
       servicesSupportedCalled              [2] IMPLICIT ServiceSupportOptions,
       ...
,      additionalSupportedCalled            [3] IMPLICIT AdditionalSupportOptions
,      additionalCbbSupportedCalled         [4] IMPLICIT AdditionalCBBOptions,
       privilegeClassIdentityCalled         [5] IMPLICIT VisibleString
       }
   }

Initiate-ErrorPDU ::= ServiceError
 Conclude-RequestPDU ::= NULL
 Conclude-ResponsePDU ::= NULL
 Conclude-ErrorPDU ::= ServiceError
 Cancel-RequestPDU ::= Unsigned32 -- originalInvokeID
 Cancel-ResponsePDU ::= Unsigned32 -- originalInvokeID
 Cancel-ErrorPDU ::= SEQUENCE {
   originalInvokeID       [0] IMPLICIT Unsigned32,
   serviceError           [1] IMPLICIT ServiceError
   }

RejectPDU ::= SEQUENCE {
   originalInvokeID       [0] IMPLICIT Unsigned32 OPTIONAL,
   -- Deviation from ISO 9506: This was made optional so that
   -- if implicitly encoded in a tag shared with a NULL value,
   -- the empty sequence {} could produce the same encoding
   -- when using BER / CER / DER.
   rejectReason           CHOICE {
        confirmed-requestPDU   [1] IMPLICIT INTEGER {
            other                         (0),
            unrecognized-service          (1),
            unrecognized-modifier         (2),
            invalid-invokeID              (3),
            invalid-argument              (4),
            invalid-modifier              (5),
            max-serv-outstanding-exceeded (6),
                                    -- Value 7 reserved for further definition
            max-recursion-exceeded        (8),
            value-out-of-range            (9)
            } (0..9),
        confirmed-responsePDU  [2] IMPLICIT INTEGER {
            other                         (0),
            unrecognized-service          (1),
            invalid-invokeID              (2),
            invalid-result                (3),
                                    -- Value 4 reserved for further definition
            max-recursion-exceeded        (5),
            value-out-of-range            (6)
            } (0..6),
        confirmed-errorPDU     [3] IMPLICIT INTEGER {
            other                         (0),
            unrecognized-service          (1),
            invalid-invokeID              (2),
            invalid-serviceError          (3),
            value-out-of-range            (4)
            } (0..4),
        unconfirmedPDU         [4] IMPLICIT INTEGER {
            other                         (0),
            unrecognized-service          (1),
            invalid-argument              (2),
            max-recursion-exceeded        (3),
            value-out-of-range            (4)
            } (0..4),
        pdu-error              [5] IMPLICIT INTEGER {
            unknown-pdu-type              (0),
            invalid-pdu                   (1),
            illegal-acse-mapping          (2)
            },
        cancel-requestPDU      [6] IMPLICIT INTEGER {
            other                         (0),
            invalid-invokeID              (1)
            } (0..1),
        cancel-responsePDU     [7] IMPLICIT INTEGER {
            other                         (0),
            invalid-invokeID              (1)
            } (0..1),
        cancel-errorPDU        [8] IMPLICIT INTEGER {
            other                         (0),
            invalid-invokeID              (1),
            invalid-serviceError          (2),
            value-out-of-range            (3)
            } (0..3),
        cancel-requestPDU      [6] IMPLICIT NULL,
        cancel-responsePDU     [7] IMPLICIT NULL,
        cancel-errorPDU        [8] IMPLICIT NULL,
        conclude-requestPDU    [9] IMPLICIT INTEGER {
            other                         (0),
            invalid-argument              (1)
            } (0..1),
        conclude-responsePDU   [10] IMPLICIT INTEGER {
            other                         (0),
            invalid-result                (1)
            } (0..1),
        conclude-errorPDU      [11] IMPLICIT INTEGER {
            other                         (0),
            invalid-serviceError          (1),
            value-out-of-range            (2)
            } (0..2)
        }
}

DefineAccessControlList-Request ::= SEQUENCE {
   accessControlListName         [0] IMPLICIT Identifier,
   accessControlListElements     [1] IMPLICIT SEQUENCE {
       readAccessCondition           [0] AccessCondition OPTIONAL,
       storeAccessCondition          [1] AccessCondition OPTIONAL,
       writeAccessCondition          [2] AccessCondition OPTIONAL,
       loadAccessCondition           [3] AccessCondition OPTIONAL,
       executeAccessCondition        [4] AccessCondition OPTIONAL,
       deleteAccessCondition         [5] AccessCondition OPTIONAL,
       editAccessCondition           [6] AccessCondition OPTIONAL
       }
   }

DefineAccessControlList-Response ::= NULL

GetAccessControlListAttributes-Request ::= CHOICE {
   accessControlListName            [0] IMPLICIT Identifier,
   vMD                              [1] IMPLICIT NULL,
   namedObject                      [2] IMPLICIT SEQUENCE {
       objectClass                      [0] ObjectClass,
       objectName                       [1] ObjectName
       }
   }

GetAccessControlListAttributes-Response ::= SEQUENCE {
   name                       [0] Identifier,
   accessControlListElements     [1] IMPLICIT SEQUENCE {
       readAccessCondition              [0] AccessCondition OPTIONAL,
       storeAccessCondition             [1] AccessCondition OPTIONAL,
       writeAccessCondition             [2] AccessCondition OPTIONAL,
       loadAccessCondition              [3] AccessCondition OPTIONAL,
       executeAccessCondition           [4] AccessCondition OPTIONAL,
       deleteAccessCondition            [5] AccessCondition OPTIONAL,
       editAccessCondition              [6] AccessCondition OPTIONAL
       },
   vMDuse                        [2] IMPLICIT BOOLEAN,
   references                    [3] IMPLICIT SEQUENCE OF SEQUENCE {
       objectClass                      [0] ObjectClass,
       objectCount                      [1] IMPLICIT INTEGER
       }
,  accessControlList             [4] IMPLICIT Identifier OPTIONAL
                       -- shall be included if and only if
                       -- aco has been negotiated
   }

ReportAccessControlledObjects-Request ::= SEQUENCE {
   accessControlList          [0] IMPLICIT Identifier,
   objectClass                [1] ObjectClass,
   continueAfter              [2] ObjectName OPTIONAL
   }

ReportAccessControlledObjects-Response ::= SEQUENCE {
   listOfNames                [0] IMPLICIT SEQUENCE OF ObjectName,
   moreFollows                [1] IMPLICIT BOOLEAN DEFAULT FALSE
   }

DeleteAccessControlList-Request ::= Identifier
         -- Name of Access Control List Object
 DeleteAccessControlList-Response ::= NULL

ChangeAccessControl-Request ::= SEQUENCE {
   scopeOfChange              CHOICE {
       vMDOnly                    [0] IMPLICIT NULL,
       listOfObjects              [1] IMPLICIT SEQUENCE {
          objectClass                [0] ObjectClass,
          objectScope                [1] CHOICE {
             specific                   [0] IMPLICIT SEQUENCE OF ObjectName,
                           -- Names of the objects (of class objectClass)
                           -- whose access is to be changed
             aa-specific                [1] IMPLICIT NULL,
             domain                     [2] IMPLICIT Identifier,
                           -- Name of the Domain whose elements
                           -- are to be changed
             vmd                    [3] IMPLICIT NULL
             }
          }
       },
   accessControlListName         [2] IMPLICIT Identifier
             -- name of the AccessControlList Object that contains
             -- the conditions for access control
   }

ChangeAccessControl-Response ::= SEQUENCE {
   numberMatched          [0] IMPLICIT Unsigned32,
   numberChanged          [1] IMPLICIT Unsigned32
   }

ChangeAccessControl-Error ::= Unsigned32

StatusResponse ::= SEQUENCE {
   vmdLogicalStatus           [0] IMPLICIT INTEGER {
       state-changes-allowed         (0),
       no-state-changes-allowed      (1),
       limited-services-permitted    (2),
       support-services-allowed      (3)
       } (0..3),
   vmdPhysicalStatus          [1] IMPLICIT INTEGER {
       operational                   (0),
       partially-operational         (1),
       inoperable                    (2),
       needs-commissioning           (3)
       } (0..3),
   localDetail                [2] IMPLICIT BIT STRING (SIZE(0..128)) OPTIONAL
   }

CS-Status-Response ::= CHOICE {
   fullResponse           SEQUENCE {
       operationState             [0] IMPLICIT OperationState,
       extendedStatus             [1] IMPLICIT ExtendedStatus,
       extendedStatusMask         [2] IMPLICIT ExtendedStatus DEFAULT '1111'B,
       selectedProgramInvocation     CHOICE {
          programInvocation             [3] IMPLICIT Identifier,
          noneSelected                  [4] IMPLICIT NULL      } }
,
   noExtraResponse     NULL
   }

OperationState ::= INTEGER {
   idle                             (0),
   loaded                           (1),
   ready                            (2),
   executing                        (3),
   motion-paused                    (4),
   manualInterventionRequired       (5) } (0..5)

ExtendedStatus ::= BIT STRING {
   safetyInterlocksViolated         (0),
   anyPhysicalResourcePowerOn       (1),
   allPhysicalResourcesCalibrated   (2),
   localControl                     (3) } (SIZE(4))

Status-Request ::= BOOLEAN -- Extended Derivation

Status-Response ::= StatusResponse

UnsolicitedStatus ::= StatusResponse

GetNameList-Request ::= SEQUENCE {
   objectClass            [0] ObjectClass,
   objectScope            [1] CHOICE {
       vmdSpecific            [0] IMPLICIT NULL,
       domainSpecific         [1] IMPLICIT Identifier,
       aaSpecific             [2] IMPLICIT NULL },
       continueAfter       [2] IMPLICIT Identifier OPTIONAL }

GetNameList-Response ::= SEQUENCE {
   listOfIdentifier       [0] IMPLICIT SEQUENCE OF Identifier,
   moreFollows            [1] IMPLICIT BOOLEAN DEFAULT TRUE }

Identify-Request ::= NULL

Identify-Response ::= SEQUENCE {
   vendorName             [0] IMPLICIT MMSString,
       modelName           [1] IMPLICIT MMSString,
   revision               [2] IMPLICIT MMSString,
   listOfAbstractSyntaxes [3] IMPLICIT SEQUENCE OF OBJECT IDENTIFIER OPTIONAL
   }

Rename-Request ::= SEQUENCE {
   objectClass            [0] ObjectClass,
   currentName            [1] ObjectName,
   newIdentifier          [2] IMPLICIT Identifier }

Rename-Response ::= NULL

GetCapabilityList-Request ::= SEQUENCE {
   continueAfter          MMSString OPTIONAL
   }

GetCapabilityList-Response ::= SEQUENCE {
   listOfCapabilities     [0] IMPLICIT SEQUENCE OF MMSString,
   moreFollows            [1] IMPLICIT BOOLEAN DEFAULT TRUE
   }

VMDStop-Request ::= NULL
 VMDStop-Response ::= NULL
 VMDReset-Request ::= BOOLEAN -- Extended Derivation
 VMDReset-Response ::= StatusResponse

InitiateDownloadSequence-Request ::= SEQUENCE {
   domainName                 [0] IMPLICIT Identifier,
   listOfCapabilities         [1] IMPLICIT SEQUENCE OF MMSString,
   sharable                   [2] IMPLICIT BOOLEAN }

InitiateDownloadSequence-Response ::= NULL
 DownloadSegment-Request ::= Identifier -- Domain Name
 DownloadSegment-Response ::= SEQUENCE {
   loadData               LoadData,
   moreFollows            [1] IMPLICIT BOOLEAN DEFAULT TRUE }

LoadData ::= CHOICE {
   non-coded              [0] IMPLICIT OCTET STRING,
   coded                  EXTERNAL,
   embedded               EMBEDDED PDV }

TerminateDownloadSequence-Request ::= SEQUENCE {
   domainName             [0] IMPLICIT Identifier,
   discard                [1] IMPLICIT ServiceError OPTIONAL }

TerminateDownloadSequence-Response ::= NULL
 InitiateUploadSequence-Request ::= Identifier -- Domain Name
 InitiateUploadSequence-Response ::= SEQUENCE {
   ulsmID                     [0] IMPLICIT Integer32,
   listOfCapabilities         [1] IMPLICIT SEQUENCE OF MMSString }

UploadSegment-Request ::= Integer32 -- ULSM ID
 UploadSegment-Response ::= SEQUENCE {
   loadData               LoadData,
   moreFollows            [1] IMPLICIT BOOLEAN DEFAULT TRUE }

TerminateUploadSequence-Request ::= Integer32 -- ULSM ID
 TerminateUploadSequence-Response ::= NULL

RequestDomainDownload-Request ::= SEQUENCE {
   domainName                 [0] IMPLICIT Identifier,
   listOfCapabilities         [1] IMPLICIT SEQUENCE OF MMSString OPTIONAL,
   sharable                   [2] IMPLICIT BOOLEAN,
   fileName                   [4] IMPLICIT FileName }

RequestDomainDownload-Response ::= NULL

RequestDomainUpload-Request ::= SEQUENCE {
   domainName                 [0] IMPLICIT Identifier,
   fileName                   [1] IMPLICIT FileName }

RequestDomainUpload-Response ::= NULL

LoadDomainContent-Request ::= SEQUENCE {
   domainName                 [0] IMPLICIT Identifier,
   listOfCapabilities         [1] IMPLICIT SEQUENCE OF MMSString OPTIONAL,
   sharable                   [2] IMPLICIT BOOLEAN,
   fileName                   [4] IMPLICIT FileName
,  thirdParty                 [5] IMPLICIT ApplicationReference OPTIONAL
   }

LoadDomainContent-Response ::= NULL

StoreDomainContent-Request ::= SEQUENCE {
   domainName                 [0] IMPLICIT Identifier,
   fileName                   [1] IMPLICIT FileName
,  thirdParty                 [2] IMPLICIT ApplicationReference OPTIONAL
   }

StoreDomainContent-Response ::= NULL
 DeleteDomain-Request ::= Identifier -- Domain Name
 DeleteDomain-Response ::= NULL
 GetDomainAttributes-Request ::= Identifier -- Domain Name
 GetDomainAttributes-Response ::= SEQUENCE {
   listOfCapabilities            [0] IMPLICIT SEQUENCE OF MMSString,
   state                         [1] IMPLICIT DomainState,
   mmsDeletable                  [2] IMPLICIT BOOLEAN,
   sharable                      [3] IMPLICIT BOOLEAN,
   listOfProgramInvocations      [4] IMPLICIT SEQUENCE OF Identifier,
                              -- Program Invocation Names
   uploadInProgress              [5] IMPLICIT Integer8
,  accessControlList             [6] IMPLICIT Identifier OPTIONAL
                       -- Shall not appear in minor version one or two
   }

CreateProgramInvocation-Request ::= SEQUENCE {
   programInvocationName         [0] IMPLICIT Identifier,
   listOfDomainNames             [1] IMPLICIT SEQUENCE OF Identifier,
   reusable                      [2] IMPLICIT BOOLEAN DEFAULT TRUE
,  monitorType                   [3] IMPLICIT BOOLEAN OPTIONAL
                    -- TRUE indicates PERMANENT monitoring,
                    -- FALSE indicates CURRENT monitoring
   }

CreateProgramInvocation-Response ::= NULL

CS-CreateProgramInvocation-Request ::= INTEGER {
   normal                        (0),
   controlling                   (1),
   controlled                    (2)
   } (0..2)

DeleteProgramInvocation-Request ::= Identifier   -- Program Invocation Name
 DeleteProgramInvocation-Response ::= NULL

Start-Request ::= SEQUENCE {
   programInvocationName      [0] IMPLICIT Identifier,
   executionArgument          CHOICE {
       simpleString               [1] IMPLICIT MMSString,
       encodedString              EXTERNAL,
       embeddedString             EMBEDDED PDV  } OPTIONAL }

Start-Response ::= NULL
 Start-Error ::= ProgramInvocationState

CS-Start-Request ::= [0] CHOICE {
   normal           NULL,
   controlling      SEQUENCE {
       startLocation          [0] IMPLICIT VisibleString OPTIONAL,
       startCount             [1] StartCount DEFAULT cycleCount: 1
       }  }

StartCount ::= CHOICE {
   noLimit                    [0] IMPLICIT NULL,
   cycleCount                 [1] IMPLICIT INTEGER,
   stepCount                  [2] IMPLICIT INTEGER   }

Stop-Request ::= SEQUENCE {
   programInvocationName         [0] IMPLICIT Identifier    }

Stop-Response ::= NULL
 Stop-Error ::= ProgramInvocationState

Resume-Request ::= SEQUENCE {
   programInvocationName      [0] IMPLICIT Identifier,
   executionArgument          CHOICE {
       simpleString               [1] IMPLICIT MMSString,
       encodedString              EXTERNAL,
       enmbeddedString            EMBEDDED PDV  } OPTIONAL
   }

Resume-Response ::= NULL
 Resume-Error ::= ProgramInvocationState

CS-Resume-Request ::= [0] CHOICE {
   normal                     NULL,
   controlling                SEQUENCE {
          modeType               CHOICE {
          continueMode               [0] IMPLICIT NULL,
          changeMode                 [1] StartCount
          }  }  }

Reset-Request ::= SEQUENCE {
   programInvocationName      [0] IMPLICIT Identifier    }

Reset-Response ::= NULL
 Reset-Error ::= ProgramInvocationState

Kill-Request ::= SEQUENCE {
   programInvocationName         [0] IMPLICIT Identifier    }

Kill-Response ::= NULL
 GetProgramInvocationAttributes-Request ::= Identifier  -- Program Invocation Name
 GetProgramInvocationAttributes-Response ::= SEQUENCE {
   state                         [0] IMPLICIT ProgramInvocationState,
   listOfDomainNames             [1] IMPLICIT SEQUENCE OF Identifier,
   mmsDeletable                  [2] IMPLICIT BOOLEAN,
   reusable                      [3] IMPLICIT BOOLEAN,
   monitor                       [4] IMPLICIT BOOLEAN,
   executionArgument             CHOICE {
       simpleString                  [5] IMPLICIT MMSString,
       encodedString                 EXTERNAL,
       enmbeddedString               EMBEDDED PDV     }
,  accessControlList             [6] IMPLICIT Identifier OPTIONAL
             -- Shall not appear in minor version one or two
   }

CS-GetProgramInvocationAttributes-Response ::= SEQUENCE {
   errorCode                     [0] IMPLICIT INTEGER,
   control                       [1] CHOICE {
       controlling                   [0] IMPLICIT SEQUENCE {
          controlledPI                  [0] IMPLICIT SEQUENCE OF Identifier,
          programLocation               [1] IMPLICIT VisibleString OPTIONAL,
          runningMode                   [2] CHOICE {
             freeRunning                   [0] IMPLICIT NULL,
             cycleLimited                  [1] IMPLICIT INTEGER,
             stepLimited                   [2] IMPLICIT INTEGER  }
          },
       controlled                    [1] CHOICE {
          controllingPI                 [0] IMPLICIT Identifier,
          none                          [1] IMPLICIT NULL
       },
       normal                           [2] IMPLICIT NULL   }  }

Select-Request ::= SEQUENCE {
   controlling         [0] IMPLICIT Identifier OPTIONAL,
   controlled          [1] IMPLICIT SEQUENCE OF Identifier OPTIONAL
       -- this field shall appear if and only if the controlling field is included
   }

Select-Response ::= NULL

AlterProgramInvocationAttributes-Request ::= SEQUENCE {
   programInvocation          [0] IMPLICIT Identifier,
   startCount                 [1] StartCount DEFAULT cycleCount: 1 }

AlterProgramInvocationAttributes-Response ::= NULL

ReconfigureProgramInvocation-Request ::= SEQUENCE {
   oldProgramInvocationName      [0] IMPLICIT Identifier,
   newProgramInvocationName      [1] IMPLICIT Identifier OPTIONAL,
   domainsToAdd                  [2] IMPLICIT SEQUENCE OF Identifier,
   domainsToRemove               [3] IMPLICIT SEQUENCE OF Identifier }

ReconfigureProgramInvocation-Response ::= NULL

ControlElement ::= CHOICE {
    beginDomainDef         [0] SEQUENCE {
        domainName             [1] IMPLICIT Identifier,
        capabilities           [2] IMPLICIT SEQUENCE OF MMSString,
        sharable               [3] IMPLICIT BOOLEAN,
        loadData               [4] LoadData OPTIONAL
    },
    continueDomainDef      [1] SEQUENCE {
        domainName             [1] IMPLICIT Identifier,
        loadData               [3] LoadData
    },
    endDomainDef           [2] IMPLICIT Identifier,
    piDefinition           [3] IMPLICIT SEQUENCE {
        piName                 [0] IMPLICIT Identifier,
        listOfDomains          [1] IMPLICIT SEQUENCE OF Identifier,
        reusable               [2] IMPLICIT BOOLEAN DEFAULT TRUE,
        monitorType            [3] IMPLICIT BOOLEAN OPTIONAL,
        pIState                [4] IMPLICIT ProgramInvocationState OPTIONAL
    }
}

InitiateUnitControlLoad-Request ::= Identifier -- Unit Control Name

InitiateUnitControlLoad-Response ::= NULL

InitiateUnitControl-Error ::= CHOICE {
    domain                 [0] IMPLICIT Identifier,
    programInvocation      [1] IMPLICIT Identifier
}

UnitControlLoadSegment-Request ::= Identifier -- Unit Control Name

UnitControlLoadSegment-Response ::= SEQUENCE {
    controlElements     [0] IMPLICIT SEQUENCE OF ControlElement,
    moreFollows         [1] IMPLICIT BOOLEAN DEFAULT TRUE
}

UnitControlUpload-Request ::= SEQUENCE {
    unitControlName        [0] IMPLICIT Identifier, -- Unit Control Name
    continueAfter          CHOICE {
        domain                 [1] IMPLICIT Identifier,
        ulsmID                 [2] IMPLICIT INTEGER,
        programInvocation      [3] IMPLICIT Identifier    } OPTIONAL
}

UnitControlUpload-Response ::= SEQUENCE {
    controlElements        [0] IMPLICIT SEQUENCE OF ControlElement,
    nextElement            CHOICE {
        domain                 [1] IMPLICIT Identifier,
        ulsmID                 [2] IMPLICIT INTEGER,
        programInvocation      [3] IMPLICIT Identifier    } OPTIONAL
}

StartUnitControl-Request ::= SEQUENCE {
    unitControlName        [0] IMPLICIT Identifier, -- Unit Control Name
    executionArgument      CHOICE {
        simpleString           [1] IMPLICIT MMSString,
        encodedString          EXTERNAL,
        enmbeddedString        EMBEDDED PDV } OPTIONAL
}

StartUnitControl-Response ::= NULL

-- Modified from ISO 9506 to make both fields OPTIONAL so NULL variant could
-- be encoded using `{}`. Look for where this is used. You'll see what I mean.
StartUnitControl-Error ::= SEQUENCE {
   programInvocationName      [0] IMPLICIT Identifier OPTIONAL,
   programInvocationState     [1] IMPLICIT ProgramInvocationState OPTIONAL  }

StopUnitControl-Request ::= Identifier -- Unit Control Name

StopUnitControl-Response ::= NULL

-- Modified from ISO 9506 to make both fields OPTIONAL so NULL variant could
-- be encoded using `{}`. Look for where this is used. You'll see what I mean.
StopUnitControl-Error ::=    SEQUENCE {
   programInvocationName         [0] IMPLICIT Identifier OPTIONAL,
   programInvocationState        [1] IMPLICIT ProgramInvocationState OPTIONAL  }

CreateUnitControl-Request ::=   SEQUENCE {
   unitControl                   [0] IMPLICIT Identifier, -- Unit Control Name
   domains                       [1] IMPLICIT SEQUENCE OF Identifier,
   programInvocations            [2] IMPLICIT SEQUENCE OF Identifier  }

CreateUnitControl-Response ::= NULL

AddToUnitControl-Request ::= SEQUENCE {
   unitControl            [0] IMPLICIT Identifier, -- Unit Control Name
   domains                [1] IMPLICIT SEQUENCE OF Identifier,
   programInvocations     [2] IMPLICIT SEQUENCE OF Identifier }

AddToUnitControl-Response ::= NULL

RemoveFromUnitControl-Request ::= SEQUENCE {
   unitControl            [0] IMPLICIT Identifier, -- Unit Control Name
   domains                [1] IMPLICIT SEQUENCE OF Identifier,
   programInvocations     [2] IMPLICIT SEQUENCE OF Identifier }

RemoveFromUnitControl-Response ::= NULL
 GetUnitControlAttributes-Request ::= Identifier -- Unit Control Name
 GetUnitControlAttributes-Response ::= SEQUENCE {
   domains                    [0] IMPLICIT SEQUENCE OF Identifier,
   programInvocations         [1] IMPLICIT SEQUENCE OF Identifier }

LoadUnitControlFromFile-Request ::= SEQUENCE {
   unitControlName            [0] IMPLICIT Identifier,
   fileName                   [1] IMPLICIT FileName
,  thirdParty                 [2] IMPLICIT ApplicationReference OPTIONAL
   }

LoadUnitControlFromFile-Response ::= NULL

LoadUnitControlFromFile-Error ::= CHOICE {
   none                       [0] IMPLICIT NULL,
   domain                     [1] IMPLICIT Identifier,
   programInvocation          [2] IMPLICIT Identifier
   }

StoreUnitControlToFile-Request ::= SEQUENCE {
   unitControlName            [0] IMPLICIT Identifier,
   fileName                   [1] IMPLICIT FileName
,  thirdParty                 [2] IMPLICIT ApplicationReference OPTIONAL
   }

StoreUnitControlToFile-Response ::= NULL
 DeleteUnitControl-Request ::= Identifier -- Unit Control Name
 DeleteUnitControl-Response ::= NULL

DeleteUnitControl-Error ::= CHOICE {
   domain                     [0] IMPLICIT Identifier,
   programInvocation          [1] IMPLICIT Identifier    }

TypeSpecification ::= CHOICE {
   typeName               [0] ObjectName,
   typeDescription        TypeDescription  }

AlternateAccess ::= SEQUENCE OF CHOICE {
   unnamed                AlternateAccessSelection
,  named                  [5] IMPLICIT SEQUENCE {
       componentName          [0] IMPLICIT Identifier,
       access                 AlternateAccessSelection   }
   }

AlternateAccessSelection ::= CHOICE {
   selectAlternateAccess         [0] IMPLICIT SEQUENCE {
       accessSelection            CHOICE {
          component                  [0] IMPLICIT Identifier,
       component                     [0] IMPLICIT NULL,
          index                      [1] IMPLICIT Unsigned32,
          indexRange                 [2] IMPLICIT SEQUENCE {
             lowIndex                   [0] IMPLICIT Unsigned32,
             numberOfElements           [1] IMPLICIT Unsigned32
             },
          index                      [1] IMPLICIT NULL,
          indexRange                 [2] IMPLICIT NULL,
          allElements                [3] IMPLICIT NULL
          },
       alternateAccess        AlternateAccess
       },
   selectAccess                  CHOICE {
       component                     [1] IMPLICIT Identifier,
       component                     [1] IMPLICIT NULL,
       index                         [2] IMPLICIT Unsigned32,
       indexRange                    [3] IMPLICIT SEQUENCE {
          lowIndex                      [0] IMPLICIT Unsigned32,
          numberOfElements              [1] IMPLICIT Unsigned32
          },
       index                         [2] IMPLICIT NULL,
       indexRange                    [3] IMPLICIT NULL,
       allElements                   [4] IMPLICIT NULL
       }  }

AccessResult ::= CHOICE {
   failure      [0] IMPLICIT DataAccessError,
   success      Data }

Data ::= CHOICE {
   -- context tag 0 is reserved for AccessResult
   array               [1] IMPLICIT SEQUENCE OF Data,
   structure           [2] IMPLICIT SEQUENCE OF Data,
   boolean             [3] IMPLICIT BOOLEAN,
   bit-string          [4] IMPLICIT BIT STRING,
   integer             [5] IMPLICIT INTEGER,
   unsigned            [6] IMPLICIT INTEGER, -- shall not be negative
   floating-point      [7] IMPLICIT FloatingPoint,
   -- [8] is reserved
   octet-string        [9] IMPLICIT OCTET STRING,
   visible-string      [10] IMPLICIT VisibleString,
   generalized-time    [11] IMPLICIT GeneralizedTime,
   binary-time         [12] IMPLICIT TimeOfDay,
   bcd                 [13] IMPLICIT INTEGER, -- shall not be negative
   booleanArray        [14] IMPLICIT BIT STRING,
   objId               [15] IMPLICIT OBJECT IDENTIFIER,
   ...,
   mMSString           [16] IMPLICIT MMSString
   }

FloatingPoint ::= OCTET STRING

DataAccessError ::= INTEGER {
   object-invalidated            (0),
   hardware-fault                (1),
   temporarily-unavailable       (2),
   object-access-denied          (3),
   object-undefined              (4),
   invalid-address               (5),
   type-unsupported              (6),
   type-inconsistent             (7),
   object-attribute-inconsistent (8),
   object-access-unsupported     (9),
   object-non-existent           (10),
   object-value-invalid          (11)
} (0..11)

VariableAccessSpecification ::= CHOICE {
       listOfVariable             [0] IMPLICIT SEQUENCE OF SEQUENCE {
              variableSpecification      VariableSpecification,
              alternateAccess            [5] IMPLICIT AlternateAccess OPTIONAL
       },
       variableListName           [1] ObjectName
}

VariableSpecification ::= CHOICE {
   name                   [0] ObjectName,
   address             [1] Address,
   variableDescription [2] IMPLICIT SEQUENCE {
       address                Address,
       typeSpecification      TypeSpecification
       },
   -- the following element is only present to support the services
   -- defined in annex E
   scatteredAccessDescription    [3] IMPLICIT ScatteredAccessDescription,
-- In ISO 9506, this alternative is used if (vsca).
-- However, since ScatteredAccessDescription is a SEQUENCE OF,
-- you get the exact same encoding if you just encode an empty SEQUENCE OF.
--    scatteredAccessDescription    [3] IMPLICIT NULL,
   invalidated                   [4] IMPLICIT NULL
}

Read-Request ::= SEQUENCE {
   specificationWithResult       [0] IMPLICIT BOOLEAN DEFAULT FALSE,
   variableAccessSpecification   [1] VariableAccessSpecification  }

Read-Response ::= SEQUENCE {
   variableAccessSpecification   [0] VariableAccessSpecification OPTIONAL,
   listOfAccessResult            [1] IMPLICIT SEQUENCE OF AccessResult   }

Write-Request ::= SEQUENCE {
   variableAccessSpecification   VariableAccessSpecification,
   listOfData                    [0] IMPLICIT SEQUENCE OF Data }

Write-Response ::= SEQUENCE OF CHOICE {
   failure                       [0] IMPLICIT DataAccessError,
   success                       [1] IMPLICIT NULL   }

InformationReport ::= SEQUENCE {
   variableAccessSpecification   VariableAccessSpecification,
   listOfAccessResult            [0] IMPLICIT SEQUENCE OF AccessResult }

GetVariableAccessAttributes-Request ::= CHOICE {
   name                [0] ObjectName,
   address             [1] Address
}

GetVariableAccessAttributes-Response ::= SEQUENCE {
   mmsDeletable           [0] IMPLICIT BOOLEAN,
   address                [1] Address OPTIONAL,
   typeDescription        [2] TypeDescription
,  accessControlList      [3] IMPLICIT Identifier OPTIONAL
             -- Shall not appear in minor version one or two
,  meaning                [4] IMPLICIT VisibleString OPTIONAL
   }

DefineNamedVariable-Request ::= SEQUENCE {
   variableName               [0] ObjectName,
   address                    [1] Address,
   typeSpecification          [2] TypeSpecification OPTIONAL   }

DefineNamedVariable-Response ::= NULL

DeleteVariableAccess-Request ::= SEQUENCE {
   scopeOfDelete              [0] IMPLICIT INTEGER {
       specific                   (0),
       aa-specific                (1),
       domain                     (2),
       vmd                        (3)
       } (0..3) DEFAULT specific,
   listOfName                 [1] IMPLICIT SEQUENCE OF ObjectName OPTIONAL,
   domainName                 [2] IMPLICIT Identifier OPTIONAL }

DeleteVariableAccess-Response ::= SEQUENCE {
   numberMatched              [0] IMPLICIT Unsigned32,
   numberDeleted              [1] IMPLICIT Unsigned32 }

DeleteVariableAccess-Error ::= Unsigned32 -- numberDeleted
 DefineNamedVariableList-Request ::= SEQUENCE {
   variableListName           ObjectName,
   listOfVariable             [0] IMPLICIT SEQUENCE OF SEQUENCE {
       variableSpecification      VariableSpecification
,      alternateAccess            [5] IMPLICIT AlternateAccess OPTIONAL
       }  }

DefineNamedVariableList-Response ::= NULL
 GetNamedVariableListAttributes-Request ::= ObjectName -- VariableListName
 GetNamedVariableListAttributes-Response ::= SEQUENCE {
   mmsDeletable               [0] IMPLICIT BOOLEAN,
   listOfVariable             [1] IMPLICIT SEQUENCE OF SEQUENCE {
       variableSpecification      VariableSpecification
,      alternateAccess            [5] IMPLICIT AlternateAccess OPTIONAL }
,  accessControlList          [2] IMPLICIT Identifier OPTIONAL
          -- Shall not appear in minor version one or two
   }

DeleteNamedVariableList-Request ::= SEQUENCE {
   scopeOfDelete          [0] IMPLICIT INTEGER {
       specific               (0),
       aa-specific            (1),
       domain                 (2),
       vmd                    (3)
       } (0..3) DEFAULT specific,
   listOfVariableListName [1] IMPLICIT SEQUENCE OF ObjectName OPTIONAL,
   domainName             [2] IMPLICIT Identifier OPTIONAL }

DeleteNamedVariableList-Response ::= SEQUENCE {
   numberMatched          [0] IMPLICIT Unsigned32,
   numberDeleted          [1] IMPLICIT Unsigned32    }

DeleteNamedVariableList-Error ::= Unsigned32 -- numberDeleted
 DefineNamedType-Request ::= SEQUENCE {
   typeName                   ObjectName,
   typeSpecification          TypeSpecification }

DefineNamedType-Response ::= NULL
 GetNamedTypeAttributes-Request ::= ObjectName --TypeName
 GetNamedTypeAttributes-Response ::= SEQUENCE {
   mmsDeletable               [0] IMPLICIT BOOLEAN,
   typeSpecification          TypeSpecification
,  accessControlList          [1] IMPLICIT Identifier OPTIONAL
                 -- Shall not appear in minor version one or two
,  meaning                    [4] IMPLICIT VisibleString OPTIONAL
   }

DeleteNamedType-Request ::= SEQUENCE {
   scopeOfDelete          [0] IMPLICIT INTEGER {
       specific               (0),
       aa-specific            (1),
       domain                 (2),
       vmd                    (3)
       } (0..3) DEFAULT specific,
   listOfTypeName         [1] IMPLICIT SEQUENCE OF ObjectName OPTIONAL,
   domainName             [2] IMPLICIT Identifier OPTIONAL }

DeleteNamedType-Response ::= SEQUENCE {
   numberMatched          [0] IMPLICIT Unsigned32,
   numberDeleted          [1] IMPLICIT Unsigned32
   }

DeleteNamedType-Error ::= Unsigned32 -- numberDeleted
 ExchangeData-Request ::= SEQUENCE {
   dataExchangeName           [0] ObjectName,
   listOfRequestData          [1] IMPLICIT SEQUENCE OF Data }

ExchangeData-Response ::= SEQUENCE {
   listOfResponseData         [0] IMPLICIT SEQUENCE OF Data }

GetDataExchangeAttributes-Request ::= ObjectName

GetDataExchangeAttributes-Response ::= SEQUENCE {
   inUse                            [0] IMPLICIT BOOLEAN,
   listOfRequestTypeDescriptions    [1] IMPLICIT SEQUENCE OF TypeDescription,
   listOfResponseTypeDescriptions   [2] IMPLICIT SEQUENCE OF TypeDescription,
   programInvocation                [3] IMPLICIT Identifier OPTIONAL
,  accessControlList                [4] IMPLICIT Identifier OPTIONAL
                    -- Shall not appear in minor version one or two
   }

TakeControl-Request ::= SEQUENCE {
   semaphoreName                 [0] ObjectName,
   namedToken                    [1] IMPLICIT Identifier OPTIONAL,
   priority                      [2] IMPLICIT Priority DEFAULT normalPriority,
   acceptableDelay               [3] IMPLICIT Unsigned32 OPTIONAL,
   controlTimeOut                [4] IMPLICIT Unsigned32 OPTIONAL,
   abortOnTimeOut                [5] IMPLICIT BOOLEAN OPTIONAL,
   relinquishIfConnectionLost    [6] IMPLICIT BOOLEAN DEFAULT TRUE
,  applicationToPreempt          [7] IMPLICIT ApplicationReference OPTIONAL
   }

TakeControl-Response ::= CHOICE {
   noResult                      [0] IMPLICIT NULL,
   namedToken                    [1] IMPLICIT Identifier    }

RelinquishControl-Request ::= SEQUENCE {
   semaphoreName                 [0] ObjectName,
   namedToken                    [1] IMPLICIT Identifier OPTIONAL }

RelinquishControl-Response ::= NULL

DefineSemaphore-Request ::= SEQUENCE {
   semaphoreName              [0] ObjectName,
   numberOfTokens             [1] IMPLICIT Unsigned16 }

DefineSemaphore-Response ::= NULL
 DeleteSemaphore-Request ::= ObjectName -- Semaphore Name
 DeleteSemaphore-Response ::= NULL
 ReportSemaphoreStatus-Request ::= ObjectName -- Semaphore Name
 ReportSemaphoreStatus-Response ::= SEQUENCE {
   mmsDeletable                  [0] IMPLICIT BOOLEAN,
   class                         [1] IMPLICIT INTEGER {
          token                      (0),
          pool                       (1)    } (0..1),
   numberOfTokens                [2] IMPLICIT Unsigned16,
   numberOfOwnedTokens           [3] IMPLICIT Unsigned16,
   numberOfHungTokens            [4] IMPLICIT Unsigned16
,  accessControlList             [5] IMPLICIT Identifier OPTIONAL
                    -- Shall not appear in minor version one or two
   }

ReportPoolSemaphoreStatus-Request ::= SEQUENCE {
   semaphoreName                 [0] ObjectName,
   nameToStartAfter              [1] IMPLICIT Identifier OPTIONAL }

ReportPoolSemaphoreStatus-Response ::= SEQUENCE {
   listOfNamedTokens             [0] IMPLICIT SEQUENCE OF CHOICE {
       freeNamedToken                [0] IMPLICIT Identifier,
       ownedNamedToken               [1] IMPLICIT Identifier,
       hungNamedToken                [2] IMPLICIT Identifier    },
   moreFollows                   [1] IMPLICIT BOOLEAN DEFAULT TRUE
   }

ReportSemaphoreEntryStatus-Request ::= SEQUENCE {
   semaphoreName              [0] ObjectName,
   state                      [1] IMPLICIT INTEGER {
       queued                     (0),
       owner                      (1),
       hung                       (2) } (0..2),
   entryIDToStartAfter        [2] IMPLICIT OCTET STRING OPTIONAL   }

ReportSemaphoreEntryStatus-Response ::= SEQUENCE {
   listOfSemaphoreEntry       [0] IMPLICIT SEQUENCE OF SemaphoreEntry,
   moreFollows                [1] IMPLICIT BOOLEAN DEFAULT TRUE    }

SemaphoreEntry ::= SEQUENCE {
   entryID                       [0] IMPLICIT OCTET STRING,
   entryClass                    [1] IMPLICIT INTEGER {
       simple                           (0),
       modifier                         (1)    } (0..1),
   applicationReference          [2] ApplicationReference,
   namedToken                    [3] IMPLICIT Identifier OPTIONAL,
   priority                      [4] IMPLICIT Priority DEFAULT normalPriority,
   remainingTimeOut              [5] IMPLICIT Unsigned32 OPTIONAL,
   abortOnTimeOut                [6] IMPLICIT BOOLEAN OPTIONAL,
   relinquishIfConnectionLost    [7] IMPLICIT BOOLEAN DEFAULT TRUE }

AttachToSemaphore ::= SEQUENCE {
   semaphoreName                 [0] ObjectName,
   namedToken                    [1] IMPLICIT Identifier OPTIONAL,
   priority                      [2] IMPLICIT Priority DEFAULT normalPriority,
   acceptableDelay               [3] IMPLICIT Unsigned32 OPTIONAL,
   controlTimeOut                [4] IMPLICIT Unsigned32 OPTIONAL,
   abortOnTimeOut                [5] IMPLICIT BOOLEAN OPTIONAL,
   relinquishIfConnectionLost    [6] IMPLICIT BOOLEAN DEFAULT TRUE    }

Input-Request ::= SEQUENCE {
   operatorStationName    [0] IMPLICIT Identifier,
   echo                   [1] IMPLICIT BOOLEAN DEFAULT TRUE,
   listOfPromptData       [2] IMPLICIT SEQUENCE OF MMSString OPTIONAL,
   inputTimeOut           [3] IMPLICIT Unsigned32 OPTIONAL }

Input-Response ::= MMSString -- Input String
 Output-Request ::= SEQUENCE {
   operatorStationName        [0] IMPLICIT Identifier,
   listOfOutputData           [1] IMPLICIT SEQUENCE OF MMSString   }

Output-Response ::= NULL

TriggerEvent-Request ::= SEQUENCE {
   eventConditionName     [0] ObjectName,
   priority               [1] IMPLICIT Priority OPTIONAL   }

TriggerEvent-Response ::= NULL

EventNotification ::= SEQUENCE {
   eventEnrollmentName        [0] ObjectName,
   eventConditionName         [1] ObjectName,
   severity                   [2] IMPLICIT Severity,
   currentState               [3] IMPLICIT EC-State OPTIONAL,
   transitionTime             [4] EventTime,
   notificationLost           [6] IMPLICIT BOOLEAN DEFAULT FALSE,
   alarmAcknowledgmentRule    [7] IMPLICIT AlarmAckRule OPTIONAL,
   actionResult               [8] IMPLICIT SEQUENCE {
       eventActionName            ObjectName,
       successOrFailure           CHOICE {
          success                    [0] IMPLICIT SEQUENCE {
             confirmedServiceResponse      ConfirmedServiceResponse
,            cs-Response-Detail            [79] Response-Detail OPTIONAL
                           -- shall not be transmitted if value is the
                           -- value of a tagged type derived from NULL
             },
          failure                    [1] IMPLICIT SEQUENCE {
             modifierPosition           [0] IMPLICIT Unsigned32 OPTIONAL,
             serviceError               [1] IMPLICIT ServiceError }
          }
       } OPTIONAL
   }

CS-EventNotification ::= [0] CHOICE {
   string                     [0] IMPLICIT VisibleString,
   index                      [1] IMPLICIT INTEGER,
   noEnhancement              NULL   }

AcknowledgeEventNotification-Request ::= SEQUENCE {
   eventEnrollmentName              [0] ObjectName,
   acknowledgedState                [2] IMPLICIT EC-State,
   timeOfAcknowledgedTransition     [3] EventTime }

AcknowledgeEventNotification-Response ::= NULL

GetAlarmSummary-Request ::= SEQUENCE {
   enrollmentsOnly               [0] IMPLICIT BOOLEAN DEFAULT TRUE,
   activeAlarmsOnly              [1] IMPLICIT BOOLEAN DEFAULT TRUE,
   acknowledgementFilter         [2] IMPLICIT INTEGER {
       not-acked                     (0),
       acked                         (1),
       all                           (2)
   } (0..2) DEFAULT not-acked,
   severityFilter                [3] IMPLICIT SEQUENCE {
       mostSevere                    [0] IMPLICIT Unsigned8,
       leastSevere                   [1] IMPLICIT Unsigned8 }
                                     DEFAULT { mostSevere 0, leastSevere 127 },
   continueAfter                 [5] ObjectName OPTIONAL
   }

GetAlarmSummary-Response ::= SEQUENCE {
   listOfAlarmSummary            [0] IMPLICIT SEQUENCE OF AlarmSummary,
   moreFollows                   [1] IMPLICIT BOOLEAN DEFAULT FALSE   }

AlarmSummary ::= SEQUENCE {
   eventConditionName            [0] ObjectName,
   severity                      [1] IMPLICIT Unsigned8,
   currentState                  [2] IMPLICIT EC-State,
   unacknowledgedState           [3] IMPLICIT INTEGER {
       none                          (0),
       active                        (1),
       idle                          (2),
       both                          (3)
       } (0..3),
   displayEnhancement            [4] Nullable{EN-Additional-Detail} OPTIONAL,
   timeOfLastTransitionToActive  [5] EventTime OPTIONAL,
   timeOfLastTransitionToIdle    [6] EventTime OPTIONAL }

EN-Additional-Detail ::=        [0] CHOICE {
   string                           [0] IMPLICIT VisibleString,
   index                            [1] IMPLICIT INTEGER,
   noEnhancement                    NULL   }

GetAlarmEnrollmentSummary-Request ::= SEQUENCE {
   enrollmentsOnly               [0] IMPLICIT BOOLEAN DEFAULT TRUE,
   activeAlarmsOnly              [1] IMPLICIT BOOLEAN DEFAULT TRUE,
   acknowledgementFilter         [2] IMPLICIT INTEGER {
       not-acked                     (0),
       acked                         (1),
       all                           (2)
   } (0..2) DEFAULT not-acked,
   severityFilter                [3] IMPLICIT SEQUENCE {
       mostSevere                    [0] IMPLICIT Unsigned8,
       leastSevere                   [1] IMPLICIT Unsigned8 }
                                     DEFAULT { mostSevere 0, leastSevere 127 },
   continueAfter                 [5] ObjectName OPTIONAL
   }

GetAlarmEnrollmentSummary-Response ::= SEQUENCE {
   listOfAlarmEnrollmentSummary  [0] IMPLICIT SEQUENCE OF AlarmEnrollmentSummary,
   moreFollows                   [1] IMPLICIT BOOLEAN DEFAULT FALSE }

AlarmEnrollmentSummary ::= SEQUENCE {
   eventEnrollmentName           [0] ObjectName,
   clientApplication             [2] Nullable{ApplicationReference} OPTIONAL,
   severity                      [3] IMPLICIT Unsigned8,
   currentState                  [4] IMPLICIT EC-State,
   displayEnhancement            [5] Nullable{EN-Additional-Detail} OPTIONAL,
   notificationLost              [6] IMPLICIT BOOLEAN DEFAULT FALSE,
   alarmAcknowledgmentRule       [7] IMPLICIT AlarmAckRule,
   enrollmentState               [8] IMPLICIT EE-State OPTIONAL,
   timeOfLastTransitionToActive  [9] EventTime OPTIONAL,
   timeActiveAcknowledged        [10] EventTime OPTIONAL,
   timeOfLastTransitionToIdle    [11] EventTime OPTIONAL,
   timeIdleAcknowledged          [12] EventTime OPTIONAL    }

AttachToEventCondition ::= SEQUENCE {
   eventEnrollmentName           [0] ObjectName,
   eventConditionName            [1] ObjectName,
   causingTransitions            [2] IMPLICIT Transitions,
   acceptableDelay               [3] IMPLICIT Unsigned32 OPTIONAL }

DefineEventCondition-Request ::= SEQUENCE {
   eventConditionName            [0] ObjectName,
   class                         [1] IMPLICIT EC-Class,
   priority                      [2] IMPLICIT Priority DEFAULT normalPriority,
   severity                      [3] IMPLICIT Unsigned8 DEFAULT normalSeverity,
   alarmSummaryReports           [4] IMPLICIT BOOLEAN OPTIONAL,
   monitoredVariable             [6] VariableSpecification OPTIONAL,
   evaluationInterval            [7] IMPLICIT Unsigned32 OPTIONAL }

DefineEventCondition-Response ::= NULL

CS-DefineEventCondition-Request ::= [0] CHOICE {
   string                        [0] IMPLICIT VisibleString,
   index                         [1] IMPLICIT INTEGER,
   noEnhancement                 NULL   }

DeleteEventCondition-Request ::= CHOICE {
   specific                   [0] IMPLICIT SEQUENCE OF ObjectName,
   aa-specific                [1] IMPLICIT NULL,
   domain                     [2] IMPLICIT Identifier,
   vmd                        [3] IMPLICIT NULL   }

DeleteEventCondition-Response ::= Unsigned32 --Candidates Not Deleted
 GetEventConditionAttributes-Request ::= ObjectName --Event Condition Name
 GetEventConditionAttributes-Response ::= SEQUENCE {
   mmsDeletable                  [0] IMPLICIT BOOLEAN DEFAULT FALSE,
   class                         [1] IMPLICIT EC-Class,
   priority                      [2] IMPLICIT Priority DEFAULT normalPriority,
   severity                      [3] IMPLICIT Unsigned8 DEFAULT normalSeverity,
   alarmSummaryReports           [4] IMPLICIT BOOLEAN DEFAULT FALSE,
   monitoredVariable             [6] CHOICE {
       variableReference             [0] VariableSpecification,
       undefined                     [1] IMPLICIT NULL   } OPTIONAL,
   evaluationInterval            [7] IMPLICIT Unsigned32 OPTIONAL,
   accessControlList             [8] IMPLICIT Identifier OPTIONAL
                    -- Shall not appear in minor version one or two
   }

CS-GetEventConditionAttributes-Response ::= SEQUENCE {
   groupPriorityOverride         [0] CHOICE {
       priority                      [0] IMPLICIT Priority,
       undefined                     [1] IMPLICIT NULL   } OPTIONAL,
   listOfReferencingECL          [1] IMPLICIT SEQUENCE OF ObjectName OPTIONAL,
   displayEnhancement            [2] CHOICE {
       string                        [0] IMPLICIT VisibleString,
       index                         [1] IMPLICIT INTEGER,
       noEnhancement                 [2] IMPLICIT NULL   }
   }

ReportEventConditionStatus-Request ::= ObjectName --Event Condition Name
 ReportEventConditionStatus-Response ::= SEQUENCE {
   currentState                     [0] IMPLICIT EC-State,
   numberOfEventEnrollments         [1] IMPLICIT Unsigned32,
   enabled                          [2] IMPLICIT BOOLEAN OPTIONAL,
   timeOfLastTransitionToActive     [3] EventTime OPTIONAL,
   timeOfLastTransitionToIdle       [4] EventTime OPTIONAL }

AlterEventConditionMonitoring-Request ::= SEQUENCE {
   eventConditionName            [0] ObjectName,
   enabled                       [1] IMPLICIT BOOLEAN OPTIONAL,
   priority                      [2] IMPLICIT Priority OPTIONAL,
   alarmSummaryReports           [3] IMPLICIT BOOLEAN OPTIONAL
,  evaluationInterval            [4] IMPLICIT Unsigned32 OPTIONAL
          -- At least one of enabled, priority, alarmSummaryReports, or
          -- evaluationInterval shall be present.
   }

AlterEventConditionMonitoring-Response ::= NULL

CS-AlterEventConditionMonitoring-Request ::= SEQUENCE {
   changeDisplay          CHOICE {
       string                 [0] IMPLICIT VisibleString,
       index                  [1] IMPLICIT INTEGER,
       noEnhancement          [2] NULL  } OPTIONAL
   }

DefineEventAction-Request ::= SEQUENCE {
   eventActionName               [0] ObjectName,
   listOfModifier                [1] IMPLICIT SEQUENCE OF Modifier OPTIONAL,
   confirmedServiceRequest       [2] ConfirmedServiceRequest
,  cs-extension                  [79] Request-Detail OPTIONAL
                 -- shall not be transmitted if value is the value
                 -- of a tagged type derived from NULL
   }

DefineEventAction-Response ::= NULL

DeleteEventAction-Request ::= CHOICE {
   specific                   [0] IMPLICIT SEQUENCE OF ObjectName,
   aa-specific                [1] IMPLICIT NULL,
   domain                     [3] IMPLICIT Identifier,
   vmd                        [4] IMPLICIT NULL   }

DeleteEventAction-Response ::= Unsigned32 --Candidates Not Deleted
 GetEventActionAttributes-Request ::= ObjectName --EventActionName
 GetEventActionAttributes-Response ::= SEQUENCE {
   mmsDeletable                  [0] IMPLICIT BOOLEAN DEFAULT FALSE,
   listOfModifier                [1] IMPLICIT SEQUENCE OF Modifier,
   confirmedServiceRequest       [2] ConfirmedServiceRequest
,  cs-extension                  [79] Request-Detail OPTIONAL
              -- shall not be transmitted if value is the value
              -- of a tagged type derived from NULL
,  accessControlList             [3] IMPLICIT Identifier OPTIONAL
             -- Shall not appear in minor version one or two
   }

ReportEventActionStatus-Request ::= ObjectName -- Event Action Name
 ReportEventActionStatus-Response ::= Unsigned32 -- Number of Event Enrollments
 DefineEventEnrollment-Request ::= SEQUENCE {
   eventEnrollmentName              [0] ObjectName,
   eventConditionName               [1] ObjectName,
   eventConditionTransitions        [2] IMPLICIT Transitions,
   alarmAcknowledgmentRule          [3] IMPLICIT AlarmAckRule,
   eventActionName                  [4] ObjectName OPTIONAL
,  clientApplication                [5] ApplicationReference OPTIONAL
   }

DefineEventEnrollment-Response ::= NULL
 DefineEventEnrollment-Error ::= ObjectName

CS-DefineEventEnrollment-Request ::= [0] CHOICE {
   string                           [0] IMPLICIT VisibleString,
   index                            [1] IMPLICIT INTEGER,
   noEnhancement                    NULL   }

DeleteEventEnrollment-Request ::= CHOICE {
   specific                   [0] IMPLICIT SEQUENCE OF ObjectName,
   ec                         [1] ObjectName,
   ea                         [2] ObjectName   }

DeleteEventEnrollment-Response ::= Unsigned32 --Candidates Not Deleted

GetEventEnrollmentAttributes-Request ::= SEQUENCE {
   scopeOfRequest             [0] IMPLICIT INTEGER {
       specific                   (0),
       client                     (1),
       ec                         (2),
       ea                         (3)       } (0..3) DEFAULT client,
   eventEnrollmentNames       [1] IMPLICIT SEQUENCE OF ObjectName OPTIONAL,
   clientApplication          [2] Nullable{ApplicationReference} OPTIONAL,
   eventConditionName         [3] ObjectName OPTIONAL,
   eventActionName            [4] ObjectName OPTIONAL,
   continueAfter              [5] ObjectName OPTIONAL    }

GetEventEnrollmentAttributes-Response ::= SEQUENCE {
   listOfEEAttributes            [0] IMPLICIT SEQUENCE OF EEAttributes,
   moreFollows                   [1] IMPLICIT BOOLEAN DEFAULT FALSE   }

EEAttributes ::= SEQUENCE {
   eventEnrollmentName           [0] ObjectName,
   eventConditionName            [1] CHOICE {
       eventCondition                [0] ObjectName,
       undefined                     [1] IMPLICIT NULL   },
   eventActionName               [2] CHOICE {
       eventAction                   [0] ObjectName,
       undefined                     [1] IMPLICIT NULL   }  OPTIONAL,
   clientApplication             [3] Nullable{ApplicationReference} OPTIONAL,
   mmsDeletable                  [4] IMPLICIT BOOLEAN DEFAULT FALSE,
   enrollmentClass               [5] IMPLICIT EE-Class,
   duration                      [6] IMPLICIT EE-Duration DEFAULT current,
   invokeID                      [7] IMPLICIT Unsigned32 OPTIONAL,
   remainingAcceptableDelay      [8] IMPLICIT Unsigned32 OPTIONAL,
   displayEnhancement            [9] CHOICE {
       string                        [0] IMPLICIT VisibleString,
       index                         [1] IMPLICIT INTEGER,
       noEnhancement                 NULL   },
             -- shall not be transmitted if the value is NULL
   accessControlList             [11] IMPLICIT Identifier
             -- shall not appear in minor version one or two
}

ReportEventEnrollmentStatus-Request ::= ObjectName --Event Enrollment Name

ReportEventEnrollmentStatus-Response ::= SEQUENCE {
   eventConditionTransitions     [0] IMPLICIT Transitions,
   notificationLost              [1] IMPLICIT BOOLEAN DEFAULT FALSE,
   duration                      [2] IMPLICIT EE-Duration,
   alarmAcknowledgmentRule       [3] IMPLICIT AlarmAckRule OPTIONAL,
   currentState                  [4] IMPLICIT EE-State  }

AlterEventEnrollment-Request ::= SEQUENCE {
   eventEnrollmentName           [0] ObjectName,
   eventConditionTransitions     [1] IMPLICIT Transitions OPTIONAL,
   alarmAcknowledgmentRule       [2] IMPLICIT AlarmAckRule OPTIONAL   }

AlterEventEnrollment-Response ::= SEQUENCE {
   currentState                  [0] CHOICE {
       state                         [0] IMPLICIT EE-State,
       undefined                     [1] IMPLICIT NULL   },
   transitionTime                [1] EventTime    }

CS-AlterEventEnrollment-Request ::= SEQUENCE {
   changeDisplay              CHOICE {
       string                     [0] IMPLICIT VisibleString,
       index                      [1] IMPLICIT INTEGER,
       noEnhancement              [2] NULL }    OPTIONAL }

EE-State ::= INTEGER {
   disabled         (0),
   idle             (1),
   active           (2),
   activeNoAckA     (3),
   idleNoAckI       (4),
   idleNoAckA       (5),
   idleAcked        (6),
   activeAcked      (7),
   undefined        (8)
   }

DefineEventConditionList-Request ::= SEQUENCE {
   eventConditionListName           [0] ObjectName,
   listOfEventConditionName         [1] IMPLICIT SEQUENCE OF ObjectName
,  listOfEventConditionListName     [2] IMPLICIT SEQUENCE OF ObjectName  OPTIONAL
       -- shall appear if an only if recl has been negotiated.
   }

DefineEventConditionList-Response ::= NULL
DefineEventConditionList-Error ::= ObjectName
DeleteEventConditionList-Request ::= ObjectName  -- EventConditionListName
DeleteEventConditionList-Response ::= NULL

AddEventConditionListReference-Request ::= SEQUENCE {
   eventConditionListName           [0] ObjectName,
   listOfEventConditionName         [1] IMPLICIT SEQUENCE OF ObjectName
,  listOfEventConditionListName     [2] IMPLICIT SEQUENCE OF ObjectName OPTIONAL
       -- shall appear if an only if recl has been negotiated.
   }

AddEventConditionListReference-Response ::= NULL
AddEventConditionListReference-Error ::= ObjectName

RemoveEventConditionListReference-Request ::= SEQUENCE {
   eventConditionListName           [0] ObjectName,
   listOfEventConditionName         [1] IMPLICIT SEQUENCE OF ObjectName
,  listOfEventConditionListName     [2] IMPLICIT SEQUENCE OF ObjectName
       -- shall appear if an only if recl has been negotiated.
   }

RemoveEventConditionListReference-Response ::= NULL

RemoveEventConditionListReference-Error ::= CHOICE {
   eventCondition                [0] ObjectName,
   eventConditionList            [1] ObjectName   }

GetEventConditionListAttributes-Request ::= ObjectName  -- eventConditionListName
 GetEventConditionListAttributes-Response ::= SEQUENCE {
   listOfEventConditionName         [1] IMPLICIT SEQUENCE OF ObjectName
,  listOfEventConditionListName     [2] IMPLICIT SEQUENCE OF ObjectName OPTIONAL
       -- shall appear if an only if recl has been negotiated.
   }

ReportEventConditionListStatus-Request ::= SEQUENCE {
   eventConditionListName        [0] ObjectName, -- Event Condition List Name
   continueAfter                 [1] IMPLICIT Identifier OPTIONAL }

ReportEventConditionListStatus-Response ::= SEQUENCE {
   listOfEventConditionStatus    [1] IMPLICIT SEQUENCE OF EventConditionStatus,
   moreFollows                   [2] IMPLICIT BOOLEAN DEFAULT TRUE }

EventConditionStatus ::= SEQUENCE {
   eventConditionName            [0] ObjectName,
   currentState                  [1] IMPLICIT EC-State,
   numberOfEventEnrollments      [2] IMPLICIT Unsigned32,
   enabled                       [3] IMPLICIT BOOLEAN OPTIONAL,
   timeOfLastTransitionToActive  [4] EventTime OPTIONAL,
   timeOfLastTransitionToIdle    [5] EventTime OPTIONAL }

AlterEventConditionListMonitoring-Request ::= SEQUENCE {
   eventConditionListName        [0] ObjectName,
   enabled                       [1] IMPLICIT BOOLEAN,
   priorityChange                [2] CHOICE {
       priorityValue                 [0] IMPLICIT INTEGER,
       priorityReset                 [1] IMPLICIT NULL } OPTIONAL
   }

AlterEventConditionListMonitoring-Response ::= NULL

ReadJournal-Request ::= SEQUENCE {
   journalName                [0] ObjectName,
   rangeStartSpecification    [1] CHOICE {
       startingTime               [0] IMPLICIT TimeOfDay,
       startingEntry              [1] IMPLICIT OCTET STRING } OPTIONAL,
   rangeStopSpecification     [2] CHOICE {
       endingTime                 [0] IMPLICIT TimeOfDay,
       numberOfEntries            [1] IMPLICIT Integer32 } OPTIONAL,
   listOfVariables            [4] IMPLICIT SEQUENCE OF VisibleString OPTIONAL,
   entryToStartAfter          [5] IMPLICIT SEQUENCE {
       timeSpecification          [0] IMPLICIT TimeOfDay,
       entrySpecification         [1] IMPLICIT OCTET STRING } OPTIONAL
   }

ReadJournal-Response ::= SEQUENCE {
   listOfJournalEntry         [0] IMPLICIT SEQUENCE OF JournalEntry,
       moreFollows            [1] IMPLICIT BOOLEAN DEFAULT FALSE }

JournalEntry ::=          SEQUENCE {
   entryIdentifier            [0] IMPLICIT OCTET STRING,
   originatingApplication     [1] ApplicationReference,
   entryContent               [2] IMPLICIT EntryContent }

WriteJournal-Request ::= SEQUENCE {
   journalName                [0] ObjectName,
   listOfJournalEntry         [1] IMPLICIT SEQUENCE OF EntryContent }

WriteJournal-Response ::= NULL

InitializeJournal-Request ::= SEQUENCE {
   journalName                [0] ObjectName,
   limitSpecification         [1] IMPLICIT SEQUENCE {
       limitingTime               [0] IMPLICIT TimeOfDay,
       limitingEntry              [1] IMPLICIT OCTET STRING OPTIONAL } OPTIONAL
   }

InitializeJournal-Response ::= Unsigned32 -- Entries Deleted
 ReportJournalStatus-Request ::= ObjectName  --Journal Name
 ReportJournalStatus-Response ::= SEQUENCE {
   currentEntries             [0] IMPLICIT Unsigned32,
   mmsDeletable               [1] IMPLICIT BOOLEAN
,  accessControlList          [2] IMPLICIT Identifier OPTIONAL
          -- Shall not appear in minor version one or two
   }

CreateJournal-Request ::= SEQUENCE {
   journalName         [0] ObjectName   }

CreateJournal-Response ::= NULL

DeleteJournal-Request ::= SEQUENCE {
   journalName         [0] ObjectName   }

DeleteJournal-Response ::= NULL

EntryContent ::= SEQUENCE {
   occurrenceTime         [0] IMPLICIT TimeOfDay,
   entryForm              CHOICE {
       data                   [2] IMPLICIT SEQUENCE {
          event                  [0] IMPLICIT SEQUENCE {
             eventConditionName     [0] ObjectName,
             currentState           [1] IMPLICIT EC-State  } OPTIONAL,
          listOfVariables        [1] IMPLICIT SEQUENCE OF Journal-Variable OPTIONAL
          },
       annotation             [3] MMSString    }
   }
 END
